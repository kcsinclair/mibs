-- ============================================================================
-- Copyright (C) 2013 by  HUAWEI TECHNOLOGIES. All rights reserved.
-- Description:  This mib is used for defining huawei's VDSL line management MIB objects.
-- Reference:  
-- Version: V1.53
-- ============================================================================
    HUAWEI-VDSL2-LINE-MIB DEFINITIONS ::= BEGIN
 
        IMPORTS
            MODULE-IDENTITY, OBJECT-TYPE, Unsigned32, NOTIFICATION-TYPE,
            Integer32, Counter32, Counter64                
               FROM SNMPv2-SMI           
            huaweiUtility			
              FROM HUAWEI-MIB      
            ifIndex
               FROM IF-MIB
            TruthValue, DateAndTime,  RowStatus, TEXTUAL-CONVENTION
               FROM SNMPv2-TC       
            hwFrameIndex, hwSlotIndex, hwPortIndex, hwPortOperStatus, hwPortPrimaryStatus, hwPortSecondaryStatus,
            hwConfigChangeIP
               FROM HUAWEI-DEVICE-MIB                  
            HCPerfIntervalThreshold, HCPerfTimeElapsed
               FROM  HC-PerfHist-TC-MIB   -- [RFC3705]
            hwXdslProfName
               FROM HUAWEI-XDSL-COMMON-MIB      
            Vdsl2Unit,
            Vdsl2Direction,
            Vdsl2TransmissionModeType,
            Vdsl2RaMode,
            Vdsl2InitResult,
            Vdsl2OperationModes,
            Vdsl2PowerMngState,
            Vdsl2ConfPmsForce,
            Vdsl2LConfProfPmMode,
            Vdsl2LineLdsf,
            Vdsl2LdsfResult,
            Vdsl2SymbolProtectionDs,
            Vdsl2SymbolProtectionUs,
            Vdsl2MaxBer,
            Vdsl2ScMaskDs,
            Vdsl2ScMaskUs,
            Vdsl2Rfi,
            Vdsl2vdsltoneblackout,
            Vdsl2PsdMaskDs,
            Vdsl2PsdMaskUs,
            Vdsl2Tssi,   
            Vdsl2BandPlan,
            Vdsl2LastTransmittedState,
            Vdsl2LineStatus,
            Vdsl2ChAtmStatus,
            Vdsl2ChPtmStatus,
            Vdsl2BandOptUsage,
            Vdsl2PSDClassMask,
            Vdsl2Profiles,
            Vdsl2DataPathMode,      
            Vdsl2DpboEpsd,
            Vdsl2DpboEscm,
            Vdsl2UpboPsdBand,
            Vdsl2UpboKl0RefBand,      
            Vdsl2UpboKlf,
            Vdsl2BitSwap,
            Vdsl2UpboBoostMode,
            Vdsl2ProfSwitchType,
            Vdsl2ForceINP,
            Vdsl2PhyRControl,
            Vdsl2ChEnabling,
            Vdsl2DataPathModeType,
            Vdsl2SubProfiles,
            Vdsl2SubProfilesWeight,
            Vdsl2Us0PsdMask,
            Vdsl2UpsPsdMaskSelection,
            Vdsl2TIPsdClassMask,
            Vdsl2PsdLimitMask,
            Vdsl2Us0Disable,
            Vdsl2CfgMode,
            Xdsl2Band,
            Vdsl2VirtualNoise,
            Vdsl2VirtualNoiseDs,
            Vdsl2VirtualNoiseUs,
            Vdsl2AutoProfile,
            Vdsl2StatusRtxUsed,      
            Vdsl2Actmode            
               FROM   HUAWEI-VDSL2-LINE-TC-MIB       -- [This document]
            MODULE-COMPLIANCE, OBJECT-GROUP, NOTIFICATION-GROUP
               FROM SNMPv2-CONF;
            
        vdslMIB MODULE-IDENTITY
            LAST-UPDATED "201307240000Z" 
            ORGANIZATION "Huawei Technologies Co.,Ltd."
            CONTACT-INFO                                        
                         "Huawei Industrial Base                
                          Bantian, Longgang                     
                          Shenzhen 518129                       
                          People's Republic of China            
                          Website: http://www.huawei.com        
                          Email: support@huawei.com             
                         "                                      
            DESCRIPTION               	
               "This mib is used for defining huawei's VDSL line management MIB objects."
           
            --  Revision history          
	    REVISION     "201307240000Z"
            DESCRIPTION  "V1.53,changes in this revision:                         
                          Add leaf node hwvdsl2LConfTempTemplateChangeTrap, hwvdsl2LConfProfProfileChangeTrap, hwvdsl2ChConfProfProfileChangeTrap in hwvdsl2CommonTrapsPrefix.    
                          Add leaf node hwvdsl2ProfOperType in hwvdsl2TrapsVbOids.
                         "
			             
            REVISION     "201306260000Z"
            DESCRIPTION  "V1.52,changes in this revision:                         
                          Add leaf node hwvdsl2PMLEverBeforeDisorderLeavingEvent, hwvdsl2PMLEverBeforeLof, hwvdsl2PMLEverBeforeLos, hwvdsl2PMLEverBeforeLop, hwvdsl2PMLEverBeforeLom, 
                          hwvdsl2PMLCurr15MDisorderLeavingEvent, hwvdsl2PMLCurr1DayDisorderLeavingEvent, hwvdsl2PMLCurr15MLof, hwvdsl2PMLCurr15MLos, hwvdsl2PMLCurr15MLop, 
                          hwvdsl2PMLCurr15MLom, hwvdsl2PMLCurr1DayLof, hwvdsl2PMLCurr1DayLos, hwvdsl2PMLCurr1DayLop, hwvdsl2PMLCurr1DayLom in vdsl2PMLineCurrTable.    
                          Add leaf node hwvdsl2PMLHist15MDisorderLeavingEvent, hwvdsl2PMLHist15MLof, hwvdsl2PMLHist15MLos, hwvdsl2PMLHist15MLop, hwvdsl2PMLHist15MLom in vdsl2PMLineHist15MinTable.   
                          Add leaf node hwvdsl2PMLHist1DDisorderLeavingEvent, hwvdsl2PMLHist1DLof, hwvdsl2PMLHist1DLos, hwvdsl2PMLHist1DLop, hwvdsl2PMLHist1DLom in vdsl2PMLineHist1DayTable.  
                          Modify leaf node vdsl2ChConfProfMaxDelayDs, vdsl2ChConfProfMaxDelayUs value range from (0..200) to (0..200 | 255).
                          Add leaf node hwvdsl2LineStatusActPsdLimitMask in table vdsl2LineTable for getting actual limit PSD mask."
                          
            REVISION     "201302210000Z"
            DESCRIPTION  "V1.51,changes in this revision:                         
                          Add leaf node hwvdsl2PMLCurr15MSraDownShiftEvent, hwvdsl2PMLCurr15MSraUpShiftEvent, hwvdsl2PMLCurr1DaySraDownShiftEvent, 
                          hwvdsl2PMLCurr1DaySraUpShiftEvent in vdsl2PMLineCurrTable.    
                          Add leaf node hwvdsl2PMLHist15MSraDownShiftEvent, hwvdsl2PMLHist15MSraUpShiftEvent in vdsl2PMLineHist15MinTable.   
                          Add leaf node hwvdsl2PMLHist1DSraDownShiftEvent, hwvdsl2PMLHist1DSraUpShiftEvent in vdsl2PMLineHist1DayTable.  
                          Modify leaf node vdsl2LConfProfMaxNomAtpDs, vdsl2LConfProfMaxNomAtpUs, vdsl2SpectrumProfMaxNomAtpDs, vdsl2SpectrumProfMaxNomAtpUs 
                          value range from (0..205) to (0..510)                                     
                         "
                         
            REVISION     "201301200000Z"
            DESCRIPTION  "V1.50,changes in this revision:
                          Add leaf node hwvdsl2ChStatusUnlimitedVersionEtru in vdsl2ChannelStatusTable.
                          Delete the node of vdsl2PrivSCStatusLinReal, vdsl2PrivSCStatusLinImg, vdsl2PrivSCStatusLog, vdsl2PrivSCStatusQln,
                          vdsl2PrivSCStatusLnAtten, vdsl2PrivSCStatusSigAtten, vdsl2PrivSCStatusSnrMargin, modify the node name of vdsl2PrivSCStatusLinScale,
                          vdsl2PrivSCStatusLogMt, vdsl2PrivSCStatusQlnMt, vdsl2PrivSCStatusAttainableRate, vdsl2PrivSCStatusActAtp, vdsl2PrivSCStatusRowStatus.                          
                          Add leaf node hwvdsl2PMLEverBeforeSraDownShiftEvent, hwvdsl2PMLEverBeforeSraUpShiftEvent in vdsl2PMLineCurrTable.                                             
                          Add leaf node hwvdsl2LineAlarmConfProfilePSConfigAbnormalAlarmSwitch in vdsl2LineAlarmConfProfileTable.                                            
                         "
            REVISION     "201211260000Z"
            DESCRIPTION  "V1.49, changes in this revision:
                          Add leaf node hwvdsl2LinePhyRcontrol in vdsl2LineTable.                          
                         "
            REVISION     "201211080000Z"
            DESCRIPTION  "V1.48, changes in this revision:
                          Add leaf node hwvdsl2LineSplitterMode, hwvdsl2LineBackup, hwvdsl2LineBackupPort in vdsl2LineTable.                          
                         "
            
            REVISION     "201208260000Z"
            DESCRIPTION  "V1.47, changes in this revision:
                          Add leaf node hwVdsl2LineAlarmConfProfileVictAbnormalVariationAlarmSwitch, hwVdsl2LineAlarmConfProfileDistAbnormalVariationAlarmSwitch,
                          hwVdsl2LineAlarmConfProfileReceivedESAbnormalAlarmSwitch, hwVdsl2LineAlarmConfProfileNonVectoringCPEActivatedAlarmSwitch, 
                          hwVdsl2LineAlarmConfProfileFreqRetrainReachThresholdAlarmSwitch.
                          Add leaf node hwvdsl2SCStatusSegmentQlnWithVectoring.
                         "
                         
            REVISION     "201207200000Z"
            DESCRIPTION  "V1.46, delete unnecessary en dashes.
                         "
            REVISION     "201204260000Z"
            DESCRIPTION  "V1.45, add leaf node vdsl2LconfProfUpboKlAuto.
                           Modify these leaf nodes:vdsl2ServProfRaMode,vdsl2ServProfCh1MinDataRateDs,vdsl2ServProfCh1MinDataRateUs,
                           vdsl2ServProfCh1MaxDataRateDs,vdsl2ServProfCh1MaxDataRateUs,vdsl2DelayInpProfCh1MaxDelayDs,
                           vdsl2DelayInpProfCh1MaxDelayUs,vdsl2DelayInpProfCh1MinProtectionDs,vdsl2DelayInpProfCh1MinProtectionUs.
                           Add leaf nodes:hwvdsl2ServProfMinEtrRtxDs,hwvdsl2ServProfMinEtrRtxUs,hwvdsl2ServProfMaxEtrRtxDs,hwvdsl2ServProfMaxEtrRtxUs,hwvdsl2ServProfMaxNdrRtxDs,
                           hwvdsl2ServProfMaxNdrRtxUs,hwvdsl2SpectrumProfRtxModeDs,hwvdsl2SpectrumProfRtxModeUs,hwvdsl2SpectrumProfProfLeftrThreshDs,
                           hwvdsl2SpectrumProfProfLeftrThreshUs,hwvdsl2DelayInpProfCh1MaxDelayRtxDs,hwvdsl2DelayInpProfCh1MaxDelayRtxUs,hwvdsl2DelayInpProfCh1MinDelayRtxDs,
                           hwvdsl2DelayInpProfCh1MinDelayRtxUs,hwvdsl2DelayInpProfCh1MinInpShineRtxDs,hwvdsl2DelayInpProfCh1MinInpShineRtxUs,hwvdsl2DelayInpProfCh1MinInp8ShineRtxDs,
                           hwvdsl2DelayInpProfCh1MinInp8ShineRtxUs,hwvdsl2DelayInpProfCh1ShineRatioRtxDs,hwvdsl2DelayInpProfCh1ShineRatioRtxUs,hwvdsl2DelayInpProfCh1MinInpReinRtxDs,
                           hwvdsl2DelayInpProfCh1MinInpReinRtxUs,hwvdsl2DelayInpProfCh1MinInp8ReinRtxDs,hwvdsl2DelayInpProfCh1MinInp8ReinRtxUs,hwvdsl2DelayInpProfCh1IatReinRtxDs,
                           hwvdsl2DelayInpProfCh1IatReinRtxUs.
                         "
            REVISION     "201203200000Z"
            DESCRIPTION  "V1.44, add leaf node hwVdslSCFextXLinScaleUs, hwVdslSCFextXlinScGroupSizeUs, hwVdslSCFextXLinBandUs                
                          hwVdslSCFextXlinRealUs, hwVdslSCFextXlinImgUs.
                          Modify the description of these leaf nodes hwvdsl2LineActmode,
                          vdsl2LineStatusXtuTransSys, vdsl2LineStatusLnAttenDs, vdsl2LineStatusLnAttenUs, vdsl2LineStatusSigAttenDs,       
                          vdsl2LineStatusSigAttenUs, vdsl2LineStatusSnrMarginDs, vdsl2LineStatusSnrMarginUs,vdsl2LineStatusAttainableRateDs, 
                          vdsl2LineStatusAttainableRateUs, vdsl2LineStatusActPsdDs, vdsl2LineStatusActPsdUs, vdsl2LineStatusActAtpDs,         
                          vdsl2LineStatusActAtpUs, vdsl2UpboProfKl0CpeVal, vdsl2LineStatusCodingGainDs, vdsl2LineStatusCodingGainUs,     
                          vdsl2LineStatusPcbDs, vdsl2UpboProfKl0CoVal, vdsl2UpboRxThreshDs, vdsl2UpboRxThreshUs, hwvdsl2LineStatusLineRateDs,     
                          hwvdsl2LineStatusLineRateUs, vdsl2ChStatusActDataRate, vdsl2ChStatusPrevDataRate, vdsl2ChStatusActDelay,           
                          vdsl2ChStatusINP, vdsl2ChStatusRSRedundancy, vdsl2ChStatusRSSymbols, vdsl2ChStatusInterDepth,         
                          vdsl2ChStatusSymbolLength, vdsl2ChStatusRSSize, vdsl2ChStatusInterBlockLength, vdsl2ChStatusLPATH,              
                          vdsl2ChStatusPhyRrrcBits, vdsl2ChStatusPhyRtxQueue, vdsl2ChStatusActNetDataRate, vdsl2ChStatusActINPAgainstREIN,
                          vdsl2UpboRxThreshDs, vdsl2UpboRxThreshUs.
                          Add the definition of the leaf node vdsl2MaximumInterleavedDepth.
                         "            
            REVISION     "201112050000Z"
            DESCRIPTION  "V1.43, add leaf node vdsl2SCStatusBandUpbokle,vdsl2UpboRxThreshDs,vdsl2UpboRxThreshUs,hwvdsl2LineStatusLineRateDs,
                          hwvdsl2LineStatusLineRateUs,vdsl2LConfProfAeleMode,vdsl2LConfProfUpboElmt.
                          Add the definition of the table: hwVdslSCFextTable.
                          Add leaf node hwVdsl2LineAlarmConfProfileLegacyCpeAlarmSwitch, hwvdsl2UnSuppVectorPortActFailAlarmTrap.
                          "
            REVISION     "201110150000Z"
            DESCRIPTION  "V1.42, add leaf node hwVdsl2LineAlarmConfProfileDyingGaspAlarmSwitch, hwVdsl2LineAlarmConfProfileActiveFailAlarmSwitch, hwVdsl2LineAlarmConfProfileRateChangeAlarmSwitch.
                         "
                         
            REVISION     "201109280000Z"
            DESCRIPTION  "V1.41, add leaf node vdsl2ProfileAutoNegotiationSwitch for the VDSL2 G993.2 profile auto-negotiation function.
                          modify the name of the nodes from vdsl2DpboEselGlobalConfig to vdsl2GlobalConfig."
                          
            REVISION     "201108270000Z"
            DESCRIPTION  "V1.40, modify the value range of the leaf node vdsl2NoiseMarginProfDsThresholdDs, vdsl2NoiseMarginProfUsThresholdDs, vdsl2NoiseMarginProfDsThresholdUs, 
                          vdsl2NoiseMarginProfUsThresholdUs."
                          
            REVISION     "201106080000Z"
            DESCRIPTION  "V1.39, add the definition of the leaf node vdsl2LConfProfForceInpDs, vdsl2LConfProfForceInpUs 
                          for force framer setting for impulse noise protection.
                          Add the definition of the leaf node vdsl2ChConfProfInitPolicy for setting channel initialization policy."
            
            REVISION     "201105100000Z"
            DESCRIPTION  "V1.38, add the definition of the leaf node vdsl2LineStatusLastRetrainInfo for getting the last retrained information."
            
            REVISION     "201104140000Z"                                                 
            DESCRIPTION  "V1.37, modify the description of these leaf nodes:vdsl2LConfProfPsdMaskSelectUs,vdsl2PMLHist15MInmainpeq, 
                          vdsl2PMLHist15MInmame,vdsl2PMLHist15MInmaiat,vdsl2PMLHist1DInmainpeq,vdsl2PMLHist1DInmame,vdsl2PMLHist1DInmaiat. 
                          Delete the default value of vdsl2LConfProfPsdMaskSelectUs.
                          Modify the default value of vdsl2LConfProfPSDClassMask and vdsl2LConfProfProfiles.
                          Modify the vdsl2LConfProfPsdMaskSelectUs ranges from 0 to 9." 

            REVISION     "201102210000Z"                                                 
            DESCRIPTION  "V1.36, Modify the description of these leaf nodes about default value:vdsl2LConfProfRaUsNrmDs,vdsl2LConfProfRaUsNrmUs,vdsl2LConfProfRaUsTimeDs,
                          vdsl2LConfProfRaUsTimeUs,vdsl2LConfProfRaDsNrmsDs,vdsl2LConfProfRaDsNrmsUs,vdsl2LConfProfRaDsTimeDs,vdsl2LConfProfRaDsTimeUs,
                          vdsl2LConfProfMaxSnrmDs,vdsl2LConfProfMaxSnrmUs,vdsl2LConfProfMinSnrmDs,vdsl2LConfProfMinSnrmUs,vdsl2LConfProfL2Time,vdsl2LConfProfL2Atpr,
                          vdsl2LConfProfL2Atprt,vdsl2DelayInpProfForceINP.
                          Modify the Description of these leaf nodes:vdsl2LineStatusSnrMarginDs,vdsl2LineStatusSnrMarginUs,vdsl2LineStatusActAtpDs,
                          vdsl2LineStatusActAtpUs,vdsl2LineStatusActPsdDs,vdsl2LineStatusActPsdUs.
                         " 
                                      
            REVISION     "201012120900Z"                                                 
            DESCRIPTION  "V1.35, Modify these leaf nodes:vdsl2LConfProfRaModeDs,vdsl2ChConfProfMinDataRateDs,vdsl2ChConfProfMinDataRateUs,vdsl2ChConfProfMaxDataRateDs,
                          vdsl2ChConfProfMaxDataRateUs,vdsl2ChConfProfMaxDelayDs,vdsl2ChConfProfMaxDelayUs,vdsl2ChConfProfMinProtectionDs,vdsl2ChConfProfMinProtectionUs,
                          vdsl2ChConfProfUsDataRateDs,vdsl2ChConfProfUsDataRateUs,vdsl2ChConfProfDsDataRateDs and vdsl2ChConfProfDsDataRateUs.
                          add leaf nodes:vdsl2LineAlarmConfProfileXtucThresh15MinLeftrs,vdsl2LineAlarmConfProfileXturThresh15MinLeftrs,vdsl2LConfProfRtxModeDs,
                          vdsl2LConfProfRtxModeUs,vdsl2LConfProfLeftrThreshDs,vdsl2LConfProfLeftrThreshUs,vdsl2ChConfProfMinEtrRtxDs,vdsl2ChConfProfMinEtrRtxUs,
                          vdsl2ChConfProfMaxEtrRtxDs,vdsl2ChConfProfMaxEtrRtxUs,vdsl2ChConfProfMaxNdrRtxDs,vdsl2ChConfProfMaxNdrRtxUs,vdsl2ChConfProfMaxDelayRtxDs,
                          vdsl2ChConfProfMaxDelayRtxUs,vdsl2ChConfProfMinDelayRtxDs,vdsl2ChConfProfMinDelayRtxUs,vdsl2ChConfProfMinInpShineRtxDs,vdsl2ChConfProfMinInpShineRtxUs,
                          vdsl2ChConfProfMinInp8ShineRtxDs,vdsl2ChConfProfMinInp8ShineRtxUs,vdsl2ChConfProfShineRatioRtxDs,vdsl2ChConfProfShineRatioRtxUs,vdsl2ChConfProfMinInpReinRtxDs,
                          vdsl2ChConfProfMinInpReinRtxUs,vdsl2ChConfProfMinInp8ReinRtxDs,vdsl2ChConfProfMinInp8ReinRtxUs,vdsl2ChConfProfIatReinRtxDs,vdsl2ChConfProfIatReinRtxUs.
                         " 

            REVISION     "201009270900Z"                                                 
            DESCRIPTION  "V1.34, Modify the Description of the whole MIB file.
                          modify the range of node about VDSL channel rate in table vdsl2ServProfTable." 
            
            REVISION     "201009070900Z"                                                 
            DESCRIPTION  "V1.33,Modify the Description of hwvdsl2PortStatusChangeTrap." 
            
            REVISION     "201008030900Z"
            DESCRIPTION  "V1.32, add the definition of the trap node ,include: hwvdsl2TemplateIDChangeTrap.
                          add leaf node hwVdsl2TemplateType in table hwvdsl2TrapsVbOids.
                          modify the definition of the trap node hwvdsl2DownstreamRateLowerThresholdAlarmTrap. 
                          modify the range of vdsl2LineAlarmCnfgTemplate from 1...32 to 0...32 in vdsl2LineTable.
                          Modify the description of the trap node ,include:hwvdsl2DownstreamRateLowerThresholdAlarmTrap,
                          hwvdsl2ChannelUpstreamLowerThresholdAlarmTrap,hwvdsl2ChannelUpstreamExcThreAlarmTrap,hwvdsl2ChannelUpstreamRestoreThreAlarmTrap,
                          hwvdsl2ChannelDownstreamExcThreAlarmTrap,hwvdsl2ChannelDownstreamRestoreThreAlarmTrap."
            
            REVISION     "201006220900Z"                                                 
            DESCRIPTION  "V1.31,Modify chinese character." 
            
            REVISION     "201005200900Z"
            DESCRIPTION  "V1.30, modify the definition of the trap node hwvdsl2PortStatusChangeTrap." 
            
            REVISION     "201005130900Z"
            DESCRIPTION  "V1.29, modify the vdsl2LConfProfL3Time ranges from 0 to 65535 seconds."  
            
            REVISION     "201005050900Z"                                                 
            DESCRIPTION  "V1.28, modify the errors of the MIB file."      
            
            REVISION     "201004020000Z"                                                 
            DESCRIPTION  "V1.27, add the definition of the trap node ,include:hwvdsl2DeltOperResultTrap.
                          modify the definition of the trap node ,include:hwvdsl2PortAutoDeactiveLineFaultAlarmTrap,
                          hwvdsl2PortReactiveAfterRecoverAlarmTrap,hwvdsl2PerformanceStatiReachThresholdAlarmTrap, hwvdsl2DownstreamRateLowerThresholdAlarmTrap,
                          hwvdsl2VTURPowerOffAlarmTrap, hwvdsl2PortActiveRateChangeAlarmTrap, hwvdsl2ChannelUpstreamExcThreAlarmTrap, hwvdsl2ChannelUpstreamRestoreThreAlarmTrap,
                          hwvdsl2ChannelDownstreamExcThreAlarmTrap, hwvdsl2ChannelDownstreamRestoreThreAlarmTrap." 
            
            REVISION     "201001200000Z"                                                 
            DESCRIPTION  "V1.26, add leaf node vdsl2PMLineCurr15MStartTime, vdsl2PMLineCurr1DayStartTime, vdsl2PMLineCurrInit15MStartTime, 
                          vdsl2PMLineCurrInit1DayStartTime, vdsl2PMLHist15MStartTime, vdsl2PMLHist1DStartTime, vdsl2PMLHistInit15MStartTime, 
                          vdsl2PMLHistinit1DStartTime, vdsl2PMChCurr15MStartTime, vdsl2PMChCurr1DayStartTime,
                          vdsl2PMChHist15MStartTime, vdsl2PMChHist1DStartTime  for performance monitoring.
                          create table hwvdsl2AutoDeleteProfUnused,add leaf node hwvdsl2AutoDeleteProfUnusedProfType,
                          hwvdsl2AutoDeleteProfUnusedOperType for deleting unused profile.
                          Add leaf node vdsl2UpboProfKl0CoVal in vdsl2LineTable to achieve the KL0 feature,
                          The node vdsl2UpboProfKl0Val is renamed vdsl2UpboProfKl0CpeVal."   
               
            REVISION     "201001120000Z"                                                 
            DESCRIPTION  "V1.25, add the definition of the trap node,include:
                          hwVdsl2ModeSwitchTrap
                          hwVdsl2CurrentModeTrap
                          hwVdsl2PortStatusChangeTrap
                          hwvdsl2AutoDeactivateLackLicensesAlarmTrap
                          hwvdsl2PortAutoDeactiveLineFaultAlarmTrap
                          hwvdsl2PortReactiveAfterRecoverAlarmTrap
                          hwvdsl2PerformanceStatiReachThresholdAlarmTrap
                          hwvdsl2DownstreamRateLowerThresholdAlarmTrap
                          hwvdsl2ActivePortFailConfigParaAlarmTrap
                          hwvdsl2PerformanceStatisReachThresholdAlarmTrap
                          hwvdsl2ChannelUpstreamLowerThresholdAlarmTrap
                          hwvdsl2VTURPowerOffAlarmTrap
                          hwvdsl2PortActiveRateChangeAlarmTrap
                          hwvdsl2ChipsetUnavailableAlarmTrap
                          hwvdsl2ChipsetRecoverAlarmTrap
                          "
            REVISION     "201001050000Z"          
            DESCRIPTION  "V1.24, Add leaf node vdsl2UpboProfKl0CoVal in vdsl2LineTable to achieve the KL0 feature,
                          The node vdsl2UpboProfKl0Val is renamed vdsl2UpboProfKl0CpeVal."
                   
            REVISION     "200906050000Z"          
            DESCRIPTION  "V1.19, Add leaf node in table vdsl2LineConfProfTable, vdsl2ChConfProfileTable, vdsl2PMLineCurrTable, vdsl2PMLineHist15MinTable,
                          and vdsl2PMLineHist1DayTable to achieve the save our showtime and the impulse noise monitor features. 
                          Delete enumerated values AnnexA998-D-48, AnnexA998-D-128, AnnexB998E17-M2x-A, and AnnexB998ADE17-M2x-M from leaf node vdsl2LConfProfPSDClassMask."
                                                  
            REVISION     "200806030000Z"                                                 
            DESCRIPTION  "V1.10, add leaf node hwadslLConfProfAdslMode for the actual value of coding gain parameter,
                          add leaf node vdsl2SCStatusSegmentTable for the sub-carriers."                                 
                                                                                         
            REVISION     "200604270000Z"  
            DESCRIPTION  "V1.00, Initial version."
                    
            ::= { huaweiUtility 115 }
        
        vdsl2              OBJECT IDENTIFIER ::= { vdslMIB 1 }
        vdsl2Line          OBJECT IDENTIFIER ::= { vdsl2 1 }
        vdsl2Status        OBJECT IDENTIFIER ::= { vdsl2 2 }
        vdsl2Inventory     OBJECT IDENTIFIER ::= { vdsl2 3 }
        vdsl2PM            OBJECT IDENTIFIER ::= { vdsl2 4 }
        vdsl2Profile       OBJECT IDENTIFIER ::= { vdsl2 5 }
        vdsl2Scalar        OBJECT IDENTIFIER ::= { vdsl2 6 }
        vdsl2Notifications OBJECT IDENTIFIER ::= { vdsl2 0 }
        vdsl2Conformance   OBJECT IDENTIFIER ::= { vdsl2 8 }
        vdsl2Mode          OBJECT IDENTIFIER ::= { vdsl2 9 }
        vdsl2GlobalConfig            OBJECT IDENTIFIER ::= { vdsl2 10 } 
        hwvdsl2AutoDeleteProfUnused  OBJECT IDENTIFIER ::= { vdsl2 11 } 
        hwvdsl2Traps                 OBJECT IDENTIFIER ::= { vdsl2 15 }
        hwvdsl2TrapsVbOids           OBJECT IDENTIFIER ::= { vdsl2 16 }
        
        vdsl2PMLine      OBJECT IDENTIFIER ::= { vdsl2PM 1 }
        vdsl2PMChannel   OBJECT IDENTIFIER ::= { vdsl2PM 2 }
        vdsl2ProfileLine      OBJECT IDENTIFIER ::= { vdsl2Profile 1 }
        vdsl2ProfileChannel   OBJECT IDENTIFIER ::= { vdsl2Profile 2 }
        vdsl2ProfileAlarmConf OBJECT IDENTIFIER ::= { vdsl2Profile 3 }  
        vdsl2ProfileTIMode    OBJECT IDENTIFIER ::= { vdsl2Profile 4 }  
        vdsl2ScalarSC         OBJECT IDENTIFIER ::= { vdsl2Scalar 1 }    
        hwvdsl2CommonTraps           OBJECT IDENTIFIER ::= { hwvdsl2Traps 1 }
        hwvdsl2CommonTrapsPrefix     OBJECT IDENTIFIER ::= { hwvdsl2CommonTraps 0 }
        hwvdsl2AlarmTraps            OBJECT IDENTIFIER ::= { hwvdsl2Traps 2 }
        hwvdsl2AlarmTrapsPrefix      OBJECT IDENTIFIER ::= { hwvdsl2AlarmTraps 0 }
        
        --         vdsl2LineTable                    
        vdsl2LineTable  OBJECT-TYPE
            SYNTAX      SEQUENCE  OF  Vdsl2LineEntry
            MAX-ACCESS  not-accessible
            STATUS      current
            DESCRIPTION
                "The table vdsl2LineTable contains configuration,
                 command and status parameters of the VDSL2 line.
                 The index of this table is ifIndex.
                "
            ::= { vdsl2Line 1 }
        
        vdsl2LineEntry  OBJECT-TYPE
            SYNTAX      Vdsl2LineEntry
            MAX-ACCESS  not-accessible
            STATUS      current
            DESCRIPTION
                "The table vdsl2LineTable contains configuration,
                 command and status parameters of the VDSL2 line.
                 The index of this entry is ifIndex.
                "
            INDEX  { ifIndex }
            ::= { vdsl2LineTable 1 }
        
        Vdsl2LineEntry  ::=
            SEQUENCE {
              vdsl2LineCnfgTemplate            OCTET STRING,
              vdsl2LineAlarmCnfgTemplate       OCTET STRING,
              vdsl2LineCmndConfPmsf            Vdsl2ConfPmsForce,
              vdsl2LineCmndConfLdsf            Vdsl2LineLdsf,
              vdsl2LineCmndConfLdsfFailReason  Vdsl2LdsfResult,
              vdsl2LineCmndAutomodeColdStart   TruthValue,
              vdsl2LineStatusXtuTransSys       Unsigned32,
              vdsl2LineStatusPwrMngState       Vdsl2PowerMngState,
              vdsl2LineStatusInitResult        Vdsl2InitResult,
              vdsl2LineStatusLastStateDs       Vdsl2LastTransmittedState,
              vdsl2LineStatusLastStateUs       Vdsl2LastTransmittedState,
              vdsl2LineStatusXtur              Vdsl2LineStatus,
              vdsl2LineStatusXtuc              Vdsl2LineStatus,
              vdsl2LineStatusLnAttenDs         Unsigned32,
              vdsl2LineStatusLnAttenUs         Unsigned32,
              vdsl2LineStatusSigAttenDs        Unsigned32,
              vdsl2LineStatusSigAttenUs        Unsigned32,
              vdsl2LineStatusSnrMarginDs       Integer32,
              vdsl2LineStatusSnrMarginUs       Integer32,
              vdsl2LineStatusAttainableRateDs  Unsigned32,
              vdsl2LineStatusAttainableRateUs  Unsigned32,
              vdsl2LineStatusActPsdDs          Integer32,
              vdsl2LineStatusActPsdUs          Integer32,
              vdsl2LineStatusActAtpDs          Integer32,
              vdsl2LineStatusActAtpUs          Integer32,
              vdsl2LineBandPlan                Vdsl2BandPlan,
              vdsl2LinePsdMaskClassSelection   Vdsl2TIPsdClassMask,
              vdsl2LineCurrentVdsl2Profile     Vdsl2SubProfiles,
              vdsl2LineCnfgServiceProf         OCTET STRING,
              vdsl2LineCnfgSpectrumProf        OCTET STRING,
              vdsl2LineCnfgDpboProf            OCTET STRING,
              vdsl2LineCnfgUpboProf            OCTET STRING,
              vdsl2LineCnfgNoiseMarginProf     OCTET STRING,
              vdsl2LineCnfgDelayINPProf        OCTET STRING,
              vdsl2UpboProfKl0CpeVal	       Unsigned32,
              vdsl2LineStatusCodingGainDs      Unsigned32,
              vdsl2LineStatusCodingGainUs      Unsigned32,
              vdsl2LineStatusPcbDs             Unsigned32,
              hwvdslDlmDsmprofile              OCTET STRING,        
              hwvdsl2LineActmode               Vdsl2Actmode,
              vdsl2UpboProfKl0CoVal	       Unsigned32,
              vdsl2LineStatusRtxUsedDs         Vdsl2StatusRtxUsed,
              vdsl2LineStatusRtxUsedUs         Vdsl2StatusRtxUsed,
              vdsl2LineStatusLastRetrainInfo   INTEGER,
              vdsl2UpboRxThreshDs              Integer32,
              vdsl2UpboRxThreshUs              Integer32,
              hwvdsl2LineStatusLineRateDs      Unsigned32,
              hwvdsl2LineStatusLineRateUs      Unsigned32,
              hwvdsl2LineSplitterMode          INTEGER,
              hwvdsl2LineBackup                INTEGER,
              hwvdsl2LineBackupPort            Unsigned32,
              hwvdsl2LinePhyRcontrol           INTEGER,
              hwvdsl2LineStatusActPsdLimitMask INTEGER
            }
        
        vdsl2LineCnfgTemplate  OBJECT-TYPE
            SYNTAX      OCTET STRING (SIZE(0..32))
            MAX-ACCESS  read-write
            STATUS      current
            DESCRIPTION
                "The value of this object identifies the row in the VDSL2 Line
                 Configuration Templates Table, (Vdsl2ConfTemplatesTable),
                 which applies for this VDSL2 line.
                "
            REFERENCE    "DSL Forum TR-90, paragraph 5.1.1"
            DEFVAL       { "DEFVAL" }
            ::= { vdsl2LineEntry 1 }
        
        vdsl2LineAlarmCnfgTemplate  OBJECT-TYPE
            SYNTAX      OCTET STRING (SIZE(0..32))
            MAX-ACCESS  read-write
            STATUS      current
            DESCRIPTION
                "The value of this object identifies the row in the VDSL2 Line
                 Alarm Configuration Template Table,
                 (vdsl2LineAlarmConfTemplateTable), which applies to this VDSL2
                 line.
                "
            REFERENCE    "DSL Forum TR-90, paragraph 5.1.1"
            DEFVAL       { "DEFVAL" }
            ::= { vdsl2LineEntry 2 }
        
        vdsl2LineCmndConfPmsf  OBJECT-TYPE
            SYNTAX      Vdsl2ConfPmsForce
            MAX-ACCESS  read-write
            STATUS      current
            DESCRIPTION
                "Power management state forced. Defines the line states to be
                 forced by the near-end xTU on this line.  
                 Options:
                 1. l3toL0(0)     - Force the line to transition from the L3 
                                    idle state to the L0 full-on state
                 2. l0toL2(2)     - Force the line to transition from L0 
                                    full on to L2 low power state
                 3. l0orL2toL3(3) - Force the line to transition from the L0 
                                    full-on or L2 low power state to the L3 idle state
                 4. invalidValue(-1) -Invalid value                   
                "
            REFERENCE    "ITU-T G.997.1, paragraph 7.3.1.1.3"
            DEFVAL       { l3toL0 }
            ::= { vdsl2LineEntry 3 }
        
        vdsl2LineCmndConfLdsf  OBJECT-TYPE
            SYNTAX      Vdsl2LineLdsf
            MAX-ACCESS  read-write
            STATUS      current
            DESCRIPTION
                "Loop diagnostics mode forced (LDSF). Defines whether the line
                 should be forced into the loop diagnostics mode by the
                 near-end xTU on this line or only be responsive to loop
                 diagnostics initiated by the far-end xTU. 
                "
            REFERENCE    "ITU-T G.997.1, paragraph 7.3.1.1.8"
            DEFVAL       { inhibit }
            ::= { vdsl2LineEntry 4 }
        
        vdsl2LineCmndConfLdsfFailReason  OBJECT-TYPE
            SYNTAX      Vdsl2LdsfResult
            MAX-ACCESS  read-only
            STATUS      current
            DESCRIPTION
                "The status of the recent occasion the Loop diagnostics mode
                 forced (LDSF) was issued for the associated line.  
                 Options:
                 1. none(1)         - The default value in case LDSF was never
                                      requested for the associated line
                 2. success(2)      - The recent command completed
                                      successfully
                 3. inProgress(3)   - The Loop Diagnostics process is in
                                      progress
                 4. unsupported(4)  - The NE or the line card doesn't support
                                      LDSF
                 5. cannotRun(5)    - The NE cannot initiate the command, due
                                      to a non specific reason
                 6. aborted(6)      - The Loop Diagnostics process aborted
                 7. failed(7)       - The Loop Diagnostics process failed
                 8. illegalMode(8)  - The NE cannot initiate the command, due
                                      to the specific mode of the relevant
                                      line
                 9. adminUp(9)      - The NE cannot initiate the command, as
                                      the relevant line is administratively
                                      'Up'
                 10.tableFull(10)   - The NE cannot initiate the command, due
                                      to reaching the maximum number of rows
                                      in the results table
                 11.noResources(11) - The NE cannot initiate the command, due
                                      to lack of internal memory resources
                 Default: none(1)                     
                "     
            ::= { vdsl2LineEntry 5 }
        
        vdsl2LineCmndAutomodeColdStart   OBJECT-TYPE
            SYNTAX      TruthValue
            MAX-ACCESS  read-write
            STATUS      current
            DESCRIPTION
                "Automode cold start forced. This parameter is defined
                 in order to improve testing of the performance of ATUs
                 supporting automode when it is enabled in the MIB.
                 Change the value of this parameter to 'true' indicates
                 a change in loop conditions applied to the devices under
                 test. The ATUs shall reset any historical information
                 used for automode and for shortening G.994.1 handshake
                 and initialization.                
                 Automode is the case where multiple operation-modes are
                 enabled through the vdsl2LConfProfXtuTransSysEna object
                 in the line configuration profile being used for the
                 VDSL line, and where the selection of the actual
                 operation-mode depends not only on the common
                 capabilities of both ATUs (as exchanged in G.994.1), but
                 also on achievable data rates under given loop
                 conditions. 
                "
            REFERENCE    "ITU-T G.997.1, paragraph 7.3.1.1.10"
            DEFVAL       { false }
            ::= { vdsl2LineEntry 6 }        
        
        vdsl2LineStatusXtuTransSys  OBJECT-TYPE
            SYNTAX      Unsigned32
            MAX-ACCESS  read-only
            STATUS      current
            DESCRIPTION
                "The xTU Transmission System (XTS) in use.
                 This parameter may be derived from the handshaking procedures
                 defined in Recommendation G.994.1. The invalid value is 4294967295. 
                 If data on the port is invalid or no data is generated on the 
                 port because the port has not been activated, the invalid value 
                 will be returned. One of VDSL2 line 
                 transmission modes:
                        ANSI_T1413(1)
                        ETSI_DTS_TM06006(2)
                        G9921_POTS_NONOVERLAP(3)
                        G9921_POTS_OVERLAP(4)
                        G9921_ISDN_NONOVERLAP(5)
                        G9921_ISDN_OVERLAP(6)
                        G9921_TCMISDN_NONOVERLAP(7)
                        G9921_TCMISDN_OVERLAP(8)
                        G9922_POTS_NONOVERLAP(9)
                        G9922_POTS_OVERLAP(10)
                        G9922_TCMISDN_NONOVERLAP(11)
                        G9922_TCMISDN_OVERLAP(12)
                        G9921_TCMISDN_SYMMETRIC(13)
                        G9923_POTS_NONOVERLAP(19)
                        G9923_POTS_OVERLAP(20)
                        G9923_ISDN_NONOVERLAP(21)
                        G9923_ISDN_OVERLAP(22)
                        G9924_POTS_NONOVERLAP(25)
                        G9924_POTS_OVERLAP(26)
                        G9923_ANNEXI_ALLDIGI_NONOVERLAP(29)
                        G9923_ANNEXI_ALLDIGI_OVERLAP(30)
                        G9923_ANNEXJ_ALLDIGI_NONOVERLAP(31)
                        G9923_ANNEXJ_ALLDIGI_OVERLAP(32)
                        G9924_ANNEXI_ALLDIGI_NONOVERLAP(33)
                        G9924_ANNEXI_ALLDIGI_OVERLAP(34)
                        G9923_ANNEXL_POTS_NONOVERLAP_MODE1_WIDEUS(35)
                        G9923_ANNEXL_POTS_NONOVERLAP_MODE2_NARROWUS(36)
                        G9923_ANNEXL_POTS_OVERLAP_MODE3_WIDEUS(37)
                        G9923_ANNEXL_POTS_NONOVERLAP_MODE4_NARROWUS(38)
                        G9923_ANNEXM_POTS_NONOVERLAP(39)
                        G9923_ANNEXM_POTS_OVERLAP(40)
                        G9925_POTS_NONOVERLAP(41)
                        G9925_POTS_OVERLAP(42)
                        G9925_ISDN_NONOVERLAP(43)
                        G9925_ISDN_OVERLAP(44)
                        G9925_ANNEXI_ALLDIGI_NONOVERLAP(47)
                        G9925_ANNEXI_ALLDIGI_OVERLAP(48)
                        G9925_ANNEXJ_ALLDIGI_NONOVERLAP(49)
                        G9925_ANNEXJ_ALLDIGI_OVERLAP(50)
                        G9925_ANNEXM_POTS_NONOVERLAP(51)
                        G9925_ANNEXM_POTS_OVERLAP(52)
                        G9931(65)
                        G9932_ANNEXA_POTS(73)
                        G9932_ANNEXA_ISDN(74)
                        G9932_ANNEXB_POTS(75)
                        G9932_ANNEXB_ISDN(76)
                        G9932_ANNEXC_POTS(77)
                        G9932_ANNEXC_ISDN(78)
                        G9935(79)
                        G9935_FRIENDLY_DS(80)
                        G9935_FULL_FRIENDLY(81)
               "
            ::= { vdsl2LineEntry 7 }
        
        vdsl2LineStatusPwrMngState  OBJECT-TYPE
            SYNTAX      Vdsl2PowerMngState
            MAX-ACCESS  read-only
            STATUS      current
            DESCRIPTION
                "The current power management state.  
                 Options:
                 1. L0 - Synchronized and full transmission 
                 2. L1 - Low Power with reduced net data rate 
                 3. L2 - Low Power with reduced net data rate 
                 4. L3 - No power
                 The various possible values are:l0(0), l1(1), l2(2), l3(3).
                "
            REFERENCE    "ITU-T G.997.1, paragraph 7.5.1.2"
               ::= { vdsl2LineEntry 8 }
        
        vdsl2LineStatusInitResult  OBJECT-TYPE
            SYNTAX      Vdsl2InitResult
            MAX-ACCESS  read-only
            STATUS      current
            DESCRIPTION
                "Indicates the result of the last full initialization performed
                 on the line.                   
                 Options:
                 1. noFail (0)            - Successful initialization
                 2. configError (1)       - Configuration failure
                 3. configNotFeasible (2) - Configuration details not supported
                 4. commFail (3)          - Communication failure
                 5. noPeerXtu (4)         - Peer xTU not detected
                 6. otherCause (5)        - Other initialization failure reason
                 7. ginpNotSelected(6)    - G.998.4 Retransmission mode was not selected 
                                            while RTX_MODE = FORCED or with RTX_MODE = RTX_TESTMODE
                 8. invalidValue(-1)      - Invalid value
                "
            REFERENCE    "ITU-T G.997.1, paragraph 7.5.1.3"
            ::= { vdsl2LineEntry 9 }
        
        vdsl2LineStatusLastStateDs  OBJECT-TYPE
            SYNTAX      Vdsl2LastTransmittedState
            MAX-ACCESS  read-only
            STATUS      current
            DESCRIPTION
                "The last successful transmitted initialization state in
                 the downstream direction in the last full initialization
                 performed on the line. States are per the specific VDSL type
                 and are counted from 0 (if G.994.1 is used) or 1 (if G.994.1
                 is not used) up to Showtime.
                "
            REFERENCE    "ITU-T G.997.1, paragraph 7.5.1.4"
            ::= { vdsl2LineEntry 10 }
            
        vdsl2LineStatusLastStateUs  OBJECT-TYPE
            SYNTAX      Vdsl2LastTransmittedState
            MAX-ACCESS  read-only
            STATUS      current
            DESCRIPTION
                "The last successful transmitted initialization state in the
                 upstream direction in the last full initialization performed
                 on the line.  States are per the specific VDSL type and are
                 counted from 0 (if G.994.1 is used) or 1 (if G.994.1 is not
                 used) up to Showtime.
                "
            REFERENCE    "ITU-T G.997.1, paragraph 7.5.1.5"
            ::= { vdsl2LineEntry 11 }
            
        vdsl2LineStatusXtur  OBJECT-TYPE
            SYNTAX      Vdsl2LineStatus
            MAX-ACCESS  read-only
            STATUS      current
            DESCRIPTION
                "Indicates current state (existing failures) of the xTU-R.
                 This is a bit-map of possible conditions.  The various bit
                 positions are: noFailure(0), lossOfFraming(1),
                 lossOfSignal(2), lossOfPower(3),
                 initFailure(4) - never active on xTU-R
                "
            REFERENCE    "ITU-T G.997.1, paragraph 7.1.1.2"
            ::= { vdsl2LineEntry 12 }
        
        vdsl2LineStatusXtuc  OBJECT-TYPE
            SYNTAX      Vdsl2LineStatus
            MAX-ACCESS  read-only
            STATUS      current
            DESCRIPTION
                "Indicates current state (existing failures) of the xTU-C.
                 This is a bit-map of possible conditions. This BITS structure can 
                 report the following failures:
                 1. noDefect (0)      - This bit position positively reports
                                        that no defect or failure exist
                 2. lossOfFraming (1) - Loss of frame synchronization
                 3. lossOfSignal (2)  - Loss of signal
                 4. lossOfPower (3)   - Loss of power.  Usually this failure may
                                        be reported for CPE units only
                 5. initFailure (4)   - Recent initialization process failed
                "
            REFERENCE    "ITU-T G.997.1, paragraph 7.1.1.1"
            ::= { vdsl2LineEntry 13 }
            
        vdsl2LineStatusLnAttenDs  OBJECT-TYPE
            SYNTAX      Unsigned32
            UNITS       "0.1 dB"
            MAX-ACCESS  read-only
            STATUS      current
            DESCRIPTION
                "The measured difference in the total power transmitted by the
                 xTU-C and the total power received by the xTU-R over all 
                 sub-carriers during diagnostics mode and initialization. It
                 ranges from 0 to 1270 units of 0.1 dB (Physical values
                 are 0 to 127 dB). A value of all 1's indicates the line
                 attenuation is out of range to be represented. The invalid value 
                 is 4294967295. If data on the port is invalid or no data is 
                 generated on the port because the port has not been activated, 
                 the invalid value will be returned.
                 Unit: 0.1 dB
                "
            REFERENCE    "ITU-T G.997.1, paragraph 7.5.1.6"
            ::= { vdsl2LineEntry 14 }
        
        vdsl2LineStatusLnAttenUs  OBJECT-TYPE
            SYNTAX      Unsigned32
            UNITS       "0.1 dB"
            MAX-ACCESS  read-only
            STATUS      current
            DESCRIPTION
                "The measured difference in the total power transmitted by the
                 xTU-R and the total power received by the xTU-C over all sub-
                 carriers during diagnostics mode and initialization.
                 It ranges from 0 to 1270 units of 0.1 dB (Physical values are
                 0 to 127 dB).  A value of all 1's indicates the line
                 attenuation is out of range to be represented. The invalid value 
                 is 4294967295. If data on the port is invalid or no data is 
                 generated on the port because the port has not been activated, 
                 the invalid value will be returned.
                 Unit: 0.1 dB
                "
            REFERENCE    "ITU-T G.997.1, paragraph 7.5.1.7"
            ::= { vdsl2LineEntry 15 }
        
        vdsl2LineStatusSigAttenDs  OBJECT-TYPE
            SYNTAX      Unsigned32
            UNITS       "0.1 dB"
            MAX-ACCESS  read-only
            STATUS      current
            DESCRIPTION
                "The measured difference in the total power transmitted by the
                 xTU-C and the total power received by the xTU-R over all sub-
                 carriers during Showtime.  It ranges from 0 to 1270 units of
                 0.1 dB (Physical values are 0 to 127 dB).  A value of all
                 1's indicates the line attenuation is out of range to be
                 represented. The invalid value is 4294967295. If data on the 
                 port is invalid or no data is generated on the port because 
                 the port has not been activated, the invalid value will be returned.
                 Unit: 0.1 dB
                "
            REFERENCE    "ITU-T G.997.1, paragraph 7.5.1.8"
            ::= { vdsl2LineEntry 16 }
            
        vdsl2LineStatusSigAttenUs  OBJECT-TYPE
            SYNTAX      Unsigned32
            UNITS       "0.1 dB"
            MAX-ACCESS  read-only
            STATUS      current
            DESCRIPTION
                "The measured difference in the total power transmitted by the
                 xTU-R and the total power received by the xTU-C over all sub-
                 carriers during Showtime.  It ranges from 0 to 1270 units of
                 0.1 dB (Physical values are 0 to 127 dB).  A value of all
                 1's indicates the line attenuation is out of range to be
                 represented. The invalid value is 4294967295. If data on the 
                 port is invalid or no data is generated on the port because 
                 the port has not been activated, the invalid value will be returned.
                 Unit: 0.1 dB
                "
            REFERENCE    "ITU-T G.997.1, paragraph 7.5.1.9"
            ::= { vdsl2LineEntry 17 }
        
        vdsl2LineStatusSnrMarginDs  OBJECT-TYPE
            SYNTAX      Integer32
            UNITS       "0.1 dB"
            MAX-ACCESS  read-only
            STATUS      current
            DESCRIPTION
                "Downstream SNR Margin is the maximum increase in dB of the
                 noise power received at the xTU-R, such that the BER
                 requirements are met for all downstream bearer channels.  It
                 ranges from -640 to 630 units of 0.1 dB (Physical values are
                 -64 to 63 dB).  A value of 0x7FFFFFFF(2147483647) indicates the line
                 attenuation is out of range to be represented. The invalid 
                 value is 2147483647. If data on the port is invalid or no data 
                 is generated on the port because the port has not been activated, 
                 the invalid value will be returned.
                 Unit: 0.1 dB
                "
            REFERENCE    "ITU-T G.997.1, paragraph 7.5.1.10"
            ::= { vdsl2LineEntry 18 }
        
        vdsl2LineStatusSnrMarginUs  OBJECT-TYPE
            SYNTAX      Integer32
            UNITS       "0.1 dB"
            MAX-ACCESS  read-only
            STATUS      current
            DESCRIPTION
                "Upstream SNR Margin is the maximum increase in dB of the noise
                 power received at the xTU-C, such that the BER requirements
                 are met for all downstream bearer channels.  It ranges from
                 -640 to 630 units of 0.1 dB (Physical values are -64 to
                 63 dB).  A value of 0x7FFFFFFF(2147483647) indicates the line attenuation
                 is out of range to be represented. The invalid value is 2147483647. 
                 If data on the port is invalid or no data is generated on 
                 the port because the port has not been activated, the 
                 invalid value will be returned.
                 Unit: 0.1 dB
                "
            REFERENCE    "ITU-T G.997.1, paragraph 7.5.1.11"
            ::= { vdsl2LineEntry 19 }
            
        vdsl2LineStatusAttainableRateDs  OBJECT-TYPE
            SYNTAX      Unsigned32
            UNITS       "bits/second"
            MAX-ACCESS  read-only
            STATUS      current
            DESCRIPTION
                "Maximum Attainable Data Rate Downstream.
                 The maximum downstream net data rate currently attainable by
                 the xTU-C transmitter and the xTU-R receiver, coded in bit/s.
                 The invalid value is 4294967295. If data on the port is invalid 
                 or no data is generated on the port because the port has not 
                 been activated, the invalid value will be returned.
                 Unit: bits/second
                "
            REFERENCE    "ITU-T G.997.1, paragraph 7.5.1.12"
            ::= { vdsl2LineEntry 20 }
        
        vdsl2LineStatusAttainableRateUs  OBJECT-TYPE
            SYNTAX      Unsigned32
            UNITS       "bits/second"
            MAX-ACCESS  read-only
            STATUS      current
            DESCRIPTION
                "Maximum Attainable Data Rate Upstream.
                 The maximum upstream net data rate currently attainable by the
                 xTU-R transmitter and the xTU-C receiver, coded in bit/s.
                 The invalid value is 4294967295. If data on the port is invalid 
                 or no data is generated on the port because the port has not 
                 been activated, the invalid value will be returned.
                 Unit: bits/second
                "
            REFERENCE    "ITU-T G.997.1, paragraph 7.5.1.13"
            ::= { vdsl2LineEntry 21 }
        
        vdsl2LineStatusActPsdDs OBJECT-TYPE
            SYNTAX      Integer32
            UNITS       "0.1 dB"
            MAX-ACCESS  read-only
            STATUS      current
            DESCRIPTION
                "Actual Power Spectrum Density (PSD) Downstream.  The average
                 downstream transmit PSD over the sub-carriers used for
                 downstream.  It ranges from -900 to 0 units of 0.1 dB
                 (Physical values are -90 to 0 dBm/Hz).  A value of 0x7FFFFFFF(2147483647)
                 indicates the measurement is out of range to be represented.
                 The invalid value is 2147483647. If data on the port is invalid 
                 or no data is generated on the port because the port has not 
                 been activated, the invalid value will be returned.
                 Unit: 0.1 dB
                "
            REFERENCE    "ITU-T G.997.1, paragraph 7.5.1.14"
            ::= { vdsl2LineEntry 22 }
        
        vdsl2LineStatusActPsdUs OBJECT-TYPE
            SYNTAX      Integer32
            UNITS       "0.1 dB"
            MAX-ACCESS  read-only
            STATUS      current
            DESCRIPTION
                "Actual Power Spectrum Density (PSD) Upstream.  The average
                 upstream transmit PSD over the sub-carriers used for upstream.
                 It ranges from -900 to 0 units of 0.1 dB (Physical values
                 are -90 to 0 dBm/Hz).  A value of 0x7FFFFFFF(2147483647) indicates the
                 measurement is out of range to be represented. The invalid value 
                 is 2147483647. If data on the port is invalid or no data is 
                 generated on the port because the port has not been activated, 
                 the invalid value will be returned.
                 Unit: 0.1 dB
                "
            REFERENCE    "ITU-T G.997.1, paragraph 7.5.1.15"
            ::= { vdsl2LineEntry 23 }
        
        vdsl2LineStatusActAtpDs  OBJECT-TYPE
            SYNTAX      Integer32
            UNITS       "0.1 dB"
            MAX-ACCESS  read-only
            STATUS      current
            DESCRIPTION
                "Actual Aggregate Transmit Power Downstream.  The total amount
                 of transmit power delivered by the xTU-C at the U-C reference
                 point, at the instant of measurement.  It ranges from -310 to
                 310 units of 0.1 dB (Physical values are -31 to 31 dBm).  A
                 value of 0x7FFFFFFF(2147483647) indicates the measurement is out of range to
                 be represented. The invalid value is 2147483647. If data on the
                 port is invalid or no data is generated on the port because 
                 the port has not been activated, the invalid value will be returned.
                 Unit: 0.1 dB
                "
            REFERENCE    "ITU-T G.997.1, paragraph 7.5.1.16"
            ::= { vdsl2LineEntry 24 }
        
        vdsl2LineStatusActAtpUs  OBJECT-TYPE
            SYNTAX      Integer32
            UNITS       "0.1 dB"
            MAX-ACCESS  read-only
            STATUS      current
            DESCRIPTION
                "Actual Aggregate Transmit Power Upstream.  The total amount of
                 transmit power delivered by the xTU-R at the U-R
                 reference point, at the instant of measurement.  It ranges
                 from -310 to 310 units of 0.1 dB (Physical values are -31
                 to 31 dBm).  A value of 0x7FFFFFFF(2147483647) indicates the measurement
                 is out of range to be represented.
                 Unit: 0.1 dB
                "
            REFERENCE    "ITU-T G.997.1, paragraph 7.5.1.17"
            ::= { vdsl2LineEntry 25 }   
            
        vdsl2LineBandPlan  OBJECT-TYPE
            SYNTAX      Vdsl2BandPlan
            MAX-ACCESS  read-only
            STATUS      current
            DESCRIPTION
                "Band contains a series of subcarriers. 
                 The first octet is the number of bands. Other octets describe the info of 
                 each band.
                 Each band info is a pair of values occupying 4 octets with the
        	     following structure:    	 
        	     First octets        - serial number of band
        	     Second octets       - Direction of band
        	     Third fourth octets - Start index of band
        	     Fifth sixth octets  - End index of band
                 Huawei defined.
                "
            ::= { vdsl2LineEntry 26 } 
        
        vdsl2LinePsdMaskClassSelection  OBJECT-TYPE
            SYNTAX      Vdsl2TIPsdClassMask
            MAX-ACCESS  read-only
            STATUS      current
            DESCRIPTION
                "The sub class of VDSL2 PSD Mask."
            REFERENCE    "ITU-T G.997.1, paragraph 7.3.1.1.12"
            ::= { vdsl2LineEntry 27 } 
        
        vdsl2LineCurrentVdsl2Profile  OBJECT-TYPE
            SYNTAX      Vdsl2SubProfiles
            MAX-ACCESS  read-only
            STATUS      current
            DESCRIPTION
                "This configuration parameter contains the G.993.2 profiles 
                 to be allowed by the near-end xTU on this line.
                "
            REFERENCE    "ITU-T G.997.1, paragraph 7.3.1.1.11"
            ::= { vdsl2LineEntry 28 } 
        
        vdsl2LineCnfgServiceProf  OBJECT-TYPE
            SYNTAX      OCTET STRING (SIZE(0..32))
            MAX-ACCESS  read-write
            STATUS      current
            DESCRIPTION
                "The value of this object identifies the row in the VDSL2 Line
                 Configuration Service Profile Table, (vdsl2ServProfTable),
                 which applies for this VDSL2 line.
                "
            DEFVAL       { "DEFVAL" }
            ::= { vdsl2LineEntry 29 }
        
        vdsl2LineCnfgSpectrumProf  OBJECT-TYPE
            SYNTAX      OCTET STRING (SIZE(0..32))
            MAX-ACCESS  read-write
            STATUS      current
            DESCRIPTION
                "The value of this object identifies the row in the VDSL2 Line
                 Configuration Spectrum Profile Table, (vdsl2SpectrumProfTable),
                 which applies for this VDSL2 line.
                "
            DEFVAL       { "DEFVAL" }
            ::= { vdsl2LineEntry 30 }
        
        vdsl2LineCnfgDpboProf  OBJECT-TYPE
            SYNTAX      OCTET STRING (SIZE(0..32))
            MAX-ACCESS  read-write
            STATUS      current
            DESCRIPTION
                "The value of this object identifies the row in the VDSL2 Line
                 Configuration Dpbo Profile Table, (vdsl2DpboProfTable),
                 which applies for this VDSL2 line.
                "
            DEFVAL       { "DEFVAL" }
            ::= { vdsl2LineEntry 31 } 
            
        vdsl2LineCnfgUpboProf  OBJECT-TYPE
            SYNTAX      OCTET STRING (SIZE(0..32))
            MAX-ACCESS  read-write
            STATUS      current
            DESCRIPTION
                "The value of this object identifies the row in the VDSL2 Line
                 Configuration Upbo Profile Table, (vdsl2UpboProfTable),
                 which applies for this VDSL2 line.
                "
            DEFVAL       { "DEFVAL" }
            ::= { vdsl2LineEntry 32 }
        
        vdsl2LineCnfgNoiseMarginProf  OBJECT-TYPE
            SYNTAX      OCTET STRING (SIZE(0..32))
            MAX-ACCESS  read-write
            STATUS      current
            DESCRIPTION
                "The value of this object identifies the row in the VDSL2 Line
                 Configuration Noise Margin Profile Table, (vdsl2NoiseMarginProfTable),
                 which applies for this VDSL2 line.
                "
            DEFVAL       { "DEFVAL" }
            ::= { vdsl2LineEntry 33 }
          
        vdsl2LineCnfgDelayINPProf  OBJECT-TYPE
            SYNTAX      OCTET STRING (SIZE(0..32))
            MAX-ACCESS  read-write
            STATUS      current
            DESCRIPTION
                "The value of this object identifies the row in the VDSL2 Line
                 Configuration Delay-INP Profile Table, (vdsl2DelayInpProfTable),
                 which applies for this VDSL2 line.
                "
            DEFVAL       { "DEFVAL" }
            ::= { vdsl2LineEntry 34 }
          
        vdsl2UpboProfKl0CpeVal  OBJECT-TYPE
            SYNTAX      Unsigned32
            UNITS       "0.1dB"
            MAX-ACCESS  read-only
            STATUS      current
            DESCRIPTION
                "The actual value of KL0_CPE parameter,it ranges
                 from 0 to 1280 units of 0.1 dB. The invalid value is 4294967295. 
                 If data on the port cannot be queried, data on the port is invalid, 
                 or no data is generated on the port because the port has not been 
                 activated, the invalid value will be returned.
                 Unit: 0.1dB
                "
            ::= { vdsl2LineEntry 35 }
          
        vdsl2LineStatusCodingGainDs  OBJECT-TYPE
            SYNTAX      Unsigned32
            UNITS       "0.5dB"
            MAX-ACCESS  read-only
            STATUS      current
            DESCRIPTION
                "The actual value of Coding gain downstream parameter,it ranges
                 from 0 to 16 units of 0.5 dB. The invalid value is 4294967295. 
                 If data on the port cannot be queried, data on the port is invalid, 
                 or no data is generated on the port because the port has not 
                 been activated, the invalid value will be returned.
                 Unit: 0.5dB
                "
            ::= { vdsl2LineEntry 36 }
        
        vdsl2LineStatusCodingGainUs  OBJECT-TYPE
            SYNTAX      Unsigned32
            UNITS       "0.5dB"
            MAX-ACCESS  read-only
            STATUS      current
            DESCRIPTION
                "The actual value of Coding gain upstream parameter,it ranges
                 from 0 to 16 units of 0.5 dB. The invalid value is 4294967295. 
                 If data on the port cannot be queried, data on the port is invalid, 
                 or no data is generated on the port because the port has not 
                 been activated, the invalid value will be returned.
                 Unit: 0.5dB
                "
            ::= { vdsl2LineEntry 37 }      
        
        vdsl2LineStatusPcbDs  OBJECT-TYPE
            SYNTAX      Unsigned32
            UNITS       "1dB"
            MAX-ACCESS  read-only
            STATUS      current
            DESCRIPTION
                "The actual value of power cut back downstream parameter,
                 it ranges from 0 to 40 units of 1 dB. The invalid value 
                 is 4294967295. If data on the port cannot be queried, 
                 data on the port is invalid, or no data is generated on the 
                 port because the port has not been activated, the invalid 
                 value will be returned.
                 Unit: 1dB
                "
            ::= { vdsl2LineEntry 38 }
        
        hwvdslDlmDsmprofile  OBJECT-TYPE
            SYNTAX      OCTET STRING (SIZE(0..32))
            MAX-ACCESS  read-write
            STATUS      current
            DESCRIPTION
                "The value of this object identifies the row 
                 in the DLM/DSM Profile Table, 
                 which applies for this VDSL2 line.
                "
            ::= { vdsl2LineEntry 39 }      
        
        hwvdsl2LineActmode  OBJECT-TYPE
            SYNTAX      Vdsl2Actmode
            MAX-ACCESS  read-only
            STATUS      current
            DESCRIPTION
                "Actived mode after training between co and cpe.
                 Options:
                 1. ADSL(1)          - ETSI,T1.413 G992.1,G992.2
                 2. ADSL2(2)         - G992.3,G992.4
                 3. ADSL2PLUS(3)     - G992.5
                 4. VDSL(4)          - G993.1
                 5. VDSL2(5)         - G993.2,G993.5
                 6. invalidValue(-1) - Invalid value
                "
            ::= { vdsl2LineEntry 40 }    
          
        vdsl2UpboProfKl0CoVal  OBJECT-TYPE
            SYNTAX      Unsigned32
            UNITS       "0.1dB"
            MAX-ACCESS  read-only
            STATUS      current
            DESCRIPTION
                "The actual value of KL0_CO parameter, it ranges
                 from 0 to 1280 units of 0.1 dB. The invalid value 
                 is 4294967295. If data on the port cannot be queried, 
                 data on the port is invalid, or no data is generated 
                 on the port because the port has not been activated, 
                 the invalid value will be returned.
                 Unit: 0.1dB
                "
            ::= { vdsl2LineEntry 41 }  
            
        vdsl2LineStatusRtxUsedDs  OBJECT-TYPE
            SYNTAX      Vdsl2StatusRtxUsed
            MAX-ACCESS  read-only
            STATUS      current
            DESCRIPTION
                "This parameter specifies whether G.998.4 retransmission 
                 is used in downstream.
                 Options:
                 1. rtxInuse(1)                             - RTX in use
                 2. rtxUnusedModeForbidden(2)               - RTX not in use, due to RTX_MODE = FORBIDDEN
                 3. rtxUnusedNotSupportedXtuc(3)            - RTX not in use, due to not supported by the XTU-C
                 4. rtxUnusedNotSupportedXtur(4)            - RTX not in use, due to not supported by the XTU-R
                 5. rtxUnusedNotSupportedXtucAndXtur(5)     - RTX not in use, due to not supported by the XTU-C and XTU-R
                 6. invalidValue(-1)                        - Invalid value
                "
            REFERENCE    "ITU-T G.997.1, paragraph 7.5.1.38"    
            ::= { vdsl2LineEntry 42 } 
            
            
        vdsl2LineStatusRtxUsedUs  OBJECT-TYPE
            SYNTAX      Vdsl2StatusRtxUsed
            MAX-ACCESS  read-only
            STATUS      current
            DESCRIPTION
                "This parameter specifies whether G.998.4 retransmission 
                 is used in upstream. 
                 Options:
                 1. rtxInuse(1)                             - RTX in use
                 2. rtxUnusedModeForbidden(2)               - RTX not in use, due to RTX_MODE = FORBIDDEN
                 3. rtxUnusedNotSupportedXtuc(3)            - RTX not in use, due to not supported by the XTU-C
                 4. rtxUnusedNotSupportedXtur(4)            - RTX not in use, due to not supported by the XTU-R
                 5. rtxUnusedNotSupportedXtucAndXtur(5)     - RTX not in use, due to not supported by the XTU-C and XTU-R
                 6. invalidValue(-1)                        - Invalid value
                "
            REFERENCE    "ITU-T G.997.1, paragraph 7.5.1.38"        
            ::= { vdsl2LineEntry 43 } 
            
      vdsl2LineStatusLastRetrainInfo  OBJECT-TYPE               
          SYNTAX INTEGER 
                {
                 none(1),
                 cpe-l3-trigger(2),
                 lom-us-trigger-dra(3),
                 lom-ds-trigger-dra(4),
                 cpe-never-answer-oam(5),
                 cpe-no-more-answer-oam(6),
                 persistent-ncd-us(7),
                 persistent-ncd-ds(8),
                 persistent-lcd-us(9),
                 persistent-lcd-ds(10),
                 l2-problem-co-drop(11),
                 l2-problem-cpe-drop(12),
                 bitswap-refused-us-co-drop(13),
                 bitswap-refused-us-cpe-drop(14),
                 channel-change-us-co-drop(15),
                 channel-change-us-cpe-drop(16),
                 noise-increase-us-co-drop(17),
                 noise-increase-us-cpe-drop(18),
                 bitswap-refused-ds-co-drop(19),
                 bitswap-refused-ds-cpe-drop(20),
                 channel-change-ds-co-drop(21),
                 channel-change-ds-cpe-drop(22),
                 noise-increase-ds-co-drop(23),
                 noise-increase-ds-cpe-drop(24),
                 lom-us-co-drop(25),
                 lom-us-cpe-drop(26),
                 lom-ds-co-drop(27),
                 lom-ds-cpe-drop(28),
                 sra-problem-us-co-drop(29),
                 sra-problem-us-cpe-drop(30),
                 sra-failed-us-co-drop(31),
                 sra-failed-us-cpe-drop(32),
                 sra-problem-ds-co-drop(33),
                 sra-problem-ds-cpe-drop(34),
                 sra-rejected-ds-co-drop(35),
                 sra-rejected-ds-cpe-drop(36),
                 bitswap-problem-us-co-drop(37),
                 bitswap-problem-us-cpe-drop(38),
                 bitswap-failed-us-co-drop(39),
                 bitswap-failed-us-cpe-drop(40),
                 bitswap-problem-ds-co-drop(41),
                 bitswap-problem-ds-cpe-drop(42),
                 bitswap-rejected-ds-co-drop(43),
                 bitswap-rejected-ds-cpe-drop(44),
                 cpe-switched-off(45),
                 cpe-lost(46),
                 co-reset(47),
                 co-stop(48),
                 unknown(49)
                }                      
      MAX-ACCESS  read-only                                 
      STATUS      current                                   
      DESCRIPTION                                           
         "Indicates the last retrained information performed on the line.                   
          Options:
          1. none(1)                           - No record is available                                                                                                       
          2. cpe-l3-trigger(2)                 - The terminal initiates a low power consumption L3 request                                                                           
          3. lom-us-trigger-dra(3)             - The upstream noise margin is smaller than the minimum noise margin in rate dynamic adjustment                                      
          4. lom-ds-trigger-dra(4)             - The downstream noise margin is smaller than the minimum noise margin in rate dynamic adjustment                                    
          5. cpe-never-answer-oam(5)           - No OAM response is received from the CPE all the time                                                                              
          6. cpe-no-more-answer-oam(6)         - No OAM response is received from the CPE                                                                                           
          7. persistent-ncd-us(7)              - Upstream continuous no cell delineation                                                                                                            
          8. persistent-ncd-ds(8)              - Downstream continuous no cell delineation                                                                                                          
          9. persistent-lcd-us(9)              - Upstream continuous loss of cell delineation                                                                                                            
          10.persistent-lcd-ds(10)             - Downstream continuous loss of cell delineation                                                                                                          
          11.l2-problem-co-drop(11)            - The CO is faulty during the switching from L0 to L2                                                                                
          12.l2-problem-cpe-drop(12)           - The CPE is faulty during the switching from L0 to L2                                                                               
          13.bitswap-refused-us-co-drop(13)    - The CO goes offline when the upstream bit swap fault occurs 10 times consecutively                                                 
          14.bitswap-refused-us-cpe-drop(14)   - The CPE goes offline when the downstream bit swap fault occurs 10 times consecutively                                              
          15.channel-change-us-co-drop(15)     - The CO goes offline when the upstream net rate changes                                                                             
          16.channel-change-us-cpe-drop(16)    - The CPE goes offline when the upstream net rate changes                                                                            
          17.noise-increase-us-co-drop(17)     - The CO goes offline when the upstream noise increases                                                                              
          18.noise-increase-us-cpe-drop(18)    - The CPE goes offline when the upstream noise increases                                                                             
          19.bitswap-refused-ds-co-drop(19)    - The CO goes offline when the downstream bit swap fault occurs 10 times consecutively                                               
          20.bitswap-refused-ds-cpe-drop(20)   - The CPE goes offline when the downstream bit swap fault occurs 10 times consecutively                                              
          21.channel-change-ds-co-drop(21)     - The CO goes offline when the downstream net rate changes                                                                           
          22.channel-change-ds-cpe-drop(22)    - The CPE goes offline when the downstream net rate changes                                                                          
          23.noise-increase-ds-co-drop(23)     - The CO goes offline when the downstream noise increases                                                                            
          24.noise-increase-ds-cpe-drop(24)    - The CPE goes offline when the downstream noise increases                                                                           
          25.lom-us-co-drop(25)                - The CO goes offline when the upstream noise margin is smaller than the minimum noise margin                                        
          26.lom-us-cpe-drop(26)               - The CPE goes offline when the upstream noise margin is smaller than the minimum noise margin                                       
          27.lom-ds-co-drop(27)                - The CO goes offline when the downstream noise margin is smaller than the minimum noise margin                                      
          28.lom-ds-cpe-drop(28)               - The CPE goes offline when the downstream noise margin is smaller than the minimum noise margin                                     
          29.sra-problem-us-co-drop(29)        - The CO goes offline when the upstream SRA is faulty                                                                                
          30.sra-problem-us-cpe-drop(30)       - The CPE goes offline when the upstream SRA is faulty                                                                               
          31.sra-failed-us-co-drop(31)         - The CO goes offline when the upstream SRA fails                                                                                    
          32.sra-failed-us-cpe-drop(32)        - The CPE goes offline when the upstream SRA fails                                                                                   
          33.sra-problem-ds-co-drop(33)        - The CO goes offline when the downstream SRA is fault                                                                               
          34.sra-problem-ds-cpe-drop(34)       - The CPE goes offline when the downstream SRA is faulty                                                                             
          35.sra-rejected-ds-co-drop(35)       - The CO goes offline when the downstream SRA is rejected                                                                            
          36.sra-rejected-ds-cpe-drop(36)      - The CPE goes offline when the downstream SRA is rejected                                                                           
          37.bitswap-problem-us-co-drop(37)    - The CO goes offline when the upstream bit swap is faulty                                                                           
          38.bitswap-problem-us-cpe-drop(38)   - The CPE goes offline when the upstream bit swap is faulty                                                                          
          39.bitswap-failed-us-co-drop(39)     - The CO goes offline when the upstream bit swap fails                                                                               
          40.bitswap-failed-us-cpe-drop(40)    - The CPE goes offline when the upstream bit swap fails                                                                              
          41.bitswap-problem-ds-co-drop(41)    - The CO goes offline when the downstream bit swap is faulty                                                                         
          42.bitswap-problem-ds-cpe-drop(42)   - The CPE goes offline when the downstream bit swap is faulty                                                                        
          43.bitswap-rejected-ds-co-drop(43)   - The CO goes offline when the downstream bit swap is rejected                                                                       
          44.bitswap-rejected-ds-cpe-drop(44)  - The CPE goes offline when the downstream bit swap is rejected                                                                      
          45.cpe-switched-off(45)              - The CPE power supply is shut down                                                                                                  
          46.cpe-lost(46)                      - The CPE is disconnected                                                                                                            
          47.co-reset(47)                      - The CO resets the chipset or line                                                                                                  
          48.co-stop(48)                       - The CO actively deactivate the port                                                                                               
          49.unknown(49)                       - Unknown reason                                                                                                                     
          " 
      ::= { vdsl2LineEntry 44 }      

        vdsl2UpboRxThreshDs OBJECT-TYPE
            SYNTAX      Integer32
            UNITS       "dB"
            MAX-ACCESS  read-only
            STATUS      current
            DESCRIPTION
                "This parameter reports the downstream received signal level threshold value 
                 used in the Alternative Electrical Length Estimation method (ELE-M1). 
                 This parameter represents an offset from -100 dB, 
                 and ranges from -64 dB to 0 dB in steps of 1 dB. The invalid value is 
                 2147483647. If data on the port cannot be queried, data on the port 
                 is invalid, or no data is generated on the port because the port has 
                 not been activated, the invalid value will be returned.
                 Unit: dB
                "
            REFERENCE    "ITU-T G.997.1, paragraph 7.5.1.23.5"
            ::= { vdsl2LineEntry 45 }
            
        vdsl2UpboRxThreshUs OBJECT-TYPE
            SYNTAX      Integer32
            UNITS       "dB"
            MAX-ACCESS  read-only
            STATUS      current
            DESCRIPTION
                "This parameter reports the upstream received signal level threshold value 
                 used in the Alternative Electrical Length Estimation method (ELE-M1). 
                 This parameter represents an offset from -100 dB, 
                 and ranges from -64 dB to 0 dB in steps of 1 dB. The invalid value is 
                 2147483647. If data on the port cannot be queried, data on the port 
                 is invalid, or no data is generated on the port because the port has 
                 not been activated, the invalid value will be returned.
                 Unit: dB
                "
            REFERENCE    "ITU-T G.997.1, paragraph 7.5.1.23.6"
            ::= { vdsl2LineEntry 46 }
            
        hwvdsl2LineStatusLineRateDs  OBJECT-TYPE
            SYNTAX      Unsigned32
            UNITS       "bits/second"
            MAX-ACCESS  read-only
            STATUS      current
            DESCRIPTION
                "The actual line rate downstream. The invalid value is 4294967295. 
                If data on the port cannot be queried, data on the port is invalid, 
                or no data is generated on the port because the port has not been 
                activated, the invalid value will be returned.
                 Unit: bits/second
                "
            ::= { vdsl2LineEntry 47 }  
            
        hwvdsl2LineStatusLineRateUs  OBJECT-TYPE
            SYNTAX      Unsigned32
            UNITS       "bits/second"
            MAX-ACCESS  read-only
            STATUS      current
            DESCRIPTION
                "The actual line rate upstream. The invalid value is 4294967295. 
                If data on the port cannot be queried, data on the port is invalid, 
                or no data is generated on the port because the port has not been 
                activated, the invalid value will be returned.
                 Unit: bits/second
                "
            ::= { vdsl2LineEntry 48 }
            
        hwvdsl2LineSplitterMode  OBJECT-TYPE
            SYNTAX INTEGER 
                {connect(1),
                 bypass(2)
                } 
            MAX-ACCESS  read-write       
            STATUS      current 
            DESCRIPTION
                "This parameter indicates which mode will be applied to the port 
                 splitter .The valid values for the splitter mode are 1 and 2. 
                 Options:
                 1. connect (1)          - Splitter mode is connect
                 2. bypass (2)           - Splitter mode is bypass
                "
            DEFVAL       { bypass }
            ::= { vdsl2LineEntry 49 }
            
        hwvdsl2LineBackup OBJECT-TYPE
            SYNTAX INTEGER 
                {enable(1),
                 disable(2)
                } 
            MAX-ACCESS  read-write       
            STATUS      current 
            DESCRIPTION
                 "This parameter indicates whether the port backup is enabled.
             	  Options:
             	  1. enable(1)      - Enable the port backup.
             	  2. disable(2)     - Disable the port backup.
             	 "
            DEFVAL       { disable }
            ::= { vdsl2LineEntry 50 }
            
        hwvdsl2LineBackupPort OBJECT-TYPE
            SYNTAX Unsigned32
            MAX-ACCESS  read-only
            STATUS      current
            DESCRIPTION
                 "This parameter indicates the backup port ifindex. If data on the port is invalid or no data is 
                  generated on the port, the port is not backed up.                 
                  The invalid value is 4294967295.
             	 "
            ::= { vdsl2LineEntry 51 }                

        hwvdsl2LinePhyRcontrol   OBJECT-TYPE
            SYNTAX INTEGER {
                               enable (1),
                               disable (2)
                           }
            MAX-ACCESS  read-write
            STATUS      current
            DESCRIPTION
                "This parameter indicates whether the PHY-R retransmission is enabling.
                 In TR165 mode, the H80BVDPM board should be enabled when it works as ADSL mode.
             	 Options:
             	  1. enable(1)        - Enable the PHY-R retransmission of VDSL2 line.
             	  2. disable(2)       - Disable the PHY-R retransmission of VDSL2 line.
             	"
            DEFVAL       { disable }
            ::= { vdsl2LineEntry 52 } 

        hwvdsl2LineStatusActPsdLimitMask    OBJECT-TYPE
            SYNTAX      INTEGER {
        	annexA998-D-32              (1),
            	annexA998-D-64              (2),
        	annexB997-M1c-A-7           (3),
        	annexB997-M1x-M-8           (4),
            	annexB997-M1x-M             (5),
            	annexB997-M2x-M-8           (6),
            	annexB997-M2x-A             (7),
            	annexB997-M2x-M             (8),
            	annexB998-M1x-A             (9),
            	annexB998-M1x-B             (10),
            	annexB998-M1x-NUS0          (11),
            	annexB998-M2x-A             (12),
            	annexB998-M2x-M             (13),
            	annexB998-M2x-B             (14),
            	annexB998-M2x-NUS0          (15),
            	annexBHPE17-M1-NUS0         (16),
            	annexBHPE30-M1-NUS0         (17),
            	annexB997E17-M2x-A          (18),
            	annexB997E30-M2x-NUS0       (19),
            	annexB998E17-M2x-NUS0       (20),
            	annexB998E17-M2x-NUS0-M     (21),
            	annexB998ADE17-M2x-NUS0-M   (22),
            	annexB998ADE17-M2x-B        (23),
            	annexB998E30-M2x-NUS0       (24),
            	annexB998E30-M2x-NUS0-M     (25),
            	annexB998ADE30-M2x-NUS0-M   (26),
            	annexB998ADE17-M2x-A        (27),
            	annexB998ADE30-M2x-NUS0-A   (28),
            	annexA998-D-48              (29),
            	annexA998-D-128             (30),
            	annexB998ADE17-M2x-M        (31),
            	annexB998E17-M2x-A          (32), 
            	invalidValue                (-1)
            }
            MAX-ACCESS  read-only
            STATUS      current
            DESCRIPTION
               "(LIMITMASK).
                This parameter contains the actual G.993.2 limit PSD masks selected during showtime.
                Options:
        	1. annexA998-D-32(1)                  - D-32
            	2. annexA998-D-64(2)                  - D-64
        	3. annexB997-M1c-A-7(3)               - B7-1        
        	4. annexB997-M1x-M-8(4)               - B7-2
            	5. annexB997-M1x-M(5)                 - B7-3
            	6. annexB997-M2x-M-8(6)               - B7-4
            	7. annexB997-M2x-A(7)                 - B7-5
            	8. annexB997-M2x-M(8)                 - B7-6
            	9. annexB998-M1x-A(9)                 - B8-1
            	10.annexB998-M1x-B(10)                - B8-2
            	11.annexB998-M1x-NUS0(11)             - B8-3
            	12.annexB998-M2x-A(12)                - B8-4
            	13.annexB998-M2x-M(13)                - B8-5
            	14.annexB998-M2x-B(14)                - B8-6
            	15.annexB998-M2x-NUS0(15)             - B8-7
            	16.annexBHPE17-M1-NUS0(16)            - B7-7 
            	17.annexBHPE30-M1-NUS0(17)            - B7-8
            	18.annexB997E17-M2x-A(18)             - B7-9
            	19.annexB997E30-M2x-NUS0(19)          - B7-10
            	20.annexB998E17-M2x-NUS0(20)          - B8-8
            	21.annexB998E17-M2x-NUS0-M(21)        - B8-9
            	22.annexB998ADE17-M2x-NUS0-M(22)      - B8-10
            	23.annexB998ADE17-M2x-B(23)           - B8-12
            	24.annexB998E30-M2x-NUS0(24)          - B8-13
            	25.annexB998E30-M2x-NUS0-M(25)        - B8-14
            	26.annexB998ADE30-M2x-NUS0-M(26)      - B8-15
            	27.annexB998ADE17-M2x-A(27)           - B8-11
            	28.annexB998ADE30-M2x-NUS0-A(28)      - B8-16
            	29.annexA998-D-48(29)                 - D-48
            	30.annexA998-D-128(30)                - D-128
            	31.annexB998ADE17-M2x-M(31)           - B8-17
            	32.annexB998E17-M2x-A(32)             - B8-18
            	33.invalidValue(-1)                   - Invalid value
                "
            REFERENCE    "ITU-T G.997.1, paragraph #7.3.1.2.16"            
            ::= { vdsl2LineEntry 53 }
            
        --       vdsl2ChannelStatusTable             
        vdsl2ChannelStatusTable  OBJECT-TYPE
            SYNTAX      SEQUENCE  OF  Vdsl2ChannelStatusEntry
            MAX-ACCESS  not-accessible
            STATUS      current
            DESCRIPTION
                "The table vdsl2ChannelStatusTable contains status
                 parameters of VDSL2 channel. 
                 The indexes of this table are ifIndex and vdsl2ChStatusUnit. 
                "
            ::= { vdsl2Status 1 }
        
        vdsl2ChannelStatusEntry  OBJECT-TYPE
            SYNTAX      Vdsl2ChannelStatusEntry
            MAX-ACCESS  not-accessible
            STATUS      current
            DESCRIPTION
                "The table vdsl2ChannelStatusTable contains status
                 parameters of VDSL2 channel. 
                 The indexes of this entry are ifIndex and vdsl2ChStatusUnit.
                "
            INDEX  { ifIndex, vdsl2ChStatusUnit }
            ::= { vdsl2ChannelStatusTable 1 }
        
        Vdsl2ChannelStatusEntry  ::=
           SEQUENCE {
              vdsl2ChStatusUnit                Vdsl2Unit,
              vdsl2ChStatusChannelNum          Unsigned32,
              vdsl2ChStatusActDataRate         Unsigned32,
              vdsl2ChStatusPrevDataRate        Unsigned32,
              vdsl2ChStatusActDelay            Unsigned32,
              vdsl2ChStatusAtmStatus           Vdsl2ChAtmStatus,
              vdsl2ChStatusPtmStatus           Vdsl2ChPtmStatus,
              vdsl2ChStatusINP                 Unsigned32,
              vdsl2ChStatusRSRedundancy        Unsigned32,
              vdsl2ChStatusRSSymbols           Unsigned32,
              vdsl2ChStatusInterDepth          Unsigned32,
              vdsl2ChStatusSymbolLength        Unsigned32,
              vdsl2ChStatusRSSize              Unsigned32,
              vdsl2ChStatusInterBlockLength    Unsigned32,
              vdsl2ChStatusLPATH	       Unsigned32,
              vdsl2ChStatusPhyRrrcBits	       Unsigned32,
              vdsl2ChStatusPhyRtxQueue	       Unsigned32,
              vdsl2ChStatusActNetDataRate      Unsigned32,
              vdsl2ChStatusActINPAgainstREIN   Unsigned32,
              hwvdsl2ChStatusUnlimitedVersionEtru Unsigned32
           }
        
        vdsl2ChStatusUnit  OBJECT-TYPE
            SYNTAX      Vdsl2Unit
            MAX-ACCESS  not-accessible
            STATUS      current
            DESCRIPTION
                "The termination unit xTU-C(1) or xTU-R(2)."
            ::= { vdsl2ChannelStatusEntry 1 }
            
        vdsl2ChStatusChannelNum  OBJECT-TYPE
            SYNTAX      Unsigned32
            MAX-ACCESS  read-only
            STATUS      current
            DESCRIPTION
                "Provides the bearer channel number associated with this
                 row (i.e., the channel ifIndex).
                 This enables determining the channel configuration profile
                 and the channel thresholds profile applicable for this
                 bearer channel.
                "
            ::= { vdsl2ChannelStatusEntry 2 }
        
        vdsl2ChStatusActDataRate  OBJECT-TYPE
            SYNTAX      Unsigned32(0..200000000)
            UNITS       "bits/second"
            MAX-ACCESS  read-only
            STATUS      current
            DESCRIPTION
                "If retransmission is not used in a given transmit direction, 
                 this parameter reports the actual net data rate at which the 
                 bearer channel is operating in L0 power management state, and 
                 in L1 or L2 states, the parameter contains the net data rate 
                 in the previous L0 state.
                 If retransmission is used in a given transmit direction, 
                 this parameter reports the Expected Throughput(ETR) at which the 
                 bearer channel is operating in L0 power management state, and in 
                 L1 or L2 states, the parameter contains the Expected Throughput(ETR) 
                 in the previous L0 state.
                 The data rate is coded in steps of 1000 bit/s.
                 The invalid value is 4294967295. If data on the port is invalid 
                 or no data is generated on the port because the port has not been 
                 activated, the invalid value will be returned.
                 Unit: bits/second
                "
            REFERENCE    "ITU-T G.997.1, paragraph 7.5.2.1"
            ::= { vdsl2ChannelStatusEntry 3 }
            
        vdsl2ChStatusPrevDataRate  OBJECT-TYPE
            SYNTAX      Unsigned32(0..200000000)
            UNITS       "bits/second"
            MAX-ACCESS  read-only
            STATUS      current
            DESCRIPTION
                "If retransmission is not used in a given transmit direction, this 
                 parameter reports the previous net data rate the bearer channel 
                 was operating at just before the latest net data rate change event 
                 occurred, excluding all transitions between L0 state and L1 or L2 
                 states.
                 If retransmission is used in a given transmit direction, this 
                 parameter reports the previous Expected Throughput(ETR)
                 (as defined in G.998.4) the bearer channel was operating at just 
                 before the latest ETR change event occurred, excluding all 
                 transitions between L0 state and L1 or L2 states.
                 The data rate is coded in steps of 1000 bit/s.
                 The invalid value is 4294967295. If data on the port is invalid 
                 or no data is generated on the port because the port has not 
                 been activated, the invalid value will be returned.
                 Unit: bits/second
                "
            REFERENCE    "ITU-T G.997.1, paragraph 7.5.2.2"
            ::= { vdsl2ChannelStatusEntry 4 }
        
        vdsl2ChStatusActDelay  OBJECT-TYPE
            SYNTAX      Unsigned32(0..8176)
            UNITS       "milliseconds"
            MAX-ACCESS  read-only
            STATUS      current
            DESCRIPTION
                "If retransmission is not used in a given transmit direction, this 
                 parameter is the actual one-way interleaving delay introduced by 
                 the PMS-TC excluding delay in L1 and L2 state. In L1 and L2 state, 
                 the parameter contains the interleaving delay in the previous L0 
                 state.
                 If retransmission is used in a given transmit direction, this 
                 parameter specifies the actual value of the time-independent 
                 component of the delay due to retransmission only.
                 It is coded in ms (rounded to the nearest ms).
                 The invalid value is 4294967295. If data on the port is invalid 
                 or no data is generated on the port because the port has not 
                 been activated, the invalid value will be returned.
                 Unit: milliseconds
                "
            REFERENCE    "ITU-T G.997.1, paragraph 7.5.2.3"
            ::= { vdsl2ChannelStatusEntry 5 }
        
        vdsl2ChStatusAtmStatus  OBJECT-TYPE
            SYNTAX      Vdsl2ChAtmStatus
            MAX-ACCESS  read-only
            STATUS      current
            DESCRIPTION
                "Indicates current state (existing failures) of the VDSL
                 channel in case its Data Path is ATM.  This is a bit-map of
                 possible conditions.  
                 Options:
                 1. noDefect(0)              - This bit position positively
                                               reports that no defect or failure
                                               exist
                 2. noCellDelineation(1)     - The link was successfully
                                               initialized but cell delineation
                                               was never acquired on the
                                               associated ATM data path
                 3. lossOfCellDelineation(2) - Loss of cell delineation on the
                                               associated ATM data path
                 In case the channel is not of ATM Data Path, the object is set
                 to '0'.
                "
            REFERENCE    "ITU-T G.997.1, paragraph 7.1.4"
            ::= { vdsl2ChannelStatusEntry 6 }
        
        vdsl2ChStatusPtmStatus  OBJECT-TYPE
            SYNTAX      Vdsl2ChPtmStatus
            MAX-ACCESS  read-only
            STATUS      current
            DESCRIPTION
                "Indicates current state (existing failures) of the VDSL
                 channel in case its Data Path is PTM.  This is a bit-map of
                 possible conditions.  
                 Options:
                 1. noFailure(0)   - No failure
                 2. outOfSync (1)  - Out of synchronization
                 In case the channel is not of PTM Data Path the object is set
                 to '0'.
                "
            REFERENCE    "ITU-T G.997.1, paragraph 7.1.5"
            ::= { vdsl2ChannelStatusEntry 7 }
        
        vdsl2ChStatusINP  OBJECT-TYPE
            SYNTAX      Unsigned32(0..254)
            UNITS       "0.1 DMT symbol"
            MAX-ACCESS  read-only
            STATUS      current
            DESCRIPTION
                "If retransmission is not used in a given transmit direction, this 
                 parameter reports the actual impulse noise protection (INP) on the 
                 bearer channel in the L0 state. In the L1 or L2 state, the parameter 
                 contains the INP in the previous L0 state.
                 If retransmission is used in a given transmit direction, this parameter 
                 reports the actual impulse noise protection (INP) against SHINE on 
                 the bearer channel in the L0 state. In the L2 state, the parameter 
                 contains the INP in the previous L0 state.
                 The value is coded in fractions of DMT symbols with a granularity of 0.1 symbols.
                 The invalid value is 4294967295. If data on the port is invalid or no 
                 data is generated on the port because the port has not been activated, 
                 the invalid value will be returned.
                 Unit: 0.1 DMT symbol
                "
            REFERENCE    "ITU-T G.997.1(200604), paragraph 7.5.2.4"
            ::= { vdsl2ChannelStatusEntry 8 }
           
        vdsl2ChStatusRSRedundancy  OBJECT-TYPE
            SYNTAX      Unsigned32(0..16)
            UNITS       "byte"
            MAX-ACCESS  read-only
            STATUS      current
            DESCRIPTION
                "The actual number of Reed-Solomon redundancy 
                 bytes per codeword used in the latency path 
                 in which the bearer channel is transported.
                 The value is coded in bytes. 
                 The value 0 indicates no Reed-Solomon coding.
                 The invalid value is 4294967295. If data on the port is invalid 
                 or no data is generated on the port because the port has not
                 been activated, the invalid value will be returned.
                 Unit: byte
                "
            REFERENCE    "ITU-T G.997.1(200604), paragraph 7.5.2.6.2"
            ::= { vdsl2ChannelStatusEntry 9 }
            
        vdsl2ChStatusRSSymbols  OBJECT-TYPE
            SYNTAX      Unsigned32
            UNITS       "0.01 DMT symbol"
            MAX-ACCESS  read-only
            STATUS      current
            DESCRIPTION
                "The DMT Symbol number per codeword used in 
                 the latency path in which the bearer channel
                 is transported. The invalid value is 4294967295. 
                 If data on the port is invalid or no data is generated 
                 on the port because the port has not been activated, 
                 the invalid value will be returned.
                 Unit: 0.01 DMT symbol
                "
            REFERENCE    "ITU-T G.997.1, paragraph 7.5.2.3"
            ::= { vdsl2ChannelStatusEntry 10 }
        
        vdsl2ChStatusInterDepth  OBJECT-TYPE
            SYNTAX      Unsigned32(1..4096)
            MAX-ACCESS  read-only
            STATUS      current
            DESCRIPTION
                "The actual Reed-Solomon codeword size used 
                 in the latency path in which the bearer channel 
                 is transported.
                 The value ranges from 1 to 4096 by step of 1. 
                 The value 1 indicates no interleaving. The invalid 
                 value is 4294967295. If data on the port is invalid 
                 or no data is generated on the port because the port 
                 has not been activated, the invalid value will be returned.
                "
            REFERENCE    "ITU-T G.997.1(200604), paragraph 7.5.2.6.4"
            ::= { vdsl2ChannelStatusEntry 11 }
           
        vdsl2ChStatusSymbolLength  OBJECT-TYPE
            SYNTAX      Unsigned32(0..65535)
            UNITS       "bit"
            MAX-ACCESS  read-only
            STATUS      current
            DESCRIPTION
                "The actual number of bits per symbol assigned 
                 to the latency path in which the bearer channel 
                 is transported.
                 This value does not include trellis overhead. The invalid 
                 value is 4294967295. If data on the port is invalid or no 
                 data is generated on the port because the port has not been 
                 activated, the invalid value will be returned.
                 Unit: bit
                "
            REFERENCE    "ITU-T G.997.1(200604), paragraph 7.5.2.6.3"
            ::= { vdsl2ChannelStatusEntry 12 }
            
        vdsl2ChStatusRSSize  OBJECT-TYPE
            SYNTAX      Unsigned32(0..255)
            UNITS       "byte"
            MAX-ACCESS  read-only
            STATUS      current
            DESCRIPTION
                "The actual Reed-Solomon codeword size used 
                 in the latency path in which the bearer channel 
                 is transported. The invalid value is 4294967295. 
                 If data on the port is invalid or no data is 
                 generated on the port because the port has not 
                 been activated, the invalid value will be returned.
                 Unit: byte
                "
            REFERENCE    "ITU-T G.997.1(200604), paragraph 7.5.2.6.1"
            ::= { vdsl2ChannelStatusEntry 13 }
           
        vdsl2ChStatusInterBlockLength  OBJECT-TYPE
            SYNTAX      Unsigned32(4..255)
            UNITS       "byte"
            MAX-ACCESS  read-only
            STATUS      current
            DESCRIPTION
                "The actual block length of the interleaver 
                 used in the latency path in which the bearer 
                 channel is transported. The invalid value is 4294967295. 
                 If data on the port is invalid or no data is generated 
                 on the port because the port has not been activated, 
                 the invalid value will be returned.
                 Unit: byte
                "
            REFERENCE    "ITU-T G.997.1(200604), paragraph 7.5.2.6.5"
            ::= { vdsl2ChannelStatusEntry 14 }
           
        vdsl2ChStatusLPATH  OBJECT-TYPE
            SYNTAX      Unsigned32(0..3)
            MAX-ACCESS  read-only
            STATUS      current
            DESCRIPTION
                "The index of the actual 
                 latency path in which the bearer is transported.
                 The invalid value is 4294967295. If data on the port 
                 is invalid or no data is generated on the port because 
                 the port has not been activated, the invalid value 
                 will be returned.
                "
            REFERENCE    "ITU-T G.997.1, paragraph 7.5.2.7"
            ::= { vdsl2ChannelStatusEntry 15 }    
                       
        vdsl2ChStatusPhyRrrcBits OBJECT-TYPE
            SYNTAX      Unsigned32
            MAX-ACCESS  read-only
            STATUS      current
            DESCRIPTION
                "The bits in the channel that used to retransmission.
                 The invalid value is 4294967295. If data on the port cannot 
                 be queried, data on the port is invalid, or no data is 
                 generated on the port because the port has not been 
                 activated, the invalid value will be returned.
                "
            ::= { vdsl2ChannelStatusEntry 16 }       
         
        vdsl2ChStatusPhyRtxQueue OBJECT-TYPE
            SYNTAX      Unsigned32
            MAX-ACCESS  read-only
            STATUS      current
            DESCRIPTION
                "Queues in send buffer used for retransmission.
                 The invalid value is 4294967295. If data on the port 
                 cannot be queried, data on the port is invalid, or no 
                 data is generated on the port because the port has 
                 not been activated, the invalid value will be returned.
                "
            ::= { vdsl2ChannelStatusEntry 17 } 
            
        vdsl2ChStatusActNetDataRate OBJECT-TYPE
            SYNTAX      Unsigned32
            UNITS       "bits/second"             
            MAX-ACCESS  read-only
            STATUS      current
            DESCRIPTION
                "In L0 state, this parameter reports the Net Data Rate at which the bearer channel is operating. 
                 In L2 state, this parameter contains the Net Data Rate in the previous L0 state. 
                 This parameter is optional if G.998.4 retransmission function is not supported.
                 The data rate is coded in steps of 1000 bit/s. The invalid value is 4294967295. 
                 If data on the port cannot be queried, data on the port is invalid, 
                 or no data is generated on the port because the port has not been activated, 
                 the invalid value will be returned.
                "
            REFERENCE    "ITU-T G.997.1, paragraph 7.5.2.8"    
            ::= { vdsl2ChannelStatusEntry 18 }             
            
        vdsl2ChStatusActINPAgainstREIN OBJECT-TYPE
            SYNTAX      Unsigned32
            MAX-ACCESS  read-only
            STATUS      current
            DESCRIPTION
                "If retransmission is used in a given transmit direction, 
                 this parameter reports the actual impulse noise protection (INP) 
                 against REIN (under specific conditions detailed in G.998.4) 
                 on the bearer channel in the L0 state. In the L2 state, the 
                 parameter contains the INP in the previous L0 state. The value 
                 is coded in fractions of DMT symbols with a granularity of 0.1 symbols.
                 The invalid value is 4294967295. If data on the port cannot be 
                 queried, data on the port is invalid, or no data is generated 
                 on the port because the port has not been activated, the invalid 
                 value will be returned.
                "
            REFERENCE    "ITU-T G.997.1, paragraph 7.5.2.9"     
            ::= { vdsl2ChannelStatusEntry 19 } 
            
        hwvdsl2ChStatusUnlimitedVersionEtru OBJECT-TYPE
            SYNTAX      Unsigned32
            UNITS       "bits/second"
            MAX-ACCESS  read-only
            STATUS      current
            DESCRIPTION
                "The unlimited version of expected throughput in kbit/s:(1 - RTxOH) * NDR. 
                 This value is specified in G.998.4 (G.INP)."
            ::= { vdsl2ChannelStatusEntry 20 } 
         	   
        --       vdsl2PrivSCStatusTable                
        
        vdsl2PrivSCStatusTable  OBJECT-TYPE
            SYNTAX      SEQUENCE  OF  Vdsl2PrivSCStatusEntry
            MAX-ACCESS  not-accessible
            STATUS      current
            DESCRIPTION
                "The table vdsl2PrivSCStatusTable contains status parameters
                 of VDSL2 sub-carriers. 
                 The indexes of this table are ifIndex and vdsl2PrivSCStatusDirection. 
                "
            ::= { vdsl2Status 2 }
            
        vdsl2PrivSCStatusEntry  OBJECT-TYPE
            SYNTAX      Vdsl2PrivSCStatusEntry
            MAX-ACCESS  not-accessible
            STATUS      current
            DESCRIPTION
                "The table vdsl2PrivSCStatusTable contains status parameters
                 of VDSL2 sub-carriers. 
                 The indexes of this entry are ifIndex and vdsl2PrivSCStatusDirection.
                "
            INDEX  { ifIndex, vdsl2PrivSCStatusDirection }
            ::= { vdsl2PrivSCStatusTable 1 }
            
        Vdsl2PrivSCStatusEntry  ::=
            SEQUENCE {
              vdsl2PrivSCStatusDirection         Vdsl2Direction,
              vdsl2PrivSCStatusMtime             Unsigned32,
              vdsl2PrivSCStatusSnr               OCTET STRING,
              vdsl2PrivSCStatusBitsAlloc         OCTET STRING,
              vdsl2PrivSCStatusGainAlloc         OCTET STRING
            }
        
        vdsl2PrivSCStatusDirection  OBJECT-TYPE
            SYNTAX      Vdsl2Direction
            MAX-ACCESS  not-accessible
            STATUS      current
            DESCRIPTION
                "The direction of the sub-carrier either
                 upstream or downstream.
                "
            ::= { vdsl2PrivSCStatusEntry 1 }    
              
        vdsl2PrivSCStatusMtime  OBJECT-TYPE
            SYNTAX      Unsigned32
            UNITS       "symbols"
            MAX-ACCESS  read-only
            STATUS      current
            DESCRIPTION
                "SNR Measurement Time.  The number of symbols used to
                 measure the SNR values on the respective transmission
                 direction.  It should correspond to the value specified in the
                 recommendation (e.g., the number of symbols in 1 second
                 time interval for G.992.3).  This parameter corresponds to
                 1 second in loop diagnostic procedure and should be updated
                 otherwise.
                 Unit: symbols
                "
            REFERENCE  "ITU-T G.997.1, paragraph 7.5.1.20.1 (SNRMTds)
                        and paragraph 7.5.1.20.3 (SNRMTus)"
            ::= { vdsl2PrivSCStatusEntry 2 }
        
        vdsl2PrivSCStatusSnr  OBJECT-TYPE
            SYNTAX      OCTET STRING  (SIZE(0..4096))
            MAX-ACCESS  read-only
            STATUS      current
            DESCRIPTION
                "The SNR Margin per sub-carrier, expressing the ratio between
                 the received signal power and received noise power per
                 subscriber.  It is an array of 4096 bytes, designed for
                 supporting up to 4096 sub-carriers.
                 The number of utilized octets on downstream direction depends
                 on NSCds, and on upstream direction it depends on NSCus.  This
                 value is referred here as NSC.
                 Byte i (0 &lt;= i &lt; NSC) is set to a value in the range 0 to
                 254 to indicate that the respective downstream or upstream sub-
                 carrier i has SNR of: (-32 + Vdsl2SubcarrierSnr(i)/2) in dB
                 (i.e., -32 to 95dB).
                 The special value 255 means that no measurement could be done
                 for the subcarrier because it is out of the PSD mask passband
                 or that the noise PSD is out of range to be represented.
                 Each value in this array is 8 bits wide.
                "
            REFERENCE    "ITU-T G.997.1, paragraph 7.5.1.20.2 (SNRpsds)
                          and paragraph 7.5.1.20.4 (SNRpsus)"
            ::= { vdsl2PrivSCStatusEntry 3 }
        
        vdsl2PrivSCStatusBitsAlloc  OBJECT-TYPE
            SYNTAX      OCTET STRING  (SIZE(0..2048))
            UNITS       "bits"
            MAX-ACCESS  read-only
            STATUS      current
            DESCRIPTION
                "The bits allocation per sub-carrier.  An array of 2048 bytes, 
                 designed for supporting up to 4096 sub-carriers.
                 The number of utilized nibbles on downstream direction depends
                 on NSCds, and on upstream direction it depends on NSCus.  This
                 value is referred here as NSC.
                 Nibble i (0 &lt;= i &lt; NSC) is set to a value in the range 0
                 to 15 to indicate that the respective downstream or upstream
                 sub-carrier i has the same amount of bits allocation.
                 Unit: bits
                "
            REFERENCE    "ITU-T G.997.1, paragraph 7.5.1.21.1 (BITSpsds)
                         and paragraph 7.5.1.21.2 (BITSpsus)"
             ::= { vdsl2PrivSCStatusEntry 4 }
        
        vdsl2PrivSCStatusGainAlloc  OBJECT-TYPE
            SYNTAX      OCTET STRING  (SIZE(0..8192))
            MAX-ACCESS  read-only
            STATUS      current
            DESCRIPTION
                "The gain allocation per sub-carrier.  An array of 8192 bytes, 
                 designed for supporting up to 4096 sub-carriers.
                 The number of utilized octets on downstream direction depends
                 on NSCds, and on upstream direction it depends on NSCus.  This
                 value is referred here as NSC.
                 Value i (0 &lt;= i &lt; NSC) is in the range 0 to 4093 to indicate
                 that the respective downstream or upstream sub-carrier i has the
                 same amount of gain value.
                 The gain value is represented as a multiple of 1/512 on
                 linear scale.  Each value in this array is 16 bits wide and is
                 stored in big endian format.
                "
            REFERENCE    "ITU-T G.997.1, paragraph 7.5.1.21.3 (GAINSpsds)
                          and paragraph 7.5.1.21.4 (GAINSpsus)"
            ::= { vdsl2PrivSCStatusEntry 5 }
        
--               Scalars that relate to the vdsl2Scalar.
        vdsl2ScalarSCMaxInterfaces  OBJECT-TYPE
            SYNTAX      Unsigned32
            MAX-ACCESS  read-only
            STATUS      current
            DESCRIPTION
                "This value determines the maximum number of
                 interfaces supported by vdsl2SCStatusTable,
                 vdsl2SCStatusBandTable, and vdsl2SCStatusSegmentTable.
                "
            ::= { vdsl2ScalarSC 1 }
            
        vdsl2ScalarSCAvailInterfaces  OBJECT-TYPE
            SYNTAX      Unsigned32
            MAX-ACCESS  read-only
            STATUS      current
            DESCRIPTION
                "This value determines the currently available number of
                 interfaces listed in vdsl2SCStatusTable,
                 vdsl2SCStatusBandTable, and vdsl2SCStatusSegmentTable.
                "
            ::= { vdsl2ScalarSC 2 }
        
        --       vdsl2SCStatusTable               
        
        vdsl2SCStatusTable  OBJECT-TYPE
            SYNTAX      SEQUENCE  OF  Vdsl2SCStatusEntry
            MAX-ACCESS  not-accessible
            STATUS      current
            DESCRIPTION
                "The table vdsl2SCStatusTable contains
                 sub-carrier status parameters for VDSL2/ADSL/ADSL2
                 and ADSL2+ that DO NOT refer to specific sub-carriers.
                 In addition, the table contains parameters
                 that provide information about the size of parameters
                 in vdsl2SCStatusSegmentTable.  This table contains live data
                 from equipment. The indexes of this table are ifIndex and 
                 vdsl2SCStatusDirection. 
                "
            ::= { vdsl2Status 3 }
        
        vdsl2SCStatusEntry  OBJECT-TYPE
            SYNTAX      Vdsl2SCStatusEntry
            MAX-ACCESS  not-accessible
            STATUS      current
            DESCRIPTION
                "The table vdsl2SCStatusTable contains
                 sub-carrier status parameters for VDSL2/ADSL/ADSL2
                 and ADSL2+ that DO NOT refer to specific sub-carriers.
                 In addition, the table contains parameters
                 that provide information about the size of parameters
                 in vdsl2SCStatusSegmentTable.  This table contains live data
                 from equipment. The indexes of this entry are ifIndex and 
                 vdsl2SCStatusDirection.
                "
            INDEX  { ifIndex, vdsl2SCStatusDirection }
            ::= { vdsl2SCStatusTable 1 }
        
        Vdsl2SCStatusEntry  ::=
           SEQUENCE {
              vdsl2SCStatusDirection         Vdsl2Direction,
              vdsl2SCStatusLinScale          Unsigned32,
              vdsl2SCStatusLinScGroupSize    Unsigned32,
              vdsl2SCStatusLogMt             Unsigned32,
              vdsl2SCStatusLogScGroupSize    Unsigned32,
              vdsl2SCStatusQlnMt             Unsigned32,
              vdsl2SCStatusQlnScGroupSize    Unsigned32,
              vdsl2SCStatusMtime             Unsigned32,
              vdsl2SCStatusSnrScGroupSize    Unsigned32,
              vdsl2SCStatusAttainableRate    Unsigned32,
              vdsl2SCStatusActAtp            Integer32,    
              vdsl2SCStatusRowStatus         RowStatus,
              vdsl2SCStatusProfile		     Vdsl2Profiles,
              vdsl2SCStatusClassmask		 Vdsl2PSDClassMask
           }
        
        vdsl2SCStatusDirection  OBJECT-TYPE
            SYNTAX      Vdsl2Direction
            MAX-ACCESS  not-accessible
            STATUS      current
            DESCRIPTION
                "The direction of the sub-carrier either
                 upstream or downstream"
            ::= { vdsl2SCStatusEntry 1 }
            
        vdsl2SCStatusLinScale  OBJECT-TYPE
            SYNTAX      Unsigned32
            MAX-ACCESS  read-only
            STATUS      current
            DESCRIPTION
                "The scale factor to be applied to the H(f) linear
                 representation values for the respective transmission direction.
                 This parameter is only available after a loop diagnostic
                 procedure.
                "
            REFERENCE  "ITU-T G.997.1, paragraph #7.5.1.26.1 (HLINSCds)
                        and paragraph #7.5.1.26.7 (HLINSCus)"
            ::= { vdsl2SCStatusEntry 2 }
        
        vdsl2SCStatusLinScGroupSize OBJECT-TYPE
            SYNTAX      Unsigned32(1 | 2 | 4 | 8)
            MAX-ACCESS  read-only
            STATUS      current
            DESCRIPTION
                "Number of sub-carriers per group used to report the H(f)
                 linear representation values for the respective transmission
                 direction. The valid values are 1, 2, 4 and 8. For ADSL, this
                 parameter is equal to one and, for VDSL2, it is equal to the
                 size of a sub-carrier group used to compute these parameters.
                 This parameter is only available after a loop diagnostic
                 procedure.
                "
            REFERENCE  "ITU-T G.997.1, paragraph #7.5.1.26.2 (HLINGds)
                        and paragraph #7.5.1.26.8 (HLINGus)"
            ::= { vdsl2SCStatusEntry 3 }
        vdsl2SCStatusLogMt  OBJECT-TYPE
            SYNTAX      Unsigned32
            MAX-ACCESS  read-only
            STATUS      current
            DESCRIPTION
                "The number of symbols used to measure the H(f) logarithmic
                 measurement values for the respective transmission direction.
                 This parameter should correspond to the value specified in the
                 recommendation (e.g., the number of symbols in 1 second
                 time interval for G.992.3).  This parameter corresponds to 1
                 second in loop diagnostic procedure and should be updated in
                 initialization.
                "
            REFERENCE  "ITU-T G.997.1, paragraph #7.5.1.26.4 (HLOGMTds)
                        and paragraph #7.5.1.26.10 (HLOGMTus)"
            ::= { vdsl2SCStatusEntry 4 }
            
        vdsl2SCStatusLogScGroupSize OBJECT-TYPE
            SYNTAX      Unsigned32(1 | 2 | 4 | 8)
            MAX-ACCESS  read-only
            STATUS      current
            DESCRIPTION
                "Number of sub-carriers per group used to report the H(f)
                 logarithmic representation values for the respective
                 transmission direction. The valid values are 1, 2, 4 and 8.
                 For ADSL, this parameter is equal to one and, for VDSL2, it is
                 equal to the size of a sub-carrier group used to compute these
                 parameters.
                 This parameter is only available after a loop diagnostic
                 procedure.
                "
            REFERENCE  "ITU-T G.997.1, paragraph #7.5.1.26.5 (HLOGGds)
                        and paragraph #7.5.1.26.11 (HLOGGus)"
            ::= { vdsl2SCStatusEntry 5 }
        
        vdsl2SCStatusQlnMt  OBJECT-TYPE
            SYNTAX      Unsigned32
            MAX-ACCESS  read-only
            STATUS      current
            DESCRIPTION
                "The number of symbols used to measure the Quiet Line Noise
                 values on the respective transmission direction.   This
                 parameter should correspond to the value specified in the
                 recommendation (e.g., the number of symbols in 1 second time
                 interval for G.992.3).  This parameter corresponds to 1 second
                 in loop diagnostic procedure and should be updated in
                 initialization. 
                "
            REFERENCE  "ITU-T G.997.1, paragraph #7.5.1.27.1 (QLNMTds)
                        and paragraph #7.5.1.27.4 (QLNMTus)"
            ::= { vdsl2SCStatusEntry 6 }
        vdsl2SCStatusQlnScGroupSize OBJECT-TYPE
            SYNTAX      Unsigned32(1 | 2 | 4 | 8)
            MAX-ACCESS  read-only
            STATUS      current
            DESCRIPTION
                "Number of sub-carriers per group used to report the Quiet
                 Line Noise values for the respective transmission direction.
                 The valid values are 1, 2, 4 and 8.
                 For ADSL, this parameter is equal to one and, for VDSL2, it is
                 equal to the size of a sub-carrier group used to compute these
                 parameters.
                 This parameter is only available after a loop diagnostic
                 procedure.
                "
            REFERENCE  "ITU-T G.997.1, paragraph #7.5.1.27.2 (QLNGds)
                        and paragraph #7.5.1.27.5 (QLNGus)"
            ::= { vdsl2SCStatusEntry 7 }
            
        vdsl2SCStatusMtime  OBJECT-TYPE
            SYNTAX      Unsigned32
            UNITS       "symbols"
            MAX-ACCESS  read-only
            STATUS      current
            DESCRIPTION
                "SNR Measurement Time.  The number of symbols used to
                 measure the SNR values on the respective transmission
                 direction.  It should correspond to the value specified in the
                 recommendation (e.g., the number of symbols in 1 second
                 time interval for G.992.3).  This parameter corresponds to
                 1 second in loop diagnostic procedure and should be updated
                 otherwise.
                 Unit: symbols
                "
            REFERENCE    "ITU-T G.997.1, paragraph #7.5.1.28.1 (SNRMTds)
                          and paragraph #7.5.1.28.4 (SNRMTus)"
            ::= { vdsl2SCStatusEntry 8 }
        
        vdsl2SCStatusSnrScGroupSize OBJECT-TYPE
            SYNTAX      Unsigned32(1 | 2 | 4 | 8)
            MAX-ACCESS  read-only
            STATUS      current
            DESCRIPTION
                "Number of sub-carriers per group used to report the SNR
                 values on the respective transmission direction.
                 The valid values are 1, 2, 4 and 8.
                 For ADSL, this parameter is equal to one and, for VDSL2, it is
                 equal to the size of a sub-carrier group used to compute these
                 parameters.
                 This parameter is only available after a loop diagnostic
                 procedure.
                "
            REFERENCE  "ITU-T G.997.1, paragraph #7.5.1.28.2 (QLNGds)
                        and paragraph #7.5.1.28.5 (QLNGus)"
            ::= { vdsl2SCStatusEntry 9 }
        
        vdsl2SCStatusAttainableRate  OBJECT-TYPE
            SYNTAX      Unsigned32
            UNITS       "bits/second"
            MAX-ACCESS  read-only
            STATUS      current
            DESCRIPTION
                "Maximum Attainable Data Rate.  The maximum net data rate
                 currently attainable by the XTU-C transmitter and XTU-R
                 receiver (when referring to downstream direction) or by the
                 XTU-R transmitter and XTU-C receiver (when referring to
                 upstream direction).  Value is coded in bits/s.
                 This object reflects the value of the parameter following the
                 most recent DELT performed on the associated line.  Once
                 the DELT process is over, the parameter no longer changes
                 until the row is deleted or a new DELT process is initiated.
                 Unit: bits/second
                "
            REFERENCE  "ITU-T G.997.1, paragraph #7.5.1.12 (ATTNDRds)
                        and paragraph #7.5.1.13 (ATTNDRus)"
            ::= { vdsl2SCStatusEntry 10 }
           
        vdsl2SCStatusActAtp  OBJECT-TYPE
            SYNTAX      Integer32
            UNITS       "0.1 dB"
            MAX-ACCESS  read-only
            STATUS      current
            DESCRIPTION
                "Actual Aggregate Transmit Power from the XTU (XTU-R on
                 downstream direction and XTU-C on upstream direction), at the
                 instant of measurement.  It ranges from -310 to 310 units of
                 0.1 dB (Physical values are -31 to 31 dBm).  A value of all
                 1's indicates the measurement is out of range to be
                 represented.
                 This object reflects the value of the parameter following the
                 most recent DELT performed on the associated line.  Once
                 the DELT process is over, the parameter no longer changes
                 until the row is deleted or a new DELT process is initiated.
                 Unit: 0.1 dB
                "
            REFERENCE  "ITU-T G.997.1, paragraph #7.5.1.16 (ACTATPds)
                        and paragraph #7.5.1.17 (ACTATPus)"
            ::= { vdsl2SCStatusEntry 11 }
          
        vdsl2SCStatusRowStatus  OBJECT-TYPE
            SYNTAX      RowStatus
            MAX-ACCESS  read-write
            STATUS      current
            DESCRIPTION
                "Row Status.  The SNMP agent should create rows in this
                 table and in the vdsl2SCStatusTable for storing the results
                 of a DELT performed on the associated line, if such rows
                 do not already exist.
                 The SNMP agent may have limited resources; therefore, if
                 multiple rows co-exist in the table, it may fail to add
                 new rows to the two tables or allocate memory resources for
                 a new DELT process.  If that occurs, the SNMP agent responds with
                 either the value 'tableFull' or the value
                 'noResources' (for xdsl2LineCmndConfLdsfFailReason
                 object in xdsl2LineTable)
                 The management system (the operator) may delete rows according
                 to any scheme.  E.g., after retrieving the results.
                "
            ::= { vdsl2SCStatusEntry 12 }
        
        vdsl2SCStatusProfile  OBJECT-TYPE
            SYNTAX      Vdsl2Profiles
            MAX-ACCESS  read-only
            STATUS      current
            DESCRIPTION
                "This configuration parameter contains the G.993.2 
                 profiles to be allowed by the near-end xTU on this line.
                "
            REFERENCE    "ITU-T G.997.1(200604), paragraph 7.3.1.1.11"
             ::= { vdsl2SCStatusEntry 13 }
           
        vdsl2SCStatusClassmask  OBJECT-TYPE
            SYNTAX      Vdsl2PSDClassMask
            MAX-ACCESS  read-only
            STATUS      current
            DESCRIPTION
                "In order to reduce the number of configuration possibilities, 
                 the limit PSD masks are grouped in the following PSD mask classes:
                 -  Class 998 Annex A: D-32, D-64.
                 -  Class 997-M1c Annex B: 997-M1c-A-7.
                 -  Class 997-M1x Annex B: 997-M1x-M-8, 997-M1x-M.
                 -  Class 997-M2x Annex B: 997-M2x-M-8, 997-M2x-A, 997-M2x-M.
                 -  Class 998-M1x Annex B: 998-M1x-A, 998-M1x-B, 998-M1x-NUS0.
                 -  Class 998-M2x Annex B: 998-M2x-A, 998-M2x-M, 998-M2x-B, 998-M2x-NUS0.
                 -  Class HPE17 Annex B: HPE17-M1-NUS0.
                 -  Class HPE30 Annex B: HPE30-M1-NUS0.
                 -  Class 997E17-M2x Annex B: 997E17-M2x-NUS0.
                 -  Class 997E30-M2x Annex B: 997E30-M2x-NUS0.
                 -  Class 998E17-M2x Annex B: 998E17-M2x-NUS0, 998E17-M2x-NUS0-M, 998E17-M2x-A.
                 -  Class 998ADE17-M2x Annex B: 998ADE17-M2x-NUS0-M, 998ADE17-M2x-A, 998ADE17-M2x-B.
                 -  Class 998E30-M2x Annex B: 998E30-M2x-NUS0, 998E30-M2x-NUS0-M.
                 -  Class 998ADE30-M2x Annex B: 998ADE30-M2x-NUS0-M, 998ADE30-M2x-NUS0-A.
                "
            REFERENCE    "ITU-T G.997.1(200604), paragraph 7.3.1.1.12"
            ::= { vdsl2SCStatusEntry 14 }
              
        --       vdsl2SCStatusBandTable               
        
        vdsl2SCStatusBandTable  OBJECT-TYPE
            SYNTAX      SEQUENCE  OF  Vdsl2SCStatusBandEntry
            MAX-ACCESS  not-accessible
            STATUS      current
            DESCRIPTION
                "The table vdsl2SCStatusBandTable contains
                 sub-carrier status parameters for VDSL2/ADSL/ADSL2
                 and ADSL2+ that are grouped per-band.
                 For ADSL/ADSL2/ADSL2+, there is a single
                 upstream band and a single downstream band.
                 For VDSL2, there are several downstream bands and
                 several upstream bands. 
                 The indexes of this table are ifIndex and vdsl2SCStatusBand.
                "
            ::= { vdsl2Status 4 }
            
        vdsl2SCStatusBandEntry  OBJECT-TYPE
            SYNTAX      Vdsl2SCStatusBandEntry
            MAX-ACCESS  not-accessible
            STATUS      current
            DESCRIPTION
                "The table vdsl2SCStatusBandTable contains
                 sub-carrier status parameters for VDSL2/ADSL/ADSL2
                 and ADSL2+ that are grouped per-band.
                 For ADSL/ADSL2/ADSL2+, there is a single
                 upstream band and a single downstream band.
                 For VDSL2, there are several downstream bands and
                 several upstream bands. 
                 The indexes of this entry are ifIndex and vdsl2SCStatusBand.
                "
            INDEX  { ifIndex, vdsl2SCStatusBand }
            ::= { vdsl2SCStatusBandTable 1 }
        
        Vdsl2SCStatusBandEntry  ::=
            SEQUENCE {
              vdsl2SCStatusBand                  Xdsl2Band,
              vdsl2SCStatusBandLnAtten           Unsigned32,
              vdsl2SCStatusBandSigAtten          Unsigned32,
              vdsl2SCStatusBandSnrMargin         Integer32, 
              vdsl2SCStatusBandUpbokle           Unsigned32
            }
        
        vdsl2SCStatusBand OBJECT-TYPE
            SYNTAX      Xdsl2Band
            MAX-ACCESS  not-accessible
            STATUS      current
            DESCRIPTION
                "The transmission band.
                 Identifies a band in a VDSL2/ADSL/ADSL2/ADSL2+ link. 
                 For a band in the upstream direction, transmission is from 
                 the remote end (xTU-R) towards the central office end (xTU-C).
                 A band in the upstream direction is indicated by upstream(1)
                 for ADSL/ADSL2/ADSL2+ single band, or any of us0(3), us1(5), 
                 us2(7), us3(9), or us4(11) for VDSL2 multiple bands.
                 For a band in the downstream direction, transmission is from 
                 the xTU-C towards the xTU-R. A band in the downstream 
                 direction is indicated by downstream(2) for ADSL/ADSL2/ADSL2+ 
                 single band, or any of ds1(4), ds2(6), ds3(8), or ds4(10) for
                 VDSL2 multiple bands.
                "
            ::= { vdsl2SCStatusBandEntry 1 }
        
        vdsl2SCStatusBandLnAtten  OBJECT-TYPE
            SYNTAX      Unsigned32 (0..1270 | 2147483646 | 2147483647)
            UNITS       "0.1 dB"
            MAX-ACCESS  read-only
            STATUS      current
            DESCRIPTION
                "When referring to a band in the downstream direction, it is
                 the measured difference in the total power transmitted by the 
                 xTU-C and the total power received by the xTU-R over all 
                 sub-carriers during diagnostics mode.
                 When referring to a band in the upstream direction, it is the
                 measured difference in the total power transmitted by the xTU-R
                 and the total power received by the xTU-C over all sub-carriers
                 during diagnostics mode.
                 It ranges from 0 to 1270 units of 0.1 dB (Physical values are
                 0 to 127 dB).
                 A special value of 0x7FFFFFFF (2147483647) indicates the line
                 attenuation is out of range to be represented.
                 A special value of 0x7FFFFFFE (2147483646) indicates the line
                 attenuation measurement is unavailable.
                 This object reflects the value of the parameter following the
                 most recent DELT performed on the associated line.  Once
                 the DELT process is over, the parameter no longer changes
                 until the row is deleted or a new DELT process is initiated.
                 Unit: 0.1 dB
                "
            REFERENCE  "ITU-T G.997.1, paragraph #7.5.1.6 (LATNds)
                        and paragraph #7.5.1.7 (LATNus)"
            ::= { vdsl2SCStatusBandEntry 2 }
        
        vdsl2SCStatusBandSigAtten  OBJECT-TYPE
            SYNTAX      Unsigned32 (0..1270 | 2147483646 | 2147483647)
            UNITS       "0.1 dB"
            MAX-ACCESS  read-only
            STATUS      current
            DESCRIPTION
                "When referring to a band the downstream direction, it is the
                 measured difference in the total power transmitted by the
                 xTU-C and the total power received by the xTU-R over all sub
                 carriers during Showtime after the diagnostics mode.
                 When referring to the upstream direction, it is the measured
                 difference in the total power transmitted by the
                 xTU-R and the total power received by the xTU-C over all sub
                 carriers during Showtime after the diagnostics mode.
                 It ranges from 0 to 1270 units of 0.1 dB (Physical values
                 are 0 to 127 dB).
                 A special value of 0x7FFFFFFF (2147483647) indicates the line
                 attenuation is out of range to be represented.
                 A special value of 0x7FFFFFFE (2147483646) indicates the line
                 attenuation measurement is unavailable.
                 This object reflects the value of the parameter following the
                 most recent DELT performed on the associated line.  Once
                 the DELT process is over, the parameter no longer changes
                 until the row is deleted or a new DELT process is initiated.
                 Unit: 0.1 dB
                "
            REFERENCE  "ITU-T G.997.1, paragraph #7.5.1.8 (SATNds)
                        and paragraph #7.5.1.9 (SATNus)"
            ::= { vdsl2SCStatusBandEntry 3 }
        
        vdsl2SCStatusBandSnrMargin  OBJECT-TYPE
            SYNTAX      Integer32 (-640..630 | 2147483646 | 2147483647)
            UNITS       "0.1 dB"
            MAX-ACCESS  read-only
            STATUS      current
            DESCRIPTION
                "SNR Margin is the maximum increase in dB of the noise power
                 received at the XTU (xTU-R on downstream direction and xTU-C
                 on upstream direction), such that the BER requirements are met
                 for all bearer channels received at the XTU.  It ranges from
                 -640 to 630 units of 0.1 dB (Physical values are -64 to
                 63 dB).
                 A special value of 0x7FFFFFFF (2147483647) indicates the
                 SNR Margin is out of range to be represented.
                 A special value of 0x7FFFFFFE (2147483646) indicates the
                 SNR Margin measurement is currently unavailable.
                 This object reflects the value of the parameter following the
                 most recent DELT performed on the associated line.  Once
                 the DELT process is over, the parameter no longer changes
                 until the row is deleted or a new DELT process is initiated.
                 Unit: 0.1 dB
                "
            REFERENCE  "ITU-T G.997.1, paragraph #7.5.1.10 (SNRMds)
                        and paragraph #7.5.1.11 (SNRMus)"
            ::= { vdsl2SCStatusBandEntry 4 }
        
        vdsl2SCStatusBandUpbokle  OBJECT-TYPE
            SYNTAX      Unsigned32 (0..1280 | 2047 | 2147483647)
            UNITS       "0.1 dB"
            MAX-ACCESS  read-only
            STATUS      current
            DESCRIPTION
                "This parameter is a vector of UPBO electrical length per-band 
                 estimates for each supported upstream/downstream band, 
                 expressed in dB at 1 MHz (kl0) calculated by the VTU-O/VTU-R, 
                 based on separate measurements in the supported upstream bands excluding US0/downstream bands. 
                 The value ranges from 0 to 128 dB in steps of 0.1 dB, with special value 204.7 
                 which indicates that the estimate is greater than 128 dB.
                 This parameter is required for the Alternative Electrical Length Estimation method (ELE-M1).
                 Unit: 0.1 dB
                "
            REFERENCE  "ITU-T G.997.1, paragraph #7.5.1.23"
            ::= { vdsl2SCStatusBandEntry 5 }
                
        --       vdsl2SCStatusSegmentTable               
        
        vdsl2SCStatusSegmentTable  OBJECT-TYPE
            SYNTAX      SEQUENCE  OF  Vdsl2SCStatusSegmentEntry
            MAX-ACCESS  not-accessible
            STATUS      current
            DESCRIPTION
                "The table vdsl2SCStatusSegmentTable contains status parameters
                 of VDSL2/ADSL/ADSL2 and ADSL2+ sub-carriers. 
                 Several objects in the table refer to NSus and NSds. For
                 G.993.2, the value of NSus and NSds are respectively the indices
                 of the highest supported upstream and downstream subcarriers
                 according to the selected implementation profile. For ADSL,
                 NSus is equal to NSCus-1 and NSds is equal to NSCds-1.
                 The indexes of this table are ifIndex, vdsl2SCStatusDirection, 
                 and vdsl2SCStatusSegment.  
                 One index of this entry is an interface index where the
                 interface has an ifType of vdsl2(251). The second index of this
                 entry is the transmission direction. The third index identifies
                 the specific segment of the sub-carriers status addressed.
                "
            ::= { vdsl2Status 5 }
        
        vdsl2SCStatusSegmentEntry  OBJECT-TYPE
            SYNTAX      Vdsl2SCStatusSegmentEntry
            MAX-ACCESS  not-accessible
            STATUS      current
            DESCRIPTION
                "The table vdsl2SCStatusSegmentTable contains status parameters
                 of VDSL2/ADSL/ADSL2 and ADSL2+ sub-carriers.               
                 Several objects in the table refer to NSus and NSds. For
                 G.993.2, the value of NSus and NSds are respectively the indices
                 of the highest supported upstream and downstream subcarriers
                 according to the selected implementation profile. For ADSL,
                 NSus is equal to NSCus-1 and NSds is equal to NSCds-1.
                 The indexes of this entry are ifIndex, vdsl2SCStatusDirection, 
                 and vdsl2SCStatusSegment.
                 One index of this entry is an interface index where the
                 interface has an ifType of vdsl2(251). The second index of this
                 entry is the transmission direction. The third index identifies
                 the specific segment of the sub-carriers status addressed.
                "
            INDEX  { ifIndex,
                     vdsl2SCStatusDirection,
                     vdsl2SCStatusSegment   }
            ::= { vdsl2SCStatusSegmentTable 1 }
        
        Vdsl2SCStatusSegmentEntry  ::=
            SEQUENCE {
              vdsl2SCStatusSegment                  Unsigned32,
              vdsl2SCStatusSegmentLinReal           OCTET STRING,
              vdsl2SCStatusSegmentLinImg            OCTET STRING,
              vdsl2SCStatusSegmentLog               OCTET STRING,
              vdsl2SCStatusSegmentQln               OCTET STRING,
              vdsl2SCStatusSegmentSnr               OCTET STRING,
              vdsl2SCStatusSegmentBitsAlloc         OCTET STRING,
              vdsl2SCStatusSegmentGainAlloc         OCTET STRING,
              vdsl2SCStatusSegmentTssi              Vdsl2Tssi,
              vdsl2SCStatusSegmentTxPSD             OCTET STRING,
              vdsl2SCStatusSegmentSnrMargin         OCTET STRING,	 
              vdsl2SCStatusSegmentLogScGroupSize    Unsigned32,
              vdsl2SCStatusSegmentQlnScGroupSize    Unsigned32,
              vdsl2SCStatusSegmentLinScGroupSize    Unsigned32,
              vdsl2SCStatusSegmentSnrScGroupSize    Unsigned32,
              hwvdsl2SCStatusSegmentQlnWithVectoring OCTET STRING
            }
        
        vdsl2SCStatusSegment  OBJECT-TYPE
            SYNTAX      Unsigned32(1..8)
            MAX-ACCESS  not-accessible
            STATUS      current
            DESCRIPTION
                "The segment of the sub-carriers
                 status information provided by this
                 row.
                 Several status parameters in this table
                 are retrieved in segments. The first segment
                 of the status information is retrieved with
                 vdsl2SCStatusSegment=1, the second segment
                 is retrieved with vdsl2SCStatusSegment=2, and
                 so on. When any status parameter is retrieved
                 in n segments where n<8) then, for that
                 parameter, GET operations for the rest segment
                 numbers (n+1 to 8) are responded with a value
                 that indicates: No measurement could be done.
                "
           ::= { vdsl2SCStatusSegmentEntry 1 }
        
        vdsl2SCStatusSegmentLinReal  OBJECT-TYPE
            SYNTAX      OCTET STRING  (SIZE(0..1024))
            MAX-ACCESS  read-only
            STATUS      current
            DESCRIPTION
                "An array of up to 512 complex H(f) linear representation
                 values in linear scale for the respective transmission
                 direction.  It is designed to support up to 512 (downstream)
                 sub-carriers groups and can be retrieved in a single segment.
                 The number of utilized values on downstream direction depends
                 on NSds, and on upstream direction it depends on NSus.  This
                 value is referred here as NS.
                 Each array entry represents the real component [referred here as
                 a(i)] of Hlin(f = i*Df) value for a particular sub-carrier group
                 index i (0 <= i < NS).
                 Hlin(f) is represented as ((scale/2^15)*((a(i)+j*b(i))/2^15)),
                 where scale is vdsl2SCStatusLinScale and a(i) and b(i)
                 [provided by the vdsl2SCStatusSegmentLinImg object] are in the
                 range (-2^15+1) to (+2^15-1).
                 A special value a(i)=b(i)= -2^15 indicates that no measurement
                 could be done for the sub-carriers group because it is out of
                 the passband or that the attenuation is out of range to be
                 represented.  This parameter is only available after a loop
                 diagnostic procedure.
                 Each value in this array is 16 bits wide and is stored in big
                 endian format.
                "
            REFERENCE  "ITU-T G.997.1, paragraph #7.5.1.26.3 (HLINpsds)
                        and paragraph #7.5.1.26.9 (HLINpsus)"
            ::= { vdsl2SCStatusSegmentEntry 2 }
        
        vdsl2SCStatusSegmentLinImg  OBJECT-TYPE
            SYNTAX      OCTET STRING  (SIZE(0..1024))
            MAX-ACCESS  read-only
            STATUS      current
            DESCRIPTION
                "An array of up to 512 complex H(f) linear representation
                 values in linear scale for the respective transmission
                 direction.  It is designed to support up to 512 (downstream)
                 sub-carriers groups and can be retrieved in a single segment.
                 The number of utilized values on downstream direction depends
                 on NSds, and on upstream direction it depends on NSus.  This
                 value is referred here as NS.
                 Each array entry represents the imaginary component [referred
                 here as b(i)] of Hlin(f = i*Df) value for a particular sub-
                 carrier group index i (0 <= i < NS).
                 Hlin(f) is represented as ((scale/2^15)*((a(i)+j*b(i))/2^15)),
                 where scale is vdsl2SCStatusLinScale and a(i) [provided by
                 the vdsl2SCStatusSegmentLinReal object] and b(i) are in the range
                 (-2^15+1) to (+2^15-1).
                 A special value a(i)=b(i)= -2^15 indicates that no measurement
                 could be done for the sub-carriers group because it is out of
                 the passband or that the attenuation is out of range to be
                 represented.  This parameter is only available after a loop
                 diagnostic procedure.
                 Each value in this array is 16 bits wide and is stored in big
                 endian format.
                "
            REFERENCE  "ITU-T G.997.1, paragraph #7.5.1.26.3 (HLINpsds)
                        and paragraph #7.5.1.26.9 (HLINpsus)"
            ::= { vdsl2SCStatusSegmentEntry 3 }
        
        vdsl2SCStatusSegmentLog  OBJECT-TYPE
            SYNTAX      OCTET STRING  (SIZE(0..1024))
            UNITS       "dB"
            MAX-ACCESS  read-only
            STATUS      current
            DESCRIPTION
                "An array of up to 512 real H(f) logarithmic representation
                 values in dB for the respective transmission direction.  It is
                 designed to support up to 512 (downstream) sub-carriers groups
                 and can be retrieved in a single segment.
                 The number of utilized values on downstream direction depends
                 on NSds, and on upstream direction it depends on NSus.  This
                 value is referred here as NS.
                 Each array entry represents the real Hlog(f = i*Df) value for a
                 particular sub-carrier group index i, (0 <= i < NS).
                 The real Hlog(f) value is represented as (6-m(i)/10), with m(i)
                 in the range 0 to 1022.  A special value m=1023 indicates that
                 no measurement could be done for the sub-carrier group because
                 it is out of the passband or that the attenuation is out of
                 range to be represented.  This parameter is applicable in loop
                 diagnostic procedure and initialization.
                 Each value in this array is 16 bits wide and is stored
                 in big endian format.
                 Unit: dB
                "
            REFERENCE  "ITU-T G.997.1, paragraph #7.5.1.26.6 (HLOGpsds)
                        and paragraph #7.5.1.26.12 (HLOGpsus)"
            ::= { vdsl2SCStatusSegmentEntry 4 }
        
        vdsl2SCStatusSegmentQln  OBJECT-TYPE
            SYNTAX      OCTET STRING  (SIZE(0..512))
            UNITS       "dBm/Hz"
            MAX-ACCESS  read-only
            STATUS      current
            DESCRIPTION
                "An array of up to 512 real Quiet Line Noise values in dBm/Hz
                 for the respective transmission direction.  It is designed for
                 up to 512 (downstream) sub-carriers groups and can be retrieved
                 in a single segment.
                 The number of utilized values on downstream direction depends
                 on NSds, and on upstream direction it depends on NSus.  This
                 value is referred here as NS.
                 Each array entry represents the QLN(f = i*Df) value for a
                 particular sub-carrier index i, (0 <= i < NS).
                 The QLN(f) is represented as ( -23-n(i)/2), with n(i) in the
                 range 0 to 254.  A special value n(i)=255 indicates that no
                 measurement could be done for the sub-carrier group because it
                 is out of the passband or that the noise PSD is out of range
                 to be represented.
                 This parameter is applicable in loop diagnostic procedure and
                 initialization.  Each value in this array is 8 bits wide.
                 Unit: dBm/Hz
                "
            REFERENCE  "ITU-T G.997.1, paragraph #7.5.1.27.3 (QLNpsds)
                        and paragraph #7.5.1.27.6 (QLNpsus)"
            ::= { vdsl2SCStatusSegmentEntry 5 }
             
        vdsl2SCStatusSegmentSnr  OBJECT-TYPE
            SYNTAX      OCTET STRING  (SIZE(0..512))
            UNITS       "0.5 dB"
            MAX-ACCESS  read-only
            STATUS      current
            DESCRIPTION
                "The SNR Margin per sub-carrier group, expressing the
                 ratio between the received signal power and received noise
                 power per sub-scriber group.  It is an array of 512 octets,
                 designed for supporting up to 512 (downstream) sub-carriers
                 groups and can be retrieved in a single segment.
                 The number of utilized octets on downstream direction depends
                 on NSds, and on upstream direction it depends on NSus.  This
                 value is referred here as NS.
                 Octet i (0 <= i < NS) is set to a value in the range 0 to
                 254 to indicate that the respective downstream or upstream sub-
                 carrier group i has SNR of: (-32 + xdsl2SCStatusSegmentSnr(i)/2)
                 in dB (i.e., -32 to 95dB).
                 The special value 255 means that no measurement could be done
                 for the sub-carrier group because it is out of the PSD mask
                 passband or that the noise PSD is out of range to be
                 represented.  Each value in this array is 8 bits wide.
                 Unit: 0.5 dB
                "
            REFERENCE    "ITU-T G.997.1, paragraph #7.5.1.28.3 (SNRpsds)
                          and paragraph #7.5.1.28.6 (SNRpsus)"
            ::= { vdsl2SCStatusSegmentEntry 6 }
        
        vdsl2SCStatusSegmentBitsAlloc  OBJECT-TYPE
            SYNTAX      OCTET STRING  (SIZE(0..256))
            UNITS       "bits"
            MAX-ACCESS  read-only
            STATUS      current
            DESCRIPTION
                "The bits allocation per sub-carrier.  An array of 256 octets
                 (512 nibbles), designed for supporting up to 512 (downstream)
                 sub-carriers. When more then 512 sub-carriers are supported,
                 the status information is reported through multiple (up to 8)
                 segments. The first segment is then used for the first 512
                 sub-carriers. The second segment is used for the sub-carriers
                 512 to 1023 and so on.
                 The aggregate number of utilized nibbles on downstream direction
                 (in all segments) depends on NSds, and on upstream direction it
                 depends on NSus.
                 This value is referred here as NS. The segment number is in
                 xdsl2SCStatusSegment.
                 Nibble i (0 <= i < MIN(NS-(segment-1)*512,512)) in each
                 segment is set to a value in the range 0 to 15 to indicate that
                 the respective downstream or upstream sub-carrier j
                 (j=(segement-1)*512+i) has the same amount of bits
                 allocation.
                 Unit: bits
                "
            REFERENCE    "ITU-T G.997.1, paragraph #7.5.1.29.1 (BITSpsds)
                          and paragraph #7.5.1.29.2 (BITSpsus)"
            ::= { vdsl2SCStatusSegmentEntry 7 }
        
        vdsl2SCStatusSegmentGainAlloc  OBJECT-TYPE
            SYNTAX      OCTET STRING  (SIZE(0..1024))
            MAX-ACCESS  read-only
            STATUS      current
            DESCRIPTION
                "The gain allocation per sub-carrier.  An array of 512 16-bits
                 values, designed for supporting up to 512 (downstream) sub-
                 carriers. When more then 512 sub-carriers are supported,
                 the status information is reported through multiple (up to 8)
                 segments. The first segment is then used for the first 512
                 sub-carriers. The second segment is used for the sub-carriers
                 512 to 1023 and so on.
                 The aggregate number of utilized octets on downstream direction
                 depends on NSds, and on upstream direction it depends on NSus.
                 This value is referred here as NS. The segment number is in
                 xdsl2SCStatusSegment.
                 Value i (0 <= i < MIN(NS-(segment-1)*512,512)) in each
                 segment is set to a value in the range 0 to 4093 to indicate
                 that the respective downstream or upstream sub-carrier j
                 (j=(segement-1)*512+i) has the same amount of gain value.
                 The gain value is represented as a multiple of 1/512 on
                 linear scale.  Each value in this array is 16 bits wide and is
                 stored in big endian format.
                "
            REFERENCE    "ITU-T G.997.1, paragraph #7.5.1.29.3 (GAINSpsds)
                          and paragraph #7.5.1.29.4 (GAINSpsus)"
            ::= { vdsl2SCStatusSegmentEntry 8 }
             
        vdsl2SCStatusSegmentTssi  OBJECT-TYPE
            SYNTAX      Vdsl2Tssi
            MAX-ACCESS  read-only
            STATUS      current
            DESCRIPTION
                "The transmit spectrum shaping (TSSi) breakpoints expressed
                 as the set of breakpoints exchanged during G.994.1.
                 Each breakpoint is a pair of values occupying 3 octets with the
                 following structure:
                 First 2 octets - Index of the subcarrier used in the context of
                                  the breakpoint.
                 Third octet    - The shaping parameter at the breakpoint.
                 Subcarrier index is an unsigned number in the range 1 to either
                 NSCds (downstream direction) or NSCus (upstream direction).
                 The shaping parameter value is in the range 0 to 127 (units of
                 -0.5dB). The special value 127 indicates that the subcarrier
                 is not transmitted.
                "
            REFERENCE  "ITU-T G.997.1, paragraph #7.5.1.29.5 (TSSpsds)
                        and paragraph #7.5.1.29.6 (TSSpsus)"
            ::= { vdsl2SCStatusSegmentEntry 9 }
             
        vdsl2SCStatusSegmentTxPSD  OBJECT-TYPE
            SYNTAX      OCTET STRING  (SIZE(0..1024))
            MAX-ACCESS  read-only
            STATUS      current
            DESCRIPTION
                "The TxPSD per sub-carrier.  An array of 512 16-bits
                 values, designed for supporting up to 512 (downstream) sub-
                 carriers. When more then 512 sub-carriers are supported,
                 the status information is reported through multiple (up to 8)
                 segments. The first segment is then used for the first 512
                 sub-carriers. The second segment is used for the sub-carriers
                 512 to 1023 and so on.
                "     
            ::= { vdsl2SCStatusSegmentEntry 65535 }
              
        vdsl2SCStatusSegmentSnrMargin  OBJECT-TYPE
            SYNTAX      OCTET STRING  (SIZE(0..1024))
            MAX-ACCESS  read-only
            STATUS      current
            DESCRIPTION
                "The SnrMargin per sub-carrier.  An array of 512 16-bits
                 values, designed for supporting up to 512 (downstream) sub-
                 carriers. When more then 512 sub-carriers are supported,
                 the status information is reported through multiple (up to 8)
                 segments. The first segment is then used for the first 512
                 sub-carriers. The second segment is used for the sub-carriers
                 512 to 1023 and so on.
                "
            ::= { vdsl2SCStatusSegmentEntry 65536 }
        
        vdsl2SCStatusSegmentLogScGroupSize  OBJECT-TYPE
            SYNTAX      Unsigned32(1 | 2 | 4 | 8)
            MAX-ACCESS  read-only
            STATUS      current
            DESCRIPTION
                "Number of sub-carriers per group used to report the H(f)
                 logarithmic representation values for the respective
                 transmission direction. The valid values are 1, 2, 4 and 8.
                 For ADSL, this parameter is equal to one and, for VDSL2, it is
                 equal to the size of a sub-carrier group used to compute these
                 parameters.
                 This parameter is only available after a loop diagnostic
                 procedure.
                 It's available for the first segment, other segments return '-1'. 
                "
            REFERENCE  "ITU-T G.997.1, paragraph #7.5.1.26.2 (HLINGds)
                        and paragraph #7.5.1.26.8 (HLINGus)"
            ::= { vdsl2SCStatusSegmentEntry 65537 }
        
        vdsl2SCStatusSegmentQlnScGroupSize  OBJECT-TYPE
            SYNTAX      Unsigned32(1 | 2 | 4 | 8)
            MAX-ACCESS  read-only
            STATUS      current
            DESCRIPTION
                "Number of sub-carriers per group used to report the Quiet
                 Line Noise values for the respective transmission direction.
                 The valid values are 1, 2, 4 and 8.
                 For ADSL, this parameter is equal to one and, for VDSL2, it is
                 equal to the size of a sub-carrier group used to compute these
                 parameters.
                 This parameter is only available after a loop diagnostic
                 procedure.
                 It's available for the first segment, other segments return '-1'. 
                "
            REFERENCE  "ITU-T G.997.1, paragraph #7.5.1.26.2 (HLINGds)
                         and paragraph #7.5.1.26.8 (HLINGus)"
            ::= { vdsl2SCStatusSegmentEntry 65538 }
             
        vdsl2SCStatusSegmentLinScGroupSize OBJECT-TYPE
            SYNTAX      Unsigned32(1 | 2 | 4 | 8)
            MAX-ACCESS  read-only
            STATUS      current
            DESCRIPTION
                "Number of sub-carriers per group used to report the H(f)
                 linear representation values for the respective transmission
                 direction. The valid values are 1, 2, 4 and 8. For ADSL, this
                 parameter is equal to one and, for VDSL2, it is equal to the
                 size of a sub-carrier group used to compute these parameters.
                 This parameter is only available after a loop diagnostic
                 procedure.
                 It's available for the first segment, other segments return '-1'. 
                "
            REFERENCE  "ITU-T G.997.1, paragraph #7.5.1.26.2 (HLINGds)
                          and paragraph #7.5.1.26.8 (HLINGus)"
            ::= { vdsl2SCStatusSegmentEntry 65539 }
             
        vdsl2SCStatusSegmentSnrScGroupSize  OBJECT-TYPE
            SYNTAX      Unsigned32(1 | 2 | 4 | 8)
            MAX-ACCESS  read-only
            STATUS      current
            DESCRIPTION
                "Number of sub-carriers per group used to report the SNR
                 values on the respective transmission direction.
                 The valid values are 1, 2, 4 and 8.
                 For ADSL, this parameter is equal to one and, for VDSL2, it is
                 equal to the size of a sub-carrier group used to compute these
                 parameters.
                 This parameter is only available after a loop diagnostic
                 procedure.
                 It's available for the first segment, other segments return '-1'. 
                "
            REFERENCE  "ITU-T G.997.1, paragraph #7.5.1.26.2 (HLINGds)
                         and paragraph #7.5.1.26.8 (HLINGus)"
            ::= { vdsl2SCStatusSegmentEntry 65540 }  
            
        hwvdsl2SCStatusSegmentQlnWithVectoring  OBJECT-TYPE
            SYNTAX      OCTET STRING  (SIZE(0..512))
            UNITS       "dBm/Hz"
            MAX-ACCESS  read-only
            STATUS      current
            DESCRIPTION
                "An array of up to 512 real Quiet Line Noise values in dBm/Hz
                 for the respective transmission direction.  It is designed for
                 up to 512 (downstream) sub-carriers groups and can be retrieved
                 in a single segment.
                 The number of utilized values on downstream direction depends
                 on NSds, and on upstream direction it depends on NSus.  This
                 value is referred here as NS.
                 Each array entry represents the QLN(f = i*Df) value for a
                 particular sub-carrier index i, (0 <= i < NS).
                 The QLN(f) is represented as ( -23-n(i)/2), with n(i) in the
                 range 0 to 254.  A special value n(i)=255 indicates that no
                 measurement could be done for the sub-carrier group because it
                 is out of the passband or that the noise PSD is out of range
                 to be represented.
                 This parameter is applicable in loop diagnostic procedure and
                 initialization.  Each value in this array is 8 bits wide.
                 Unit: dBm/Hz
                 This value is calculated with vectoring effect.
                "
            REFERENCE  "ITU-T G.997.1, paragraph #7.5.1.27.3 (QLNpsds)
                        and paragraph #7.5.1.27.6 (QLNpsus)"
            ::= { vdsl2SCStatusSegmentEntry 65541 }
                              
        hwVdslSCFextTable  OBJECT-TYPE
            SYNTAX      SEQUENCE  OF  HwVdslSCFextEntry
            MAX-ACCESS  not-accessible
            STATUS      current
            DESCRIPTION
                "The table hwVdslSCFextTable contains FEXT coupling function parameters.
                 The indexes of this table are ifIndex, hwVdslSCFextFromIfindex, 
                 and hwVdslSCFextRequestXLinScGroupSize.                   
                "
            ::= { vdsl2Status 6 }
        
        hwVdslSCFextEntry  OBJECT-TYPE 
            SYNTAX      HwVdslSCFextEntry
            MAX-ACCESS  not-accessible
            STATUS      current
            DESCRIPTION
                "The table hwVdslSCFextTable contains FEXT coupling function parameters.
                 The indexes of this entry are ifIndex, hwVdslSCFextFromIfindex, 
                 and hwVdslSCFextRequestXLinScGroupSize.                   
                "
            INDEX  { ifIndex,
                     hwVdslSCFextFromIfindex,
                     hwVdslSCFextRequestXLinScGroupSize   }
            ::= { hwVdslSCFextTable 1 }
        
        HwVdslSCFextEntry  ::=
            SEQUENCE {
              hwVdslSCFextFromIfindex                   Integer32,
              hwVdslSCFextRequestXLinScGroupSize        Unsigned32,
              hwVdslSCFextXLinScaleDs                   Unsigned32,
              hwVdslSCFextXlinScGroupSizeDs             Unsigned32,
              hwVdslSCFextXLinBandDs                    OCTET STRING,
              hwVdslSCFextXlinRealDs                    OCTET STRING,
              hwVdslSCFextXlinImgDs                     OCTET STRING,
              hwVdslSCFextXLinScaleUs                   Unsigned32,
              hwVdslSCFextXlinScGroupSizeUs             Unsigned32,
              hwVdslSCFextXLinBandUs                    OCTET STRING,
              hwVdslSCFextXlinRealUs                    OCTET STRING,
              hwVdslSCFextXlinImgUs                     OCTET STRING
            }
        
        hwVdslSCFextFromIfindex  OBJECT-TYPE
            SYNTAX      Integer32
            MAX-ACCESS  not-accessible
            STATUS      current
            DESCRIPTION
                "The hwVdslSCFextFromIfindex is an interface index where the
                 interface has an ifType of vdsl2(251).
                "
           ::= { hwVdslSCFextEntry 1 }
        
        hwVdslSCFextRequestXLinScGroupSize  OBJECT-TYPE
            SYNTAX      Unsigned32(1 | 2 | 4 | 8 | 16 | 32 | 64)
            MAX-ACCESS  not-accessible
            STATUS      current
            DESCRIPTION
                "This parameter is the requested value of XLING. 
                 The valid values are 1, 2, 4, 8, 16, 32, and 64.
                "
            REFERENCE  "ITU-T G.997.1, paragraph #7.5.1.38.3 and #7.5.1.38.8"
            ::= { hwVdslSCFextEntry 2 }
        
        hwVdslSCFextXLinScaleDs  OBJECT-TYPE
            SYNTAX      Unsigned32
            MAX-ACCESS  read-only
            STATUS      current
            DESCRIPTION
                "This parameter is the scale factor to be applied to the downstream 
                 Xlinpsds values. It is represented as an unsigned integer 
                 in the range from 1 to 2^16 - 1.
                "
            REFERENCE  "ITU-T G.997.1, paragraph #7.5.1.38.1 "
            ::= { hwVdslSCFextEntry 3 }
            
        hwVdslSCFextXlinScGroupSizeDs  OBJECT-TYPE
            SYNTAX      Unsigned32(1 | 2 | 4 | 8 | 16 | 32 | 64)
            MAX-ACCESS  read-only
            STATUS      current
            DESCRIPTION
                "This parameter is the number of subcarriers per group used 
                 to report Xlinpsds. The valid values are 1, 2, 4, 8, 16, 32, 
                 and 64. XLINGds should equal the sub-sampling factor used to 
                 estimate the crosstalk channel for cancellation. 
                "
            REFERENCE  "ITU-T G.997.1, paragraph #7.5.1.38.2"
            ::= { hwVdslSCFextEntry 4 }
            
        hwVdslSCFextXLinBandDs  OBJECT-TYPE
            SYNTAX      OCTET STRING  (SIZE(0..96))
            MAX-ACCESS  read-only
            STATUS      current
            DESCRIPTION
                "XLINBANDSds contains pairs of (start_subcarrier_index, stop_subcarrier_index) 
                 for every band in which XLINpsds is reported.
                "
            REFERENCE  "ITU-T G.997.1, paragraph #7.5.1.38.4"
            ::= { hwVdslSCFextEntry 5 }

        hwVdslSCFextXlinRealDs  OBJECT-TYPE
            SYNTAX      OCTET STRING  (SIZE(0..1024))
            MAX-ACCESS  read-only
            STATUS      current
            DESCRIPTION
                "For each given VCE port index k, this parameter is a one-dimensional 
                 array of complex values in linear scale for downstream FEXT coupling 
                 coefficients Xlinds(f) originating from the loop connected to the VCE 
                 port k into the loop for which Xlinds(f) is being reported. Each array 
                 entry represents the Xlinds(f = n*Df) value for a particular subcarrier 
                 index n. The Xlinds(f = n*Df) value is represented as 
                 ((XLINSCds/2^15) * ((a(n) + j*b(n))/2^15)), where a(n) and b(n) are 
                 signed integers in the (-2^15 + 1) to (+2^15 - 1) range. A special 
                 value indicates that no measurement could be done from line k into this 
                 line for subcarrier n. Another special value indicates that there is 
                 no phase information and the magnitude of Xlinds
                 (f = n*Df) is ((XLINSCds/2^15) * (a(n)/2^15)).
                "
            REFERENCE  "ITU-T G.997.1, paragraph #7.5.1.38.5 "
            ::= { hwVdslSCFextEntry 6 }
            
        hwVdslSCFextXlinImgDs  OBJECT-TYPE
            SYNTAX      OCTET STRING  (SIZE(0..1024))
            MAX-ACCESS  read-only
            STATUS      current
            DESCRIPTION
                "For each given VCE port index k, this parameter is a one-dimensional 
                 array of complex values in linear scale for downstream FEXT coupling 
                 coefficients Xlinds(f) originating from the loop connected to the VCE 
                 port k into the loop for which Xlinds(f) is being reported. Each array 
                 entry represents the Xlinds(f = n*Df) value for a particular subcarrier 
                 index n. The Xlinds(f = n*Df) value is represented as 
                 ((XLINSCds/2^15) * ((a(n) + j*b(n))/2^15)), where a(n) and b(n) are 
                 signed integers in the (-2^15 + 1) to (+2^15 - 1) range. A special 
                 value indicates that no measurement could be done from line k into this 
                 line for subcarrier n. Another special value indicates that there is 
                 no phase information and the magnitude of Xlinds
                 (f = n*Df) is ((XLINSCds/2^15) * (a(n)/2^15)).
                "
            REFERENCE  "ITU-T G.997.1, paragraph #7.5.1.38.5"
            ::= { hwVdslSCFextEntry 7 }            
            
        hwVdslSCFextXLinScaleUs  OBJECT-TYPE
            SYNTAX      Unsigned32
            MAX-ACCESS  read-only
            STATUS      current
            DESCRIPTION
                "This parameter is the scale factor to be applied to the upstream 
                 Xlinpsus values. It is represented as an unsigned integer 
                 in the range from 1 to 2^16 - 1.
                "
            REFERENCE  "ITU-T G.997.1, paragraph #7.5.1.38.6"
            ::= { hwVdslSCFextEntry 8 }
            
        hwVdslSCFextXlinScGroupSizeUs  OBJECT-TYPE
            SYNTAX      Unsigned32(1 | 2 | 4 | 8 | 16 | 32 | 64)
            MAX-ACCESS  read-only
            STATUS      current
            DESCRIPTION
                "This parameter is the number of subcarriers per group used 
                 to report Xlinpsus. The valid values are 1, 2, 4, 8, 16, 32, 
                 and 64. XLINGus should equal the sub-sampling factor used to 
                 estimate the crosstalk channel for cancellation. 
                "
            REFERENCE  "ITU-T G.997.1, paragraph #7.5.1.38.7"
            ::= { hwVdslSCFextEntry 9 }
            
        hwVdslSCFextXLinBandUs  OBJECT-TYPE
            SYNTAX      OCTET STRING  (SIZE(0..96))
            MAX-ACCESS  read-only
            STATUS      current
            DESCRIPTION
                "XLINBANDSus contains pairs of (start_subcarrier_index, stop_subcarrier_index) 
                 for every band in which XLINpsus is reported.
                "
            REFERENCE  "ITU-T G.997.1, paragraph #7.5.1.38.9"
            ::= { hwVdslSCFextEntry 10 }

        hwVdslSCFextXlinRealUs  OBJECT-TYPE
            SYNTAX      OCTET STRING  (SIZE(0..1024))
            MAX-ACCESS  read-only
            STATUS      current
            DESCRIPTION
                "For each given VCE port index k, this parameter is a one-dimensional 
                 array of complex values in linear scale for upstream FEXT coupling 
                 coefficients Xlinus(f) originating from the loop connected to the VCE 
                 port k into the loop for which Xlinus(f) is being reported. Each array 
                 entry represents the Xlinus(f = n*Df) value for a particular subcarrier 
                 index n. The Xlinus(f = n*Df) value is represented as 
                 ((XLINSCus/2^15) * ((a(n) + j*b(n))/2^15)), where a(n) and b(n) are 
                 signed integers in the (-2^15 + 1) to (+2^15 - 1) range. A special 
                 value indicates that no measurement could be done from line k into this 
                 line for subcarrier n. Another special value indicates that there is 
                 no phase information and the magnitude of Xlinus
                 (f = n*Df) is ((XLINSCus/2^15) * (a(n)/2^15)).
                "
            REFERENCE  "ITU-T G.997.1, paragraph #7.5.1.38.10"
            ::= { hwVdslSCFextEntry 11 }
            
        hwVdslSCFextXlinImgUs  OBJECT-TYPE
            SYNTAX      OCTET STRING  (SIZE(0..1024))
            MAX-ACCESS  read-only
            STATUS      current
            DESCRIPTION
                "For each given VCE port index k, this parameter is a one-dimensional 
                 array of complex values in linear scale for upstream FEXT coupling 
                 coefficients Xlinus(f) originating from the loop connected to the VCE 
                 port k into the loop for which Xlinus(f) is being reported. Each array 
                 entry represents the Xlinus(f = n*Df) value for a particular subcarrier 
                 index n. The Xlinus(f = n*Df) value is represented as 
                 ((XLINSCus/2^15) * ((a(n) + j*b(n))/2^15)), where a(n) and b(n) are 
                 signed integers in the (-2^15 + 1) to (+2^15 - 1) range. A special 
                 value indicates that no measurement could be done from line k into this 
                 line for subcarrier n. Another special value indicates that there is 
                 no phase information and the magnitude of Xlinus
                 (f = n*Df) is ((XLINSCus/2^15) * (a(n)/2^15)).
                "
            REFERENCE  "ITU-T G.997.1, paragraph #7.5.1.38.10"
            
            ::= { hwVdslSCFextEntry 12 }
        --       vdsl2LineInventoryTable             
        vdsl2LineInventoryTable  OBJECT-TYPE
            SYNTAX      SEQUENCE  OF  Vdsl2LineInventoryEntry
            MAX-ACCESS  not-accessible
            STATUS      current
            DESCRIPTION
                "The table vdsl2LineInventoryTable contains inventory of VDSL2
                 unit. The indexes of this table are ifIndex and vdsl2LInvUnit.
                "
            ::= { vdsl2Inventory 1 }
            
        vdsl2LineInventoryEntry  OBJECT-TYPE
            SYNTAX      Vdsl2LineInventoryEntry
            MAX-ACCESS  not-accessible
            STATUS      current
            DESCRIPTION
                "The table vdsl2LineInventoryTable contains inventory of VDSL2
                 unit. The indexes of this entry are ifIndex and vdsl2LInvUnit.
                "
            INDEX  { ifIndex, vdsl2LInvUnit }
            ::= { vdsl2LineInventoryTable 1 }
        
        Vdsl2LineInventoryEntry  ::=
           SEQUENCE {
              vdsl2LInvUnit                      Vdsl2Unit,
              vdsl2LInvG994VendorId              OCTET STRING,
              vdsl2LInvSystemVendorId            OCTET STRING,
              vdsl2LInvVersionNumber             OCTET STRING,
              vdsl2LInvSerialNumber              OCTET STRING,
              vdsl2LInvSelfTestResult            OCTET STRING,
              vdsl2LInvTransmissionCapabilities  Vdsl2TransmissionModeType,
              vdsl2LInvModelId	                 OCTET STRING
           }
        
        vdsl2LInvUnit  OBJECT-TYPE
            SYNTAX      Vdsl2Unit
            MAX-ACCESS  not-accessible
            STATUS      current
            DESCRIPTION
                "The termination unit XTUC{1} or XTUR{2}."            
            ::= { vdsl2LineInventoryEntry 1 }
            
        vdsl2LInvG994VendorId  OBJECT-TYPE
            SYNTAX      OCTET STRING  (SIZE(0..8))
            MAX-ACCESS  read-only
            STATUS      current
            DESCRIPTION
                "The xTU G.994.1 Vendor ID as inserted in the G.994.1 CL/CLR
                 message.  It consists of 8 binary octets, including a country
                 code followed by a (regionally allocated) provider code, as
                 defined in Recommendation T.35.
                "
            REFERENCE    "ITU-T G.997.1(200604), paragraph 7.4"
            ::= { vdsl2LineInventoryEntry 2 }
        
        vdsl2LInvSystemVendorId  OBJECT-TYPE
            SYNTAX      OCTET STRING  (SIZE(0..8))
            MAX-ACCESS  read-only
            STATUS      current
            DESCRIPTION
                "The xTU System Vendor ID (identifies the xTU system
                 integrator) as inserted in the Overhead Messages (both xTUs
                 for G.992.3 and G.992.4) or in the Embedded Operations
                 Channel (only xTU-R in G.992.1 and G.992.2).  It consists of
                 8 binary octets, with same format as used for
                 Vdsl2InvG994VendorId.
                "
            REFERENCE    "ITU-T G.997.1(200604), paragraph 7.4"
            ::= { vdsl2LineInventoryEntry 3 }
        
        vdsl2LInvVersionNumber  OBJECT-TYPE
            SYNTAX      OCTET STRING  (SIZE(0..16))
            MAX-ACCESS  read-only
            STATUS      current
            DESCRIPTION
                "The xTU version number (vendor specific information) as
                 inserted in the Overhead Messages (both xTUs for G.992.3 and
                 G.992.4) or in the Embedded Operations Channel (only xTU-R in
                 G.992.1 and G.992.2).  It consists of up to 16 binary octets.
                "
            REFERENCE    "ITU-T G.997.1(200604), paragraph 7.4"
            ::= { vdsl2LineInventoryEntry 4 }
        
        vdsl2LInvSerialNumber  OBJECT-TYPE
            SYNTAX      OCTET STRING  (SIZE(0..32))
            MAX-ACCESS  read-only
            STATUS      current
            DESCRIPTION
                "The xTU serial number (vendor specific information) as
                 inserted in the Overhead Messages (both xTUs for G.992.3 and
                 G.992.4) or in the Embedded Operations Channel (only xTU-R in
                 G.992.1 and G.992.2).  It is vendor specific information.  It
                 consists of up to 32 ASCII characters.
                "
            REFERENCE    "ITU-T G.997.1(200604), paragraph 7.4"
            ::= { vdsl2LineInventoryEntry 5 }
        
        vdsl2LInvSelfTestResult  OBJECT-TYPE
            SYNTAX      OCTET STRING  (SIZE(0..4))
            MAX-ACCESS  read-only
            STATUS      current
            DESCRIPTION
                "The xTU self-test result, coded as a 32-bit integer.  The
                 most significant octet of this object is '0' if the self-test
                 passed, and '1' if the self-test failed.  The interpretation
                 of the other octets is vendor discretionary.
                "
            REFERENCE    "ITU-T G.997.1(200604), paragraph 7.4"
            ::= { vdsl2LineInventoryEntry 6 }
        
        vdsl2LInvTransmissionCapabilities  OBJECT-TYPE
            SYNTAX      Vdsl2TransmissionModeType
            MAX-ACCESS  read-only
            STATUS      current
            DESCRIPTION
                "The xTU transmission system capability list of the different
                 coding types.  It is coded in a bit-map representation with 1
                 or more bits set.  A bit set to '1' means that the xTU
                 supports the respective coding.  The value may be derived
                 from the handshaking procedures defined in G.994.1.  A set
                 of VDSL2 line transmission modes, with one bit per mode.
                "
            REFERENCE    "ITU-T G.997.1(200604), paragraph 7.4"
            ::= { vdsl2LineInventoryEntry 7 }      
             
        vdsl2LInvModelId  OBJECT-TYPE
            SYNTAX      OCTET STRING  (SIZE(0..32))
            MAX-ACCESS  read-only
            STATUS      current
            DESCRIPTION
                "The XTU model ID."
            ::= { vdsl2LineInventoryEntry 8 }
        
        
        --       vdsl2LineConfTemplateTable          
        vdsl2LineConfTemplateTable  OBJECT-TYPE
            SYNTAX      SEQUENCE  OF  Vdsl2LineConfTemplateEntry
            MAX-ACCESS  not-accessible
            STATUS      current
            DESCRIPTION
                "The table vdsl2LineConfTemplateTable contains VDSL2 line
                 configuration template. The index of this table is 
                 vdsl2LConfTempTemplateName.  
                 A default template with an index of 'DEFVAL' will
                 always exist and its parameters will be set to vendor-specific
                 values, unless otherwise specified in this document.
                "
            ::= { vdsl2ProfileLine 1 }
        
        vdsl2LineConfTemplateEntry  OBJECT-TYPE
            SYNTAX      Vdsl2LineConfTemplateEntry
            MAX-ACCESS  not-accessible
            STATUS      current
            DESCRIPTION
                "The table vdsl2LineConfTemplateTable contains VDSL2 line
                 configuration template.
                 The index of this entry is vdsl2LConfTempTemplateName.
                 A default template with an index of 'DEFVAL' will
                 always exist and its parameters will be set to vendor-specific
                 values, unless otherwise specified in this document.
                "
            INDEX  { IMPLIED vdsl2LConfTempTemplateName }
            ::= { vdsl2LineConfTemplateTable 1 }
        
        Vdsl2LineConfTemplateEntry  ::=
            SEQUENCE {
              vdsl2LConfTempTemplateName      OCTET STRING,
              vdsl2LConfTempLineProfile       OCTET STRING,
              vdsl2LConfTempChan1ConfProfile  OCTET STRING,
              vdsl2LConfTempChan1RaRatioDs    Unsigned32,
              vdsl2LConfTempChan1RaRatioUs    Unsigned32,
              vdsl2LConfTempChan2ConfProfile  OCTET STRING,
              vdsl2LConfTempChan2RaRatioDs    Unsigned32,
              vdsl2LConfTempChan2RaRatioUs    Unsigned32,
              vdsl2LConfTempChan3ConfProfile  OCTET STRING,
              vdsl2LConfTempChan3RaRatioDs    Unsigned32,
              vdsl2LConfTempChan3RaRatioUs    Unsigned32,
              vdsl2LConfTempChan4ConfProfile  OCTET STRING,
              vdsl2LConfTempChan4RaRatioDs    Unsigned32,
              vdsl2LConfTempChan4RaRatioUs    Unsigned32,
              vdsl2LConfTempRowStatus         RowStatus
           }
        
        vdsl2LConfTempTemplateName  OBJECT-TYPE
            SYNTAX      OCTET STRING (SIZE(1..32))
            MAX-ACCESS  not-accessible
            STATUS      current
            DESCRIPTION
                "This object identifies a row in this table."
            REFERENCE    "DSL Forum TR-90, paragraph 5.1.4"
            ::= { vdsl2LineConfTemplateEntry 1 }
        
        vdsl2LConfTempLineProfile  OBJECT-TYPE
            SYNTAX      OCTET STRING (SIZE(1..32))
            MAX-ACCESS  read-create
            STATUS      current
            DESCRIPTION
                "The value of this object identifies the row in the VDSL2 Line
                 Configuration Profile Table, (Vdsl2LineConfProfileTable),
                 which applies for this VDSL2 line.
                "
            REFERENCE    "DSL Forum TR-90, paragraph 5.1.4"
            DEFVAL       { "DEFVAL" }
            ::= { vdsl2LineConfTemplateEntry 2 }
        
        vdsl2LConfTempChan1ConfProfile  OBJECT-TYPE
            SYNTAX      OCTET STRING (SIZE(1..32))
            MAX-ACCESS  read-create
            STATUS      current
            DESCRIPTION
                "The value of this object identifies the row in the VDSL2
                 Channel Configuration Profile Table,
                 (Vdsl2ChanConfProfileTable) that applies to VDSL2 bearer
                 channel #1.  The channel profile name specified here must
                 match the name of an existing row in the
                 vdsl2ChConfProfileTable table.
                "
            DEFVAL       { "DEFVAL" }
            ::= { vdsl2LineConfTemplateEntry 3 }
        
        vdsl2LConfTempChan1RaRatioDs  OBJECT-TYPE
            SYNTAX      Unsigned32(0..100)
            UNITS       "percents"
            MAX-ACCESS  read-create
            STATUS      current
            DESCRIPTION
                "Rate Adaptation Ratio.  The ratio (in %) that should be taken
                 into account for the bearer channel #1 when performing rate
                 adaptation on Downstream.  The ratio refers to the available
                 data rate in excess of the Minimum Data Rate, summed over all
                 bearer channels.  Also, the 100 -
                 Vdsl2ConfTemplateChan1RaRatioDs is the ratio of excess data
                 rate to be assigned to all other bearer channels on Downstream
                 direction.  The sum of rate adaptation ratios over all bearers
                 on the same direction shall be equal to 100%.
                 Unit: percents
                "
            REFERENCE    "ITU-T G.997.1, paragraph 7.3.2.1"
            DEFVAL       { 100 }
            ::= { vdsl2LineConfTemplateEntry 4 }
        
        vdsl2LConfTempChan1RaRatioUs  OBJECT-TYPE
            SYNTAX      Unsigned32(0..100)
            UNITS       "percents"
            MAX-ACCESS  read-create
            STATUS      current
            DESCRIPTION
                "Rate Adaptation Ratio.  The ratio (in %) that should be taken
                 into account for the bearer channel #1 when performing rate
                 adaptation on Upstream.  The ratio refers to the available
                 data rate in excess of the Minimum Data Rate, summed over all
                 bearer channels.  Also, the
                 100 - Vdsl2ConfTemplateChan1RaRatioUs is the ratio of excess
                 data rate to be assigned to all other bearer channels on
                 Upstream direction.  The sum of rate adaptation ratios over
                 all bearers on the same direction shall be equal to 100 %.
                 Unit: percents
                "
            
            REFERENCE    "ITU-T G.997.1, paragraph 7.3.2.1"
            DEFVAL       { 100 }
            ::= { vdsl2LineConfTemplateEntry 5 }
        
        vdsl2LConfTempChan2ConfProfile  OBJECT-TYPE
            SYNTAX      OCTET STRING (SIZE(0..32))
            MAX-ACCESS  read-create
            STATUS      current
            DESCRIPTION
                "The value of this object identifies the row in the VDSL2
                 Channel Configuration Profile Table,
                 (Vdsl2ChanConfProfileTable) that applies to VDSL2 bearer
                 channel #2.  If the channel is unused, then the object is set
                 to a zero length string.
                 This object may be set to a zero length string only if
                 vdsl2LConfTempChan3ConfProfile contains a zero length
                 string.
                "
            ::= { vdsl2LineConfTemplateEntry 6 }
            
        vdsl2LConfTempChan2RaRatioDs  OBJECT-TYPE
            SYNTAX      Unsigned32(0..100)
            UNITS       "percents"
            MAX-ACCESS  read-create
            STATUS      current
            DESCRIPTION
                "Rate Adaptation Ratio.  The ratio (in %) that should be taken
                 into account for the bearer channel #2 when performing rate
                 adaptation on Downstream.  The ratio refers to the available
                 data rate in excess of the Minimum Data Rate, summed over all
                 bearer channels.  Also, the
                 100 - Vdsl2ConfTemplateChan2RaRatioDs is the ratio of excess
                 data rate to be assigned to all other bearer channels on
                 Downstream direction.  The sum of rate adaptation ratios
                 over all bearers on the same direction shall be equal to
                 100%.
                 Unit: percents
                "
            REFERENCE    "ITU-T G.997.1, paragraph 7.3.2.1"
            DEFVAL       { 0 }
            ::= { vdsl2LineConfTemplateEntry 7 }
        
        vdsl2LConfTempChan2RaRatioUs  OBJECT-TYPE
            SYNTAX      Unsigned32(0..100)
            UNITS       "percents"
            MAX-ACCESS  read-create
            STATUS      current
            DESCRIPTION
                "Rate Adaptation Ratio.  The ratio (in %) that should be taken
                 into account for the bearer channel #2 when performing rate
                 adaptation on Upstream.  The ratio refers to the available
                 data rate in excess of the Minimum Data Rate, summed over all
                 bearer channels.  Also, the
                 100 - Vdsl2ConfTemplateChan2RaRatioUs is the ratio of excess
                 data rate to be assigned to all other bearer channels on
                 Upstream direction.  The sum of rate adaptation ratios over
                 all bearers on the same direction shall be equal to 100 %.
                 Unit: percents
                "
            REFERENCE    "ITU-T G.997.1, paragraph 7.3.2.1"
            DEFVAL       { 0 }
            ::= { vdsl2LineConfTemplateEntry 8 }
        
        vdsl2LConfTempChan3ConfProfile  OBJECT-TYPE
            SYNTAX      OCTET STRING (SIZE(0..32))
            MAX-ACCESS  read-create
            STATUS      current
            DESCRIPTION
                "The value of this object identifies the row in the VDSL2
                 Channel Configuration Profile Table,
                 (Vdsl2ChanConfProfileTable) that applies to VDSL2 bearer
                 channel #3.  If the channel is unused, then the object is set
                 to a zero length string.
                 This object may be set to a zero length string only if
                 vdsl2LConfTempChan4ConfProfile contains a zero length
                 string.
                 This object may be set to a non-zero length string only if
                 vdsl2LConfTempChan2ConfProfile contains a non-zero length
                 string.
                "
            ::= { vdsl2LineConfTemplateEntry 9 }
        
        vdsl2LConfTempChan3RaRatioDs  OBJECT-TYPE
            SYNTAX      Unsigned32(0..100)
            UNITS       "percents"
            MAX-ACCESS  read-create
            STATUS      current
            DESCRIPTION
                "Rate Adaptation Ratio.  The ratio (in %) that should be taken
                 into account for the bearer channel #3 when performing rate
                 adaptation on Downstream.  The ratio refers to the available
                 data rate in excess of the Minimum Data Rate, summed over all
                 bearer channels.  Also, the 100 -
                 Vdsl2ConfTemplateChan3RaRatioDs is the ratio of excess data
                 rate to be assigned to all other bearer channels on Downstream
                 direction.  The sum of rate adaptation ratios over all bearers
                 on the same direction shall be equal to 100%.
                 Unit: percents
                "
            REFERENCE    "ITU-T G.997.1, paragraph 7.3.2.1"
            DEFVAL       { 0 }
            ::= { vdsl2LineConfTemplateEntry 10 }
            
        vdsl2LConfTempChan3RaRatioUs  OBJECT-TYPE
            SYNTAX      Unsigned32(0..100)
            UNITS       "percents"
            MAX-ACCESS  read-create
            STATUS      current
            DESCRIPTION
                "Rate Adaptation Ratio.  The ratio (in %) that should be taken
                 into account for the bearer channel #3 when performing rate
                 adaptation on Upstream.  The ratio refers to the available
                 data rate in excess of the Minimum Data Rate, summed over all
                 bearer channels.  Also, the
                 100 - Vdsl2ConfTemplateChan3RaRatioUs is the ratio of excess
                 data rate to be assigned to all other bearer channels on
                 Upstream direction.  The sum of rate adaptation ratios over
                 all bearers on the same direction shall be equal to 100%.
                 Unit: percents
                "
            REFERENCE    "ITU-T G.997.1, paragraph 7.3.2.1"
            DEFVAL       { 0 }
            ::= { vdsl2LineConfTemplateEntry 11 }
        
        vdsl2LConfTempChan4ConfProfile  OBJECT-TYPE
            SYNTAX      OCTET STRING (SIZE(0..32))
            MAX-ACCESS  read-create
            STATUS      current
            DESCRIPTION
                "The value of this object identifies the row in the VDSL2
                 Channel Configuration Profile Table
                 (Vdsl2ChanConfProfileTableDs) that applies to VDSL2 bearer
                 channel #4.  If the channel is unused, then the object is set
                 to a zero length string.
                 This object may be set to a non-zero length string only if
                 vdsl2LConfTempChan3ConfProfile contains a non-zero length
                 string.
                "
            ::= { vdsl2LineConfTemplateEntry 12 }
        
        vdsl2LConfTempChan4RaRatioDs  OBJECT-TYPE
            SYNTAX      Unsigned32(0..100)
            UNITS       "percents"
            MAX-ACCESS  read-create
            STATUS      current
            DESCRIPTION
                "Rate Adaptation Ratio.  The ratio (in %) that should be taken
                 into account for the bearer channel #4 when performing rate
                 adaptation on Downstream.  The ratio refers to the available
                 data rate in excess of the Minimum Data Rate, summed over all
                 bearer channels.  Also, the 100 -
                 vdsl2LConfTempChan4RaRatioDs is the ratio of
                 excess data rate to be assigned to all other bearer channels.
                 The sum of rate adaptation ratios over all bearers on the same
                 direction shall sum to 100%.
                 Unit: percents
                "
            REFERENCE    "ITU-T G.997.1, paragraph 7.3.2.1"
            DEFVAL       { 0 }
            ::= { vdsl2LineConfTemplateEntry 13 }
        
        vdsl2LConfTempChan4RaRatioUs  OBJECT-TYPE
            SYNTAX      Unsigned32(0..100)
            UNITS       "percents"
            MAX-ACCESS  read-create
            STATUS      current
            DESCRIPTION
                "Rate Adaptation Ratio.  The ratio (in %) that should be taken
                 into account for the bearer channel #4 when performing rate
                 adaptation on Upstream.  The ratio refers to the available
                 data rate in excess of the Minimum Data Rate, summed over
                 all bearer channels.  Also, the 100 -
                 vdsl2LConfTempChan4RaRatioUs is the
                 ratio of excess data rate to be assigned to all other bearer
                 channels.  The sum of rate adaptation ratios over all bearers
                 on the same direction shall sum to 100%.
                 Unit: percents
                "
            REFERENCE    "ITU-T G.997.1, paragraph 7.3.2.1"
            DEFVAL       { 0 }
            ::= { vdsl2LineConfTemplateEntry 14 }
            
        vdsl2LConfTempRowStatus  OBJECT-TYPE
            SYNTAX      RowStatus
            MAX-ACCESS  read-create
            STATUS      current
            DESCRIPTION
                "This object is used to create a new row or to modify or
                 delete an existing row in this table.
                 
                 A profile is activated by setting this object to 'active'.
                 When 'active' is set, the system will validate the profile.
                 
                 Before a profile can be deleted or taken out of service
                 (by setting this object to 'destroy' or 'outOfService'),
                 it must be not referenced from all associated
                 lines.
                "
            ::= { vdsl2LineConfTemplateEntry 15 }
            
        
        --        vdsl2LineConfProfTable        
        Vdsl2LineClockReferenceType ::= TEXTUAL-CONVENTION
            STATUS    current
            DESCRIPTION
                "The various clock references for the VDSL line.
                 Options:
                 1. freeRun(1)  - network timing reference clock mode is freeRun
                 2. system(2)   - network timing reference clock mode is system
                "
            SYNTAX    INTEGER
                   {
                   freeRun(1),  
                   system(2)    
                   }
        
        vdsl2LineConfProfTable  OBJECT-TYPE
            SYNTAX      SEQUENCE  OF  Vdsl2LineConfProfEntry
            MAX-ACCESS  not-accessible
            STATUS      current
            DESCRIPTION
                "The table vdsl2LineConfProfTable contains VDSL2 line profile
                 configuration. The index of this table is vdsl2LConfProfProfileName. 
                 A default profile with an index of 'DEFVAL' will
                 always exist and its parameters will be set to vendor-specific
                 values, unless otherwise specified in this document.
                "
            ::= { vdsl2ProfileLine 2 }
            
        vdsl2LineConfProfEntry  OBJECT-TYPE
            SYNTAX      Vdsl2LineConfProfEntry
            MAX-ACCESS  not-accessible
            STATUS      current
            DESCRIPTION
                "The table vdsl2LineConfProfTable contains VDSL2 line profile
                 configuration. The index of this entry is vdsl2LConfProfProfileName.
                 A default profile with an index of 'DEFVAL' will
                 always exist and its parameters will be set to vendor-specific
                 values, unless otherwise specified in this document.
                "
            INDEX  { IMPLIED vdsl2LConfProfProfileName }
            ::= { vdsl2LineConfProfTable 1 }
        
        Vdsl2LineConfProfEntry  ::=
           SEQUENCE {
              vdsl2LConfProfProfileName          OCTET STRING,
              vdsl2LConfProfScMaskDs             Vdsl2ScMaskDs,
              vdsl2LConfProfScMaskUs             Vdsl2ScMaskUs,
              vdsl2LConfProfRfiBands             OCTET STRING,
              vdsl2LConfProfVDSLtoneblackout     OCTET STRING,
              vdsl2LConfProfRaModeDs             INTEGER,
              vdsl2LConfProfRaModeUs             INTEGER,
              vdsl2LConfProfRaUsNrmDs            Unsigned32,
              vdsl2LConfProfRaUsNrmUs            Unsigned32,
              vdsl2LConfProfRaUsTimeDs           Unsigned32,
              vdsl2LConfProfRaUsTimeUs           Unsigned32,
              vdsl2LConfProfRaDsNrmsDs           Unsigned32,
              vdsl2LConfProfRaDsNrmsUs           Unsigned32,
              vdsl2LConfProfRaDsTimeDs           Unsigned32,
              vdsl2LConfProfRaDsTimeUs           Unsigned32,
              vdsl2LConfProfTargetSnrmDs         Unsigned32,
              vdsl2LConfProfTargetSnrmUs         Unsigned32,
              vdsl2LConfProfMaxSnrmDs            Unsigned32,
              vdsl2LConfProfMaxSnrmUs            Unsigned32,
              vdsl2LConfProfMinSnrmDs            Unsigned32,
              vdsl2LConfProfMinSnrmUs            Unsigned32,
              vdsl2LConfProfMsgMinUs             Unsigned32,
              vdsl2LConfProfMsgMinDs             Unsigned32,
              vdsl2LConfProfXtuTransSysEna       Vdsl2TransmissionModeType,
              vdsl2LConfProfPmMode               Vdsl2LConfProfPmMode,
              vdsl2LConfProfL0Time               Unsigned32,
              vdsl2LConfProfL2Time               Unsigned32,
              vdsl2LConfProfL2Atpr               Unsigned32,
              vdsl2LConfProfL2Atprt              Unsigned32,  
              vdsl2LConfProfDpboEpsd             Vdsl2DpboEpsd,
              vdsl2LConfProfDpboEsel             Unsigned32,
              vdsl2LConfProfDpboEscm             Vdsl2DpboEscm,
              vdsl2LConfProfDpboMus		 Unsigned32,
              vdsl2LConfProfDpboFmin	         Unsigned32,
              vdsl2LConfProfDpboFmax		 Unsigned32,
              vdsl2LConfProfUpboPsdBand          Vdsl2UpboPsdBand,
              vdsl2LConfProfUpboKl		 Unsigned32,
              vdsl2LConfProfUpboKlf		 Vdsl2UpboKlf,
              vdsl2LConfProfRowStatus            RowStatus,         
              vdsl2LConfProfBitSwapDs            Vdsl2BitSwap,
              vdsl2LConfProfBitSwapUs            Vdsl2BitSwap,
              vdsl2LConfProfUpboBoostMode	 Vdsl2UpboBoostMode, 
              vdsl2LConfProfDpboEselMin          Unsigned32,
              vdsl2LConfProfUpboKl0RefBand       Vdsl2UpboKl0RefBand,         
              vdsl2LConfProfReferenceClock       Vdsl2LineClockReferenceType,
              vdsl2LConfProfSosTimeDs            Unsigned32,
              vdsl2LConfProfSosTimeUs            Unsigned32,
              vdsl2LConfProfSosNtonesDs          Unsigned32,
              vdsl2LConfProfSosNtonesUs          Unsigned32,
              vdsl2LConfProfSosCrcDs             Unsigned32,
              vdsl2LConfProfSosCrcUs             Unsigned32,
              vdsl2LConfProfMaxSosDs             Unsigned32,
              vdsl2LConfProfMaxSosUs             Unsigned32, 
              vdsl2LConfProfSnrmoffsetRocDs      Unsigned32,
              vdsl2LConfProfSnrmoffsetRocUs      Unsigned32,
              vdsl2LConfProfInpminRocDs          Unsigned32,
              vdsl2LConfProfInpminRocUs          Unsigned32,
              vdsl2LConfProfInmIatoDs            Unsigned32,     
              vdsl2LConfProfInmIatsDs            Unsigned32,    
              vdsl2LConfProfInmCcDs              Unsigned32,    
              vdsl2LConfProfInmInpeqModeDs       Unsigned32,  
              vdsl2LConfProfInmIatoUs            Unsigned32,     
              vdsl2LConfProfInmIatsUs            Unsigned32,    
              vdsl2LConfProfInmCcUs              Unsigned32,    
              vdsl2LConfProfInmInpeqModeUs       Unsigned32,
              vdsl2LConfProfL3Time               Unsigned32,
              vdsl2LConfProfRtxModeDs            INTEGER,
              vdsl2LConfProfRtxModeUs            INTEGER,
              vdsl2LConfProfLeftrThreshDs        Unsigned32,
              vdsl2LConfProfLeftrThreshUs        Unsigned32,
              vdsl2LConfProfForceInpDs           TruthValue,
              vdsl2LConfProfForceInpUs           TruthValue,
              vdsl2LConfProfAeleMode             Unsigned32,
              vdsl2LConfProfUpboElmt             Unsigned32,
              vdsl2LconfProfUpboKlAuto           Unsigned32
           }
        
        vdsl2LConfProfProfileName  OBJECT-TYPE
            SYNTAX      OCTET STRING (SIZE(1..32))
            MAX-ACCESS  not-accessible
            STATUS      current
            DESCRIPTION
                "This object identifies a row in this table."
            ::= { vdsl2LineConfProfEntry 1 }
            
        vdsl2LConfProfScMaskDs  OBJECT-TYPE
            SYNTAX      Vdsl2ScMaskDs
            MAX-ACCESS  read-create
            STATUS      current
            DESCRIPTION
                "Sub-carriers mask.  A bitmap of 512 bits that allows masking
                 up to 512 downstream sub-carriers, depending on NSCds.  If bit
                 i (0 &lt;= i &lt; NSCds) is set to '1', the respective
                 downstream sub-carrier i is masked, and if set to '0', the
                 respective sub-carrier is unmasked.  Note that there should
                 always be unmasked sub-carriers (i.e., the object cannot be
                 all 1's).  Also note that if NSCds &lt; 512, all bits
                 i (NSCds i &lt;= 512) should be set to '1'.
                "
            REFERENCE    "ITU-T G.997.1, paragraph 7.3.1.2.6"
            ::= { vdsl2LineConfProfEntry 2 }
        
        vdsl2LConfProfScMaskUs  OBJECT-TYPE
            SYNTAX      Vdsl2ScMaskUs
            MAX-ACCESS  read-create
            STATUS      current
            DESCRIPTION
                "Sub-carriers mask.  A bitmap of 64 bits that allows masking
                 up to 64 downstream sub-carriers, depending on NSCds.  If
                 bit i (0 &lt;= i &lt; NSCus) is set to '1', the respective
                 upstream sub-carrier i is masked, and if set to '0', the
                 respective sub-carrier is unmasked.  Note that there
                 should always be unmasked sub-carriers (i.e., the object
                 cannot be all 1's).  Also note that if NSCus &lt;
                 64, all bits i (NSCus &lt; i &lt;= 64) should be set to '1'.
                "
            REFERENCE    "ITU-T G.997.1, paragraph 7.3.1.2.7"
            ::= { vdsl2LineConfProfEntry 3 }
        
        vdsl2LConfProfRfiBands  OBJECT-TYPE
            SYNTAX      OCTET STRING(SIZE(0..159))
            MAX-ACCESS  read-create
            STATUS      current
            DESCRIPTION
                "The subset of PSD mask breakpoints that shall be
                 used to notch an RFI band.
                 It is a string of bands consist of begin tone index
                 and end tone index.
                 for example :0-10,20-50,100-4095
                 It can contain as most as 16 bands.
                "
            REFERENCE    "ITU-T G.997.1(200604), paragraph 7.3.1.2.10"
            ::= { vdsl2LineConfProfEntry 4 }
            
        vdsl2LConfProfVDSLtoneblackout  OBJECT-TYPE
             SYNTAX      OCTET STRING(SIZE(0..79))
             MAX-ACCESS  read-create
             STATUS      current
             DESCRIPTION
                 "The subset of subcarriermask that shall be
                  used to mask the subcarriers.
                  It is a string of bands consist of begin tone index
                  and end tone index.
                  for example :0-10,20-50,100-4095
                  It can contain as most as 8 bands.
                 "
             REFERENCE    "ITU-T G.997.1(200604), paragraph 7.3.1.2.8"
             ::= { vdsl2LineConfProfEntry 5 }     
             
        vdsl2LConfProfRaModeDs  OBJECT-TYPE
            SYNTAX      INTEGER
                        {
                         manual(1),
                         rainit(2),
                         dynamic(3),
                         dynamicwithsos(4)
                        }                            
            MAX-ACCESS  read-create
            STATUS      current
            DESCRIPTION
                "The mode of operation of a rate-adaptive xTU-C in the transmit
                 direction. 
                 Options:          
                 1. manual(1)            - No Rate-Adaptation.  The initialization
                                           process attempts to synchronize to a
                                           specified rate
                 2. rainit(2)            - Rate-Adaptation during initialization process
                                           only, which attempts to synchronize to a rate
                                           between minimum and maximum specified values 
                 3. dynamic(3)           - Rate-Adaptation during show time 
                 4. dynamicwithsos(4)    - Rate-Adaptation during show time by SOS and SRA.
                                           In this mode, enabling of SOS and SRA is mandatory.

                "
            REFERENCE    "ITU-T G.997.1, paragraph 7.3.1.4.1"
            DEFVAL       { raInit }
            ::= { vdsl2LineConfProfEntry 6 }
        
        vdsl2LConfProfRaModeUs  OBJECT-TYPE
            SYNTAX      INTEGER
                        {
                         manual(1),
                         rainit(2),
                         dynamic(3),
                         dynamicwithsos(4)
                        }
            MAX-ACCESS  read-create
            STATUS      current
            DESCRIPTION
                "The mode of operation of a rate-adaptive xTU-R in the transmit
                 direction. 
                 Options:          
                 1. manual(1)            - No Rate-Adaptation.  The initialization
                                           process attempts to synchronize to a
                                           specified rate
                 2. rainit(2)            - Rate-Adaptation during initialization process
                                           only, which attempts to synchronize to a rate
                                           between minimum and maximum specified values
                 3. dynamic(3)           - Rate-Adaptation during show time
                 4. dynamicwithsos(4)    - Rate-Adaptation during show time by SOS and SRA.
                                           In this mode, enabling of SOS and SRA is mandatory.
                "
            REFERENCE    "ITU-T G.997.1, paragraph 7.3.1.4.2"
            DEFVAL       { raInit }
            ::= { vdsl2LineConfProfEntry 7 }
        
        vdsl2LConfProfRaUsNrmDs  OBJECT-TYPE
            SYNTAX      Unsigned32(0..310)
            UNITS       "0.1 dB"
            MAX-ACCESS  read-create
            STATUS      current
            DESCRIPTION
                "The Downstream Up-Shift Noise Margin value, to be used when
                 Vdsl2LineConfRaModeDs is set to DynamicRa.  If the downstream
                 noise margin is above this value and stays above it for
                 more than the time specified by the Vdsl2LineConfRaUsTimeDs,
                 the xTU-R shall attempt to increase the downstream net data
                 rate.  The Downstream Up-shift Noise Margin ranges from 0 to
                 310 units of 0.1 dB (Physical values are 0 to 31 dB).
                 Unit: 0.1 dB
                "
            REFERENCE    "ITU-T G.997.1, paragraph 7.3.1.4.3"
            DEFVAL       { 0 }
            ::= { vdsl2LineConfProfEntry 8 }
        
        vdsl2LConfProfRaUsNrmUs  OBJECT-TYPE
            SYNTAX      Unsigned32(0..310)
            UNITS       "0.1 dB"
            MAX-ACCESS  read-create
            STATUS      current
            DESCRIPTION
                "The Upstream Up-Shift Noise Margin value, to be used when
                 Vdsl2LineConfRaModeUs is set to DynamicRa.  If the upstream
                 noise margin is above this value and stays above it for more
                 than the time specified by the Vdsl2LineConfRaUsTimeUs, the
                 xTU-C shall attempt to increase the upstream net data rate.
                 The Upstream Up-shift Noise Margin ranges from 0 to 310 units
                 of 0.1 dB (Physical values are 0 to 31 dB).
                 Unit: 0.1 dB
                "
            REFERENCE    "ITU-T G.997.1, paragraph 7.3.1.4.4"
            DEFVAL       { 0 }
            ::= { vdsl2LineConfProfEntry 9 }
        
        vdsl2LConfProfRaUsTimeDs  OBJECT-TYPE
            SYNTAX      Unsigned32(0..16383)
            UNITS       "seconds"
            MAX-ACCESS  read-create
            STATUS      current
            DESCRIPTION
                "The Downstream Up-Shift Time Interval, to be used when
                 Vdsl2LineConfRaModeDs is set to DynamicRa.  The interval of
                 time that the downstream noise margin should stay above the
                 Downstream Up-shift Noise Margin before the xTU-R shall
                 attempt to increase the downstream net data rate.  The time
                 interval ranges from 0 to 16383 seconds.
                 Unit: seconds
                "
            REFERENCE    "ITU-T G.997.1, paragraph 7.3.1.4.5"
            DEFVAL       { 0 }
            ::= { vdsl2LineConfProfEntry 10 }
        
        vdsl2LConfProfRaUsTimeUs  OBJECT-TYPE
            SYNTAX      Unsigned32(0..16383)
            UNITS       "seconds"
            MAX-ACCESS  read-create
            STATUS      current
            DESCRIPTION
                "The Upstream Up-Shift Time Interval, to be used when
                 Vdsl2LineConfRaModeUs is set to DynamicRa.  The interval of
                 time the upstream noise margin should stay above the
                 Upstream Up-shift Noise Margin before the xTU-C shall
                 attempt to increase the upstream net data rate.  
                 Unit: seconds
                "
            REFERENCE    "ITU-T G.997.1, paragraph 7.3.1.4.6"
            DEFVAL       { 0 }
            ::= { vdsl2LineConfProfEntry 11 }
            
        vdsl2LConfProfRaDsNrmsDs  OBJECT-TYPE
            SYNTAX      Unsigned32(0..310)
            UNITS       "0.1 dB"
            MAX-ACCESS  read-create
            STATUS      current
            DESCRIPTION
                "The Downstream Down-Shift Noise Margin value, to be used when
                 Vdsl2LineConfRaModeDs is set to DynamicRa.  If the downstream
                 noise margin is below this value and stays below that for more
                 than the time specified by the Vdsl2LineConfRaDsTimeDs, the
                 xTU-R shall attempt to decrease the downstream net data rate.
                 The Downstream Down-shift Noise Margin ranges from 0 to 310
                 units of 0.1 dB (Physical values are 0 to 31 dB).
                 Unit: 0.1 dB
                "
            REFERENCE    "ITU-T G.997.1, paragraph 7.3.1.4.7"
            DEFVAL       { 0 }
            ::= { vdsl2LineConfProfEntry 12 }
            
        vdsl2LConfProfRaDsNrmsUs  OBJECT-TYPE
            SYNTAX      Unsigned32(0..310)
            UNITS       "0.1 dB"
            MAX-ACCESS  read-create
            STATUS      current
            DESCRIPTION
                "The Upstream Downshift Noise Margin value, to be used when
                 Vdsl2LineConfRaModeUs is set to DynamicRa.  If the upstream
                 noise margin is below this value and stays below that for more
                 than the time specified by the Vdsl2LineConfRaDsTimeUs, the
                 xTU-C shall attempt to decrease the upstream net data rate.
                 The Upstream Down-shift Noise Margin ranges from 0 to 310
                 units of 0.1 dB (Physical values are 0 to 31 dB).
                 Unit: 0.1 dB
                "
            REFERENCE    "ITU-T G.997.1, paragraph 7.3.1.4.8"
            DEFVAL       { 0 }
            ::= { vdsl2LineConfProfEntry 13 }
            
        vdsl2LConfProfRaDsTimeDs  OBJECT-TYPE
            SYNTAX      Unsigned32(0..16383)
            UNITS       "seconds"
            MAX-ACCESS  read-create
            STATUS      current
            DESCRIPTION
                "The Downstream Downshift Time Interval, to be used when
                 Vdsl2LineConfRaModeDs is set to DynamicRa.  The interval of
                 time the downstream noise margin should stay below the
                 Downstream Down-shift Noise Margin before the xTU-R shall
                 attempt to decrease the downstream net data rate. 
                 Unit: seconds
                "
            REFERENCE    "ITU-T G.997.1, paragraph 7.3.1.4.9"
            DEFVAL       { 0 }
            ::= { vdsl2LineConfProfEntry 14 }
        
        vdsl2LConfProfRaDsTimeUs  OBJECT-TYPE
            SYNTAX      Unsigned32(0..16383)
            UNITS       "seconds"
            MAX-ACCESS  read-create
            STATUS      current
            DESCRIPTION
                "The Upstream Down-Shift Time Interval, to be used when
                 Vdsl2LineConfRaModeUs is set to DynamicRa.  The interval of
                 time the upstream noise margin should stay below the Upstream
                 Down-shift Noise Margin before the xTU-C shall attempt to
                 decrease the upstream net data rate.  
                 Unit: seconds
                "
            REFERENCE    "ITU-T G.997.1, paragraph 7.3.1.4.10"
            DEFVAL       { 0 }
            ::= { vdsl2LineConfProfEntry 15 }
        
        vdsl2LConfProfTargetSnrmDs  OBJECT-TYPE
            SYNTAX      Unsigned32(0..310)
            UNITS       "0.1 dB"
            MAX-ACCESS  read-create
            STATUS      current
            DESCRIPTION
                "The minimum Noise Margin the xTU-R receiver shall achieve,
                 relative to the BER requirement for each of the downstream
                 bearer channels, to successfully complete initialization.
                 The target noise margin ranges from 0 to 310 units of 0.1 dB
                 (Physical values are 0 to 31 dB).
                 Unit: 0.1 dB
                "
            REFERENCE    "ITU-T G.997.1, paragraph 7.3.1.3.1"
            DEFVAL       { 60 }
            ::= { vdsl2LineConfProfEntry 16 }
        
        vdsl2LConfProfTargetSnrmUs  OBJECT-TYPE
            SYNTAX      Unsigned32(0..310)
            UNITS       "0.1 dB"
            MAX-ACCESS  read-create
            STATUS      current
            DESCRIPTION
                "The minimum Noise Margin the xTU-C receiver shall achieve,
                 relative to the BER requirement for each of the upstream
                 bearer channels, to successfully complete initialization.
                 The target noise margin ranges from 0 to 310 units of 0.1 dB
                 (Physical values are 0 to 31 dB).
                 Unit: 0.1 dB
                "
            REFERENCE    "ITU-T G.997.1, paragraph 7.3.1.3.2"
            DEFVAL       { 60 }
            ::= { vdsl2LineConfProfEntry 17 }
        
        vdsl2LConfProfMaxSnrmDs  OBJECT-TYPE
            SYNTAX      Unsigned32
            UNITS       "0.1 dB"
            MAX-ACCESS  read-create
            STATUS      current
            DESCRIPTION
                "The maximum Noise Margin the xTU-R receiver shall try to
                 sustain. If the Noise Margin is above this level, the xTU-R
                 shall request that the xTU-C reduce the xTU-C transmit power
                 to get a noise margin below this limit (if this functionality
                 is supported).  The maximum noise margin ranges from 0 to 310
                 units of 0.1 dB (Physical values are 0 to 31 dB).  A value of
                 all 1's means that there is no maximum.
                 Unit: 0.1 dB
                "
            REFERENCE    "ITU-T G.997.1, paragraph 7.3.1.3.3"
            DEFVAL       { 300 }
            ::= { vdsl2LineConfProfEntry 18 }
        
        vdsl2LConfProfMaxSnrmUs  OBJECT-TYPE
            SYNTAX      Unsigned32
            UNITS       "0.1 dB"
            MAX-ACCESS  read-create
            STATUS      current
            DESCRIPTION
                "The maximum Noise Margin the xTU-C receiver shall try to
                 sustain. If the Noise Margin is above this level, the xTU-C
                 shall request that the xTU-R reduce the xTU-R transmit power
                 to get a noise margin below this limit (if this functionality
                 is supported).  The maximum noise margin ranges from 0 to 310
                 units of 0.1 dB (Physical values are 0 to 31 dB).  A value of
                 all 1's means that there is no maximum.
                 Unit: 0.1 dB
                "
            REFERENCE    "ITU-T G.997.1, paragraph 7.3.1.3.4"
            DEFVAL       { 300 }
            ::= { vdsl2LineConfProfEntry 19 }
           
        vdsl2LConfProfMinSnrmDs  OBJECT-TYPE
            SYNTAX      Unsigned32(0..310)
            UNITS       "0.1 dB"
            MAX-ACCESS  read-create
            STATUS      current
            DESCRIPTION
                "The minimum Noise Margin the xTU-R receiver shall tolerate.
                 If the noise margin falls below this level, the xTU-R shall
                 request that the xTU-C increase the xTU-C transmit power.
                 If an increase to xTU-C transmit power is not possible, a
                 loss-of-margin (LOM) defect occurs, the xTU-R shall fail and
                 attempt to reinitialize and the NMS shall be notified.  The
                 minimum noise margin ranges from 0 to 310 units of
                 0.1 dB (Physical values are 0 to 31 dB).  A value of 0 means
                 that there is no minimum.
                 Unit: 0.1 dB
                "
            REFERENCE    "ITU-T G.997.1, paragraph 7.3.1.3.5"
            DEFVAL       { 0 }
            ::= { vdsl2LineConfProfEntry 20 }
        
        vdsl2LConfProfMinSnrmUs  OBJECT-TYPE
            SYNTAX      Unsigned32(0..310)
            UNITS       "0.1 dB"
            MAX-ACCESS  read-create
            STATUS      current
            DESCRIPTION
                "The minimum Noise Margin the xTU-C receiver shall tolerate.
                 If the noise margin falls below this level, the xTU-C shall
                 request that the xTU-R increase the xTU-R transmit power.
                 If an increase of xTU-R transmit power is not possible, a
                 loss-of-margin (LOM) defect occurs, the xTU-C shall fail and
                 attempt to re-initialize and the NMS shall be notified.  The
                 minimum noise margin ranges from 0 to 310 units of
                 0.1 dB (Physical values are 0 to 31 dB).  A value of 0 means
                 that there is no minimum.
                 Unit: 0.1 dB
                "
            REFERENCE    "ITU-T G.997.1, paragraph 7.3.1.3.6"
            DEFVAL       { 0 }
            ::= { vdsl2LineConfProfEntry 21 }
        
        vdsl2LConfProfMsgMinUs  OBJECT-TYPE
            SYNTAX      Unsigned32(4000..63000)
            UNITS       "bits/second"
            MAX-ACCESS  read-create
            STATUS      current
            DESCRIPTION
                "Minimum Overhead Rate Upstream.  Defines the minimum rate of
                 the message-based overhead that shall be maintained by the xTU
                 in upstream direction.  Expressed in bits per second and
                 ranges from 4000 to 63000 bps.
                 Unit: bits/second
                "
            REFERENCE    "ITU-T G.997.1, paragraph 7.3.1.5.1"
            DEFVAL       { 4000 }
            ::= { vdsl2LineConfProfEntry 22 }
           
        vdsl2LConfProfMsgMinDs  OBJECT-TYPE
            SYNTAX      Unsigned32(4000..63000)
            UNITS       "bits/second"
            MAX-ACCESS  read-create
            STATUS      current
            DESCRIPTION
                "Minimum Overhead Rate Downstream.  Defines the minimum rate of
                 the message-based overhead that shall be maintained by the xTU
                 in downstream direction.  Expressed in bits per second and
                 ranges from 4000 to 63000 bps.
                 Unit: bits/second
                "
            REFERENCE    "ITU-T G.997.1, paragraph 7.3.1.5.2"
            DEFVAL       { 4000 }
            ::= { vdsl2LineConfProfEntry 23 }
        
        vdsl2LConfProfXtuTransSysEna  OBJECT-TYPE
            SYNTAX      Vdsl2TransmissionModeType
            MAX-ACCESS  read-create
            STATUS      current
            DESCRIPTION
                "xTU Transmission System Enabling (XTSE).  A list of the
                 different coding types enabled in this profile.  It is coded
                 in a bit-map representation with 1 or more bits set.  A bit
                 set to  '1' means that the XTUs may apply the respective
                 coding for the VDSL line.  A bit set to '0' means that
                 the XTUs cannot apply the respective coding for the VDSL
                 line.  All 'reserved' bits should be set to '0'.
                "
            REFERENCE    "ITU-T G.997.1, paragraph 7.3.1.1.1"
            ::= { vdsl2LineConfProfEntry 24 }
        
        vdsl2LConfProfPmMode  OBJECT-TYPE
            SYNTAX      Vdsl2LConfProfPmMode
            MAX-ACCESS  read-create
            STATUS      current
            DESCRIPTION
                "Power management state Enabling.  Defines the power states the
                 xTU-C or xTU-R may autonomously transition to on this line.
                 Options:
                 1. allowTransitionsToIdle (0) 
                 2. allowTransitionsToLowPower (1)  
                 A bit with a '1' value means
                 that the xTU is allowed to transit into the respective state
                 and a '0' value means that the xTU is not allowed
                 to transit into the respective state.
                "
            REFERENCE    "ITU-T G.997.1, paragraph 7.3.1.1.4"
            DEFVAL  { { allowTransitionsToIdle, allowTransitionsToLowPower } }
            ::= { vdsl2LineConfProfEntry 25 }
        
        vdsl2LConfProfL0Time  OBJECT-TYPE
            SYNTAX      Unsigned32 (0..255)
            UNITS       "seconds"
            MAX-ACCESS  read-create
            STATUS      current
            DESCRIPTION
                "This minimum time (in seconds) between an Exit from the L2
                 state and the next Entry into the L2 state. 
                 Unit: seconds
                "
            REFERENCE    "ITU-T G.997.1, paragraph 7.3.1.1.5"
            DEFVAL       { 255 }
            ::= { vdsl2LineConfProfEntry 26 }
        
        vdsl2LConfProfL2Time  OBJECT-TYPE
            SYNTAX      Unsigned32 (0..255)
            UNITS       "seconds"
            MAX-ACCESS  read-create
            STATUS      current
            DESCRIPTION
                "This minimum time (in seconds) between an Entry into the
                 L2 state and the first Power Trim in the L2 state and between
                 two consecutive Power Trims in the L2 State.  
                 Unit: seconds               
                "
            REFERENCE    "ITU-T G.997.1, paragraph 7.3.1.1.6"
            DEFVAL       { 30 }
            ::= { vdsl2LineConfProfEntry 27 }      
        
        vdsl2LConfProfL2Atpr  OBJECT-TYPE
            SYNTAX      Unsigned32 (0..31)
            UNITS       "dB"
            MAX-ACCESS  read-create
            STATUS      current
            DESCRIPTION
                "The maximum aggregate transmit power reduction (in dB) that
                 can be performed at transition of L0 to L2 state or through a
                 single Power Trim in the L2 state.
                 It ranges from 0 dB to 31 dB.
                 Unit: dB
                "
            REFERENCE    "ITU-T G.997.1 (amendment 1), 7.3.1.1.7"
            DEFVAL       { 3 }
            ::= { vdsl2LineConfProfEntry 28 }
            
        vdsl2LConfProfL2Atprt  OBJECT-TYPE
            SYNTAX      Unsigned32 (0..31)
            UNITS       "dB"
            MAX-ACCESS  read-create
            STATUS      current
            DESCRIPTION
                "The total maximum aggregate transmit power reduction
                 (in dB) that can be performed in an L2 state. This is the
                 sum of all reductions of L2 Request (i.e., at transition of
                 L0 to L2 state) and Power Trims.
                 Unit: dB
                "
            REFERENCE    "ITU-T G.997.1 (amendment 1), 7.3.1.1.9"
            DEFVAL       { 9 }
            ::= { vdsl2LineConfProfEntry 29 }    
           
        vdsl2LConfProfDpboEpsd  OBJECT-TYPE
            SYNTAX      Vdsl2DpboEpsd
            MAX-ACCESS  read-create
            STATUS      current
            DESCRIPTION
                "This parameter defines the PSD mask that is assumed to be permitted at the exchange. 
                 This parameter shall use the same format as PSDMASKds.The maximum number of breakpoints 
                 for DPBOEPSD is 16.
                 This is a string of 16 pairs of values in the following
                 structure:
                 Octets 0+1 - Index of 1st sub-carrier used in the context
                              of a first breakpoint.
                 Octet 2    - The PSD reduction for the sub-carrier indicated in
                             octets 0 and 1.
                 Octets 3-5 - Same, for a 2nd breakpoint.
                 Octets 6-8 - Same, for a 3rd breakpoint.
                 This architecture continues until octets 45-47, which are
                 associated with a 16th breakpoint.
                 Each subcarrier index is an unsigned number in the range 1 and
                 NSCds.  Each PSD reduction value is in the range 0 (0dBm/Hz) to
                 255 (-127.5dBm/Hz) with steps of 0.5dBm/Hz.  Valid values are
                 in the range 0 to 190 (0 to -95dBm/Hz).
                 When the number of breakpoints is less than 16, all remaining
                 octets are set to the value 0xff. 
                "
            REFERENCE    "ITU-T G.997.1(200604), paragraph 7.3.1.2.13"         
            ::= { vdsl2LineConfProfEntry 30 }     
              
        vdsl2LConfProfDpboEsel  OBJECT-TYPE
            SYNTAX      Unsigned32 (0..511)
            UNITS       "0.5dB"
            MAX-ACCESS  read-create
            STATUS      current
            DESCRIPTION
                "This configuration parameter defines the assumed electrical length of 
                 cables (E-side cables) connecting exchange based DSL services to a remote
                 flexibility point (cabinet), that hosts the xTU-C that is subject to 
                 spectrally shaped downstream power back-off depending on this length. 
                 For this parameter the electrical length is defined as the loss (in dB) 
                 of an equivalent length of hypothetical cable at a reference frequency 
                 defined by the network operator or in spectrum management regulations. 
                 DPBOESEL shall be coded as an unsigned integer representing an electrical 
                 length from 0 dB (coded as 0) to 255.5 dB (coded as 511) in steps of 0.5 dB. 
                 All values in the range are valid.If DPBOESEL is set to zero, the DPBO in 
                 this section shall be disabled.
                 Unit: 0.5dB
                "
            REFERENCE    "ITU-T G.997.1(200604), paragraph 7.3.1.2.13"
            ::= { vdsl2LineConfProfEntry 31 }        
           
        vdsl2LConfProfDpboEscm  OBJECT-TYPE
            SYNTAX      Vdsl2DpboEscm
            MAX-ACCESS  read-create
            STATUS      current
            DESCRIPTION
                "This configuration parameter defines a cable model in terms of three scalars 
                 DPBOESCMA, DPBOESCMB and DPBOESCMC that shall be used to describe the frequency
                 dependent loss of E-side cables.Parameters DPBOESCMA, DPBOESCMB, DPBOESCMC shall be
                 coded as unsigned integers representing a scalar value from -1 (coded as 0) to 1.5 
                 (coded as 640) in step of 1/256. All values in the range are valid.
                 Octets 0+1 DPBOESCMA
                 Octets 2+3 DPBOESCMB
                 Octets 4+5 DPBOESCMC
                "
            REFERENCE    "ITU-T G.997.1(200604), paragraph 7.3.1.2.13"          
            ::= { vdsl2LineConfProfEntry 32 }       
           
        vdsl2LConfProfDpboMus  OBJECT-TYPE
            SYNTAX      Unsigned32 (0..255)
            UNITS       "-0.5dBm/Hz"
            MAX-ACCESS  read-create
            STATUS      current
            DESCRIPTION
                "DPBOMUS defines the assumed Minimum Usable receive Signal PSD (in dBm/Hz) for 
                 exchange based services, used to modify parameter DPBOFMAX defined below. It 
                 shall be coded as an unsigned integer representing a PSD level from 0 dBm/Hz 
                 (coded as 0) to -127.5 dBm/Hz (coded as 255) in steps of 0.5 dBm/Hz. 
                 All values in the range are valid.
                 Unit: -0.5dBm/Hz
                " 
             REFERENCE    "ITU-T G.997.1(200604), paragraph 7.3.1.2.13"                      
            ::= { vdsl2LineConfProfEntry 33 }   
            
        vdsl2LConfProfDpboFmin  OBJECT-TYPE
            SYNTAX      Unsigned32 (0..2048)
            UNITS       "4.3125 KHz"
            MAX-ACCESS  read-create
            STATUS      current
            DESCRIPTION
                "DPBOFMIN defines the minimum frequency from which the DPBO shall be applied. 
                 It shall be coded as a 16 bits unsigned integer representing a frequency in 
                 multiple of 4.3125 KHz. The range of valid values is from 0 kHz (coded as 0)
                 to 8832 kHz (coded as 2048).
                 Unit: 4.3125 KHz
                "  
            REFERENCE    "ITU-T G.997.1(200604), paragraph 7.3.1.2.13"            
            ::= { vdsl2LineConfProfEntry 34 }        
            
        vdsl2LConfProfDpboFmax  OBJECT-TYPE
            SYNTAX      Unsigned32 (32..6956)
            UNITS       "4.3125 KHz"
            MAX-ACCESS  read-create
            STATUS      current
            DESCRIPTION
                "DPBOFMAX defines the maximum frequency at which DPBO may be applied. It shall be
                 coded as a 16 bits unsigned integer representing a frequency in multiple of 4.3125 KHz. 
                 The range of valid values is from 138 kHz (coded as 32) to 29997.75 kHz (coded as 6956).
                 Unit: 4.3125 KHz
                "  
            REFERENCE    "ITU-T G.997.1(200604), paragraph 7.3.1.2.13"                      
            ::= { vdsl2LineConfProfEntry 35 }     
           
        vdsl2LConfProfUpboPsdBand  OBJECT-TYPE
            SYNTAX      Vdsl2UpboPsdBand
            MAX-ACCESS  read-create
            STATUS      current
            DESCRIPTION
                "This parameter defines the UPBO reference PSD used to compute the upstream power back-off
                 for each upstream band except US0. A UPBOPSD defined for each band shall consist of two 
                 parameters [a, b]. Parameter a shall be coded as an unsigned 12-bit number from 40 dBm/Hz
                 (coded as 0) to 80.95 dBm/Hz (coded as 4095) in steps of 0.01 dBm/Hz; and b shall be coded
                 as an unsigned 12 bit number from 0 (coded as 0) to 40.95 dBm/Hz (coded as 4095) in steps 
                 of 0.01 dBm/Hz. The UPBO reference PSD at the frequency f expressed in MHz shall be equal 
                 to '-a-b(SQRT(f))'. The set of parameter values a = 40 dBm/Hz, b = 0 dBm/Hz is a special configuration
                 to disable UPBO in the respective upstream band.
                 Octets 0+1 -   a[0]
                 Octets 2+3 -   b[0]
                 Octets 4+5 -   a[1]
                 Octets 6+7 -   b[1]
                 Octets 8+9 -   a[2]
                 Octets 10+11 - b[2]
         	 Octets 12+13 - a[3]
                 Octets 14+15 - b[3]
                "
            REFERENCE    "ITU-T G.997.1(200604), paragraph 7.3.1.2.14"                                
            ::= { vdsl2LineConfProfEntry 36 }      
           
        vdsl2LConfProfUpboKl  OBJECT-TYPE
            SYNTAX      Unsigned32 (0..1280)
            UNITS       "0.1 dB"
            MAX-ACCESS  read-create
            STATUS      current
            DESCRIPTION
                "This parameter defines the electrical loop length expressed in dB at 1MHz, kl0, configured by
                 the CO-MIB. The value shall be coded as an unsigned 16 bit number in the range 0 (coded as 0) 
                 to 128 dB (coded as 1280) in steps of 0.1 dB.
                 Unit: 0.1 dB
                "
            REFERENCE    "ITU-T G.997.1(200604), paragraph 7.3.1.2.14"                                          
            ::= { vdsl2LineConfProfEntry 37 }        
           
        vdsl2LConfProfUpboKlf  OBJECT-TYPE
            SYNTAX      Vdsl2UpboKlf
            MAX-ACCESS  read-create
            STATUS      current
            DESCRIPTION
                "This parameter is a flag that forces the VTU-R to use the electrical loop length of the CO-MIB
                 (UPBOKL) to compute the UPBO. The value shall be forced if the flag is set to 1. Otherwise, the
                 electrical loop length shall be autonomously selected by the VTU-O.
                "  
            REFERENCE    "ITU-T G.997.1(200604), paragraph 7.3.1.2.14"                                                    
            ::= { vdsl2LineConfProfEntry 38 }                     
            
        vdsl2LConfProfRowStatus  OBJECT-TYPE
            SYNTAX      RowStatus
            MAX-ACCESS  read-create
            STATUS      current
            DESCRIPTION
                "This object is used to create a new row or to modify or
                 delete an existing row in this table.
                 A profile is activated by setting this object to 'active'.
                 When 'active' is set, the system will validate the profile.
                 Before a profile can be deleted or taken out of service
                 (by setting this object to 'destroy' or 'outOfService'),
                 it must be not referenced from all associated
                 templates.
                "
            ::= { vdsl2LineConfProfEntry 39 } 
           
        vdsl2LConfProfReferenceClock  OBJECT-TYPE
            SYNTAX      Vdsl2LineClockReferenceType 
            MAX-ACCESS  read-create
            STATUS      current
            DESCRIPTION
                "This object configures the clock reference for the ATU-C
                 in a VDSL Line.
                "
            DEFVAL       { freeRun }
            ::= { vdsl2LineConfProfEntry 65534 }
           
        vdsl2LConfProfBitSwapDs  OBJECT-TYPE
            SYNTAX      Vdsl2BitSwap 
            MAX-ACCESS  read-create
            STATUS      current
            DESCRIPTION
                "Enables or disables the bit swap downstream of a line."
            DEFVAL       { enable }
            ::= { vdsl2LineConfProfEntry 65535 }
                  
        vdsl2LConfProfBitSwapUs  OBJECT-TYPE
            SYNTAX      Vdsl2BitSwap 
            MAX-ACCESS  read-create
            STATUS      current
            DESCRIPTION
            	 "Enables or disables the bit swap upstream of a line."
            DEFVAL       { enable }
            ::= { vdsl2LineConfProfEntry 65536 }
        
        vdsl2LConfProfUpboBoostMode  OBJECT-TYPE
            SYNTAX      Vdsl2UpboBoostMode 
            MAX-ACCESS  read-create
            STATUS      current
            DESCRIPTION
            	"Options:
            	 1. disable(1)  - The Equalized FEXT UPBO method is not supported
            	 2. enable(2)   - The Equalized FEXT UPBO method is supported
            	"
            DEFVAL       { enable }
            ::= { vdsl2LineConfProfEntry 65537 }
                 
        vdsl2LConfProfDpboEselMin  OBJECT-TYPE
            SYNTAX      Unsigned32 (0..511)
            UNITS       "0.5dB"
            MAX-ACCESS  read-create
            STATUS      current
            DESCRIPTION
                "DPBOESELMIN in dB is the minimum of all main cable losses for the KVz supplied when using
                 the SOL model (expansion of a KVz and VDSL2 provision of additional KVz areas from this KVz
                 using cross-cables to additional KVz), including the KVz at the MSAN site. This value must 
                 be adjustable as the minimum requirement via the SNMP interface in the configuration profile
                 for each VDSL2 port, and is set individually for each MSAN site and usage. As an option, 
                 As an option, adjustment can be done for each MSAN or line card, thus taking effect for 
                 entire port groups. It is used only for determining the MUF.
                 Unit: 0.5 dB
                "
            ::= { vdsl2LineConfProfEntry 65538 } 
           
        vdsl2LConfProfUpboKl0RefBand  OBJECT-TYPE
            SYNTAX      Vdsl2UpboKl0RefBand
            MAX-ACCESS  read-create
            STATUS      current
            DESCRIPTION
                "Octets 0+1 - length[1]
                 Octets 2+3 - length[2]
                 Octets 4+5 - length[3]
                 Octets 6+7 - length[4] 
                "
            REFERENCE    
                "This parameter defines the UPBO reference electrical length used to compute the 
                 upstream power back-off for each upstream band except US0, for the optional Equalized FEXT UPBO 
                 method. The value ranges from 1.8 to 63.5 dB in steps of 0.1 dB with special value 0.The special 
                 value 0 indicates optional Equalized FEXT UPBO method is not supported.
                "                                
            ::= { vdsl2LineConfProfEntry 65539 }     
                                                          
        vdsl2LConfProfSosTimeDs  OBJECT-TYPE                                               
            SYNTAX      Unsigned32 (0..255)                                                
            UNITS       "64ms"                                                        
            MAX-ACCESS  read-create                                                         
            STATUS      current                                                             
            DESCRIPTION                                                                     
                "The parameter is used in the specification of the receiver initiated SOS. 
                 If the value of this parameter is not zero, the standard SOS triggering criteria are enabled, 
                 and the value corresponds with duration of the time window used in the standard SOS triggering 
                 criteria in the downstream direction.The special value zero, indicates that the standard SOS 
                 triggering criteria are disabled. The valid range of non-zero values is from 64 ms to (255*64) ms 
                 in steps of 64ms.
                 Unit: 64ms
                "                                               
            REFERENCE    "ITU-T G.997.1(200811), paragraph 7.3.1.10.1"                     
            ::= { vdsl2LineConfProfEntry 65540 }  
        
        vdsl2LConfProfSosTimeUs  OBJECT-TYPE                                               
            SYNTAX      Unsigned32 (0..255)                                                
            UNITS       "64ms"                                                        
            MAX-ACCESS  read-create                                                         
            STATUS      current                                                             
            DESCRIPTION                                                                     
                "The parameter is used in the specification of the receiver initiated SOS. 
                 If the value of this parameter is not zero, the standard SOS triggering criteria are enabled, 
                 and the value corresponds with duration of the time window used in the standard SOS triggering 
                 criteria in the upstream direction.The special value zero, indicates that the standard SOS 
                 triggering criteria are disabled. The valid range of non-zero values is from 64 ms to (255*64) ms 
                 in steps of 64ms.
                 Unit: 64ms
                "                                               
            REFERENCE    "ITU-T G.997.1(200811), paragraph 7.3.1.10.2"                     
            ::= { vdsl2LineConfProfEntry 65541 }
        
        vdsl2LConfProfSosNtonesDs  OBJECT-TYPE                                               
            SYNTAX      Unsigned32 (0..100)                                                                                                        
            MAX-ACCESS  read-create                                                         
            STATUS      current                                                             
            DESCRIPTION                                                                     
                "This parameter is defined as the minimum percentage of tones in the downstream MEDLEY SET 
                 that must be degraded in order to arm the first sub-condition of the standard SOS triggering 
                 criteria in the downstream direction. The parameter SOS-NTONES-ds is defined as a percentage of tones. 
                 The valid range of values is from 1 to 100 in steps of 1. A special value of 0 indicates that this
                 parameter is not used in the decision criteria.
                "                                               
            REFERENCE    "ITU-T G.997.1(200811), paragraph 7.3.1.10.3"                     
            ::= { vdsl2LineConfProfEntry 65542 }
        
        vdsl2LConfProfSosNtonesUs  OBJECT-TYPE                                               
            SYNTAX      Unsigned32 (0..100)                                                                                                       
            MAX-ACCESS  read-create                                                         
            STATUS      current                                                             
            DESCRIPTION                                                                     
                "This parameter is defined as the minimum percentage of tones in the upstream MEDLEY SET 
                 that must be degraded in order to arm the first sub-condition of the standard SOS triggering 
                 criteria in the downstream direction. The parameter SOS-NTONES-ds is defined as a percentage of tones. 
                 The valid range of values is from 1 to 100 in steps of 1. A special value of 0 indicates that this
                 parameter is not used in the decision criteria.
                "                                               
            REFERENCE    "ITU-T G.997.1(200811), paragraph 7.3.1.10.4"                     
            ::= { vdsl2LineConfProfEntry 65543 }
        
        vdsl2LConfProfSosCrcDs  OBJECT-TYPE                                               
            SYNTAX      Unsigned32 (1..65535)                                                
            UNITS       "0.02"                                                        
            MAX-ACCESS  read-create                                                         
            STATUS      current                                                             
            DESCRIPTION                                                                     
                "This parameter is defined as the minimum number of normalized CRC anomalies received in SOS-TIME-ds 
                 seconds in order to arm the second sub-condition of the standard SOS triggering criteria  in the 
                 downstream direction. The valid range of SOS-CRC values is 0.02 to 65535*0.02, in steps of 0.02.
                 Unit: 0.02
                "                                               
            REFERENCE    "ITU-T G.997.1(200811), paragraph 7.3.1.10.5"                     
            ::= { vdsl2LineConfProfEntry 65544 }
            
        vdsl2LConfProfSosCrcUs  OBJECT-TYPE                                               
            SYNTAX      Unsigned32 (1..65535)                                                
            UNITS       "0.02"                                                        
            MAX-ACCESS  read-create                                                         
            STATUS      current                                                             
            DESCRIPTION                                                                     
                "This parameter is defined as the minimum number of normalized CRC anomalies received in SOS-TIME-ds 
                 seconds in order to arm the second sub-condition of the standard SOS triggering criteria  in the 
                 upstream direction. The valid range of SOS-CRC values is 0.02 to 65535*0.02, in steps of 0.02.
                 Unit: 0.02
                "                                               
           REFERENCE    "ITU-T G.997.1(200811), paragraph 7.3.1.10.6"                     
           ::= { vdsl2LineConfProfEntry 65545 }
        
        vdsl2LConfProfMaxSosDs  OBJECT-TYPE                                               
            SYNTAX      Unsigned32 (0..15)                                                                                                        
            MAX-ACCESS  read-create                                                         
            STATUS      current                                                             
            DESCRIPTION                                                                     
                "This parameter is used in G.993.2 de-activation. If the number of successful SOS procedures in the 
                 downstream direction performed within a 120-second interval exceeds MAX-SOS-ds, the modem shall transition 
                 to the L3 state. The valid range of values is 1 to 15. A special value of 0 indicates that there is no
                 limit on the maximum allowed number of SOS recoveries within this time interval.
                "                                               
            REFERENCE    "ITU-T G.997.1(200811), paragraph 7.3.1.10.7"                     
            ::= { vdsl2LineConfProfEntry 65546 }
        
        vdsl2LConfProfMaxSosUs  OBJECT-TYPE                                               
            SYNTAX      Unsigned32 (0..15)                                                                                                        
            MAX-ACCESS  read-create                                                         
            STATUS      current                                                             
            DESCRIPTION                                                                     
                "This parameter is used in G.993.2 de-activation. If the number of successful SOS procedures in the 
                 upstream direction performed within a 120-second interval exceeds MAX-SOS-ds, the modem shall transition 
                 to the L3 state. The valid range of values is 1 to 15. A special value of 0 indicates that there is no
                 limit on the maximum allowed number of SOS recoveries within this time interval.
                "                                               
            REFERENCE    "ITU-T G.997.1(200811), paragraph 7.3.1.10.8"                     
            ::= { vdsl2LineConfProfEntry 65547 }
        
        vdsl2LConfProfSnrmoffsetRocDs  OBJECT-TYPE                                               
            SYNTAX      Unsigned32 (0..310)                                                
            UNITS       "0.1dB"                                                        
            MAX-ACCESS  read-create                                                         
            STATUS      current                                                             
            DESCRIPTION                                                                     
                "The parameter is defined as the SNR Margin offset for the ROC channel in the downstream direction.
                 The parameter is used in the specification of the Channel Initialization Policy (see 12.3.7.1/G.993.2).
                 The valid range of SNR margin offset values is from 0 to (310*0.1) dB with 0.1 dB steps.
                 Unit: 0.1dB
                "                                               
            REFERENCE    "ITU-T G.997.1(200811), paragraph 7.3.1.10.9"                     
        ::= { vdsl2LineConfProfEntry 65548 }
        
        vdsl2LConfProfSnrmoffsetRocUs  OBJECT-TYPE                                               
            SYNTAX      Unsigned32 (0..310)                                                
            UNITS       "0.1dB"                                                         
            MAX-ACCESS  read-create                                                         
            STATUS      current                                                             
            DESCRIPTION                                                                     
                "The parameter is defined as the SNR Margin offset for the ROC channel in the upstream direction.
                 The parameter is used in the specification of the Channel Initialization Policy (see 12.3.7.1/G.993.2).
                 The valid range of SNR margin offset values is from 0 to (310*0.1) dB with 0.1 dB steps.
                 Unit: 0.1dB
                "                                               
            REFERENCE    "ITU-T G.997.1(200811), paragraph 7.3.1.10.10"                     
            ::= { vdsl2LineConfProfEntry 65549 }
            
        vdsl2LConfProfInpminRocDs  OBJECT-TYPE                                               
            SYNTAX      Unsigned32 (0..16)                                                                                                      
            MAX-ACCESS  read-create                                                         
            STATUS      current                                                             
            DESCRIPTION                                                                     
                "This parameter contains the minimum impulse noise protection to apply on the ROC in the downstream direction. 
                 The minimum impulse noise protection is an integer ranging from 0 to 16.
                "                                               
            REFERENCE    "ITU-T G.997.1(200811), paragraph 7.3.1.10.11"                     
            ::= { vdsl2LineConfProfEntry 65550 }
        
        vdsl2LConfProfInpminRocUs  OBJECT-TYPE                                               
            SYNTAX      Unsigned32 (0..16)                                                                                                      
            MAX-ACCESS  read-create                                                         
            STATUS      current                                                             
            DESCRIPTION                                                                     
                "This parameter contains the minimum impulse noise protection to apply on the robust ROC in the upstream direction.
                 The minimum impulse noise protection is an integer ranging from 0 to 16.
                "                                               
            REFERENCE    "ITU-T G.997.1(200811), paragraph 7.3.1.10.12"                     
            ::= { vdsl2LineConfProfEntry 65551 }
            
        vdsl2LConfProfInmIatoDs  OBJECT-TYPE
            SYNTAX      Unsigned32(3..511)
            MAX-ACCESS  read-create
            STATUS      current
            DESCRIPTION
                "The parameter of downstream impulse noise monitoring inter arrival time offset.
                 This is the Inter Arrival Time Offset that the xTU receiver shall use to determine 
                 in which bin of the Inter Arrival Time histogram the IAT is reported. 
                 The valid values for INMIATO ranges from 3 to 511 DMT symbols in steps of 1 DMT symbol.
                "
            REFERENCE    "ITU-T G.997.1, paragraph 7.3.1.9.1"
            DEFVAL       { 3 }
            ::= { vdsl2LineConfProfEntry 65552 }
            
        vdsl2LConfProfInmIatsDs  OBJECT-TYPE
            SYNTAX      Unsigned32(0..7)
            MAX-ACCESS  read-create
            STATUS      current
            DESCRIPTION
                "The parameter of downstream impulse noise monitoring inter arrival time step.
                 This is the Inter Arrival Time Step that the xTU receiver shall use to determine 
                 in which bin of the Inter Arrival Time histogram the IAT is reported.
                 The valid values for INMIATS ranges from 0 to 7 in steps of 1.
                "
            REFERENCE    "ITU-T G.997.1, paragraph 7.3.1.9.2"
            DEFVAL       { 0 }
            ::= { vdsl2LineConfProfEntry 65553 }
        
        vdsl2LConfProfInmCcDs  OBJECT-TYPE
            SYNTAX      Unsigned32(0..64)
            MAX-ACCESS  read-create
            STATUS      current
            DESCRIPTION
                "The parameter of Downstream impulse noise monitoring cluster continuation value.
                 This is the Cluster Continuation value that the xTU receiver shall use 
                 in the cluster indication process described in the relevant ITU-T Recommendation. 
                 The valid values for INMCC range from 0 to 64 DMT symbols in steps of 1 DMT symbol.
                "
            REFERENCE    "ITU-T G.997.1, paragraph 7.3.1.9.3"
            DEFVAL       { 0 }
            ::= { vdsl2LineConfProfEntry 65554 }
        
        vdsl2LConfProfInmInpeqModeDs  OBJECT-TYPE
            SYNTAX      Unsigned32(0..4)
            MAX-ACCESS  read-create
            STATUS      current
            DESCRIPTION
                "The parameter of Downstream impulse noise monitoring equivalent impulse noise protect mode.
                 This is the INM Equivalent INP Mode that the xTU receiver shall use in the computation of the Equivalent INP, 
                 as defined in the relevant ITU-T Recommendation. The valid values for INM_INPEQ_MODE are 0, 1, 2, 3, and 4.
                "
            REFERENCE    "ITU-T G.997.1, paragraph 7.3.1.9.4"
            DEFVAL       { 0 }
            ::= { vdsl2LineConfProfEntry 65555 }
            
        vdsl2LConfProfInmIatoUs  OBJECT-TYPE
            SYNTAX      Unsigned32(3..511)
            MAX-ACCESS  read-create
            STATUS      current
            DESCRIPTION
                "The parameter of upstream impulse noise monitoring inter arrival time offset.
                 This is the Inter Arrival Time Offset that the xTU receiver shall use to determine 
                 in which bin of the Inter Arrival Time histogram the IAT is reported. 
                 The valid values for INMIATO ranges from 3 to 511 DMT symbols in steps of 1 DMT symbol.
                "
            REFERENCE    "ITU-T G.997.1, paragraph 7.3.1.9.1"
            DEFVAL       { 3 }
            ::= { vdsl2LineConfProfEntry 65556 }
           
        vdsl2LConfProfInmIatsUs  OBJECT-TYPE
            SYNTAX      Unsigned32(0..7)
            MAX-ACCESS  read-create
            STATUS      current
            DESCRIPTION
                "The parameter of upstream impulse noise monitoring inter arrival time step.
                 This is the Inter Arrival Time Step that the xTU receiver shall use to determine 
                 in which bin of the Inter Arrival Time histogram the IAT is reported.
                 The valid values for INMIATS ranges from 0 to 7 in steps of 1.
                "
            REFERENCE    "ITU-T G.997.1, paragraph 7.3.1.9.2"
            DEFVAL       { 0 }
            ::= { vdsl2LineConfProfEntry 65557 }
            
        vdsl2LConfProfInmCcUs  OBJECT-TYPE
            SYNTAX      Unsigned32(0..64)
            MAX-ACCESS  read-create
            STATUS      current
            DESCRIPTION
                "The parameter of upstream impulse noise monitoring cluster continuation value.
                 This is the Cluster Continuation value that the xTU receiver shall use 
                 in the cluster indication process described in the relevant ITU-T Recommendation. 
                 The valid values for INMCC range from 0 to 64 DMT symbols in steps of 1 DMT symbol.
                "
            REFERENCE    "ITU-T G.997.1, paragraph 7.3.1.9.3"
            DEFVAL       { 0 }
            ::= { vdsl2LineConfProfEntry 65558 }
        
        vdsl2LConfProfInmInpeqModeUs  OBJECT-TYPE
            SYNTAX      Unsigned32(0..4)
            MAX-ACCESS  read-create
            STATUS      current
            DESCRIPTION
                "The parameter of upstream impulse noise monitoring equivalent impulse noise protect mode.
                 This is the INM Equivalent INP Mode that the xTU receiver shall use in the computation of the Equivalent INP, 
                 as defined in the relevant ITU-T Recommendation. The valid values for INM_INPEQ_MODE are 0, 1, 2, 3, and 4.
                "
            REFERENCE    "ITU-T G.997.1, paragraph 7.3.1.9.4"
            DEFVAL       { 0 }
            ::= { vdsl2LineConfProfEntry 65559 }
            
        vdsl2LConfProfL3Time  OBJECT-TYPE
            SYNTAX      Unsigned32 (0..65535)
            UNITS       "seconds"
            MAX-ACCESS  read-create
            STATUS      current
            DESCRIPTION
                "This minimum time (in seconds) between an Entry into the
                 L3 state and the L0 or L2 state.
                 Unit: seconds
                "
            DEFVAL       { 255 }
            ::= { vdsl2LineConfProfEntry 65560 }
        vdsl2LConfProfRtxModeDs  OBJECT-TYPE
            SYNTAX      INTEGER
                        {
                         forbidden(0),
                         preferred(1),
                         forced(2),
                         testmode(3)
                        }            
            MAX-ACCESS  read-create
            STATUS      current
            DESCRIPTION
                "The mode of operation of G.998.4 retransmission in downstream direction. 
                 Options:          
                 1. forbidden(0)    - G.998.4 retransmission not allowed.
                 2. preferred(1)    - G.998.4 retransmission is preferred.
                 3. forced(2)       - Force the use of the G.998.4 retransmission.               
                 4. testmode(3)     - Force the use of the G.998.4 retransmission in test mode.
                "
            REFERENCE    "ITU-T G.997.1, paragraph 7.3.1.11"
            DEFVAL       { forbidden }
            ::= { vdsl2LineConfProfEntry 65561 }
            
        vdsl2LConfProfRtxModeUs  OBJECT-TYPE
            SYNTAX      INTEGER
                        {
                         forbidden(0),
                         preferred(1),
                         forced(2),
                         testmode(3)
                        }            
            MAX-ACCESS  read-create
            STATUS      current
            DESCRIPTION
                "The mode of operation of G.998.4 retransmission in upstream direction. 
                 Options:          
                 1. forbidden(0)    - G.998.4 retransmission not allowed.
                 2. preferred(1)    - G.998.4 retransmission is preferred.
                 3. forced(2)       - Force the use of the G.998.4 retransmission.               
                 4. testmode(3)     - Force the use of the G.998.4 retransmission in test mode.
                "
            REFERENCE    "ITU-T G.997.1, paragraph 7.3.1.11"
            DEFVAL       { forbidden }
            ::= { vdsl2LineConfProfEntry 65562 }            

        vdsl2LConfProfLeftrThreshDs  OBJECT-TYPE
            SYNTAX      Unsigned32(0..99)
            UNITS       "0.01"
            MAX-ACCESS  read-create
            STATUS      current
            DESCRIPTION
                "If retransmission is used in downstream direction, this parameter specifies the 
                 threshold for declaring a near-end leftr defect. The value is coded as a fraction of the 
                 NDR with valid range from 0.01 to 0.99 with increments of 0.01. A special value means the
                 ETR shall be used as the default threshold for declaring a leftr defect.
                "
            REFERENCE    "ITU-T G.997.1, paragraph 7.3.1.12"
            DEFVAL       { 0 }
            ::= { vdsl2LineConfProfEntry 65563 }
            
        vdsl2LConfProfLeftrThreshUs  OBJECT-TYPE
            SYNTAX      Unsigned32(0..99)
            UNITS       "0.01"
            MAX-ACCESS  read-create
            STATUS      current
            DESCRIPTION
                "If retransmission is used in upstream direction, this parameter specifies the 
                 threshold for declaring a near-end leftr defect. The value is coded as a fraction of the 
                 NDR with valid range from 0.01 to 0.99 with increments of 0.01. A special value means the
                 ETR shall be used as the default threshold for declaring a leftr defect.
                "
            REFERENCE    "ITU-T G.997.1, paragraph 7.3.1.12"
            DEFVAL       { 0 }
            ::= { vdsl2LineConfProfEntry 65564 }
            
        vdsl2LConfProfForceInpDs  OBJECT-TYPE
            SYNTAX TruthValue
            MAX-ACCESS  read-create
            STATUS      current
            DESCRIPTION
                "This parameter indicates that the framer settings of the 
                 bearer shall be selected such that the impulse noise protection
                 computed according to the formula specified in the relevant
                 Recommendation is greater or equal to the minimal impulse noise
                 protection requirement.
                 This flag shall have the same value for all the bearers of one
                 line in the same direction.
                "
            REFERENCE    "ITU-T G.997.1, paragraph 7.3.2.5"    
            DEFVAL       { false }
            ::= { vdsl2LineConfProfEntry 65565 }
            
        vdsl2LConfProfForceInpUs  OBJECT-TYPE
            SYNTAX TruthValue
            MAX-ACCESS  read-create
            STATUS      current
            DESCRIPTION
                "This parameter indicates that the framer settings of the 
                 bearer shall be selected such that the impulse noise protection
                 computed according to the formula specified in the relevant
                 Recommendation is greater or equal to the minimal impulse noise
                 protection requirement.
                 This flag shall have the same value for all the bearers of one
                 line in the same direction.
                "
            REFERENCE    "ITU-T G.997.1, paragraph 7.3.2.5"
            DEFVAL       { false }
            ::= { vdsl2LineConfProfEntry 65566 }

        vdsl2LConfProfAeleMode  OBJECT-TYPE
            SYNTAX      Unsigned32(0..3)
            MAX-ACCESS  read-create
            STATUS      current
            DESCRIPTION
                "This parameter defines the UPBO electrical length estimation mode to be used 
                 in the Alternative Electrical Length Estimation method (ELE-M1) in 7.2.1.3.2.2/G.993.2. 
                 The value of this parameter is 0, 1, 2 or 3.
                 0-ELE_M0, 1-ELE_DS, 2-ELE_PB, 3-ELE_MIN
                "
            REFERENCE    "ITU-T G.997.1, paragraph 7.3.1.2.14"
            DEFVAL       { 0 }
            ::= { vdsl2LineConfProfEntry 65567 }
            
        vdsl2LConfProfUpboElmt  OBJECT-TYPE
            SYNTAX      Unsigned32(0..15)
            MAX-ACCESS  read-create
            STATUS      current
            DESCRIPTION
                "This parameter defines the UPBO electrical length minimum threshold percentile 
                 in percent used in the Alternative Electrical Length Estimation method (ELE-M1) 
                 in clause 7.2.1.3.2.2/G.993.2.  It is set by network management via the CO-MIB. 
                 The parameter ranges from 0 to 15 percent in steps of 1 percent.
                 This value is communicated to the VTU-R via G.994.1 at start-up.
                "
            REFERENCE    "ITU-T G.997.1, paragraph 7.3.1.2.14"
            DEFVAL       { 10 }
            ::= { vdsl2LineConfProfEntry 65568 }          

        vdsl2LconfProfUpboKlAuto  OBJECT-TYPE
            SYNTAX      Unsigned32(1..4 | 4294967295)
            MAX-ACCESS  read-create
            STATUS      current
            DESCRIPTION
                "This parameter defines the mode in which kl0 is computed when vdsl2LconfProfUpboKlf is auto.
                 Options:
                 1--max(kl0_CO,kl0_CPE)
                 2--min(kl0_CO,kl0_CPE)
                 3--kl0_CO
                 4--kl0_CPE
                 4294967295--Invalid value
                "
            DEFVAL       { 1 }
            ::= { vdsl2LineConfProfEntry 65569 } 
        --    vdsl2LineConfProfModeSpecTable    
        vdsl2LineConfProfModeSpecTable  OBJECT-TYPE
            SYNTAX      SEQUENCE  OF  Vdsl2LineConfProfModeSpecEntry
            MAX-ACCESS  not-accessible
            STATUS      current
            DESCRIPTION
                "The table vdsl2LineConfProfModeSpecTable extends the
                 VDSL2 line configuration profile by VDSL Mode Specific
                 parameters.
                 A row in this table that has an index of
                 vdsl2LconfProfVdslMode == defMode(1), is called a
                 'mandatory' row.
                 A row in this table that has an index such that
                 vdsl2LconfProfVdslMode is not equal to defMode(1),
                 is called an 'optional' row.
                 When a row in the vdsl2LineConfProfTable table
                 (the parent row) is created, the SNMP agent will
                 automatically create a 'mandatory' row in this table.
                 When the parent row is deleted, the SNMP agent will
                 automatically delete all associated rows in this table.
                 Any attempt to delete the 'mandatory' row using the
                 vdsl2LConfProfModeSpecRowStatus attribute will be
                 rejected by the SNMP agent.
                 The manager MAY create an 'optional' row in this table
                 using the vdsl2LConfProfModeSpecRowStatus attribute if
                 the parent row exists.
                 The manager MAY delete an 'optional' row in this table
                 using the vdsl2LConfProfModeSpecRowStatus attribute at
                 any time.
                 If the actual transmission mode of a DSL line does not
                 match one of the 'optional' rows in this table, then
                 the line will use the PSD configuration from the
                 'mandatory' row. 
                 The indexes of this table are vdsl2LConfProfProfileName 
                 and vdsl2LconfProfVdslMode.
                "
            ::= { vdsl2ProfileLine 3 }
        
        vdsl2LineConfProfModeSpecEntry  OBJECT-TYPE
            SYNTAX      Vdsl2LineConfProfModeSpecEntry
            MAX-ACCESS  not-accessible
            STATUS      current
            DESCRIPTION
                "The table vdsl2LineConfProfModeSpecTable extends the
                 VDSL2 line configuration profile by VDSL Mode Specific
                 parameters. 
                 A row in this table that has an index of
                 vdsl2LconfProfVdslMode == defMode(1), is called a
                 'mandatory' row.
                 A row in this table that has an index such that
                 vdsl2LconfProfVdslMode is not equal to defMode(1),
                 is called an 'optional' row.
                 When a row in the vdsl2LineConfProfTable table
                 (the parent row) is created, the SNMP agent will
                 automatically create a 'mandatory' row in this table.
                 When the parent row is deleted, the SNMP agent will
                 automatically delete all associated rows in this table.
                 Any attempt to delete the 'mandatory' row using the
                 vdsl2LConfProfModeSpecRowStatus attribute will be
                 rejected by the SNMP agent.
                 The manager MAY create an 'optional' row in this table
                 using the vdsl2LConfProfModeSpecRowStatus attribute if
                 the parent row exists.
                 The manager MAY delete an 'optional' row in this table
                 using the vdsl2LConfProfModeSpecRowStatus attribute at
                 any time.
                 If the actual transmission mode of a DSL line does not
                 match one of the 'optional' rows in this table, then
                 the line will use the PSD configuration from the
                 'mandatory' row. 
                 The indexes of this entry are vdsl2LConfProfProfileName 
                 and vdsl2LconfProfVdslMode.
                "
            INDEX  { vdsl2LConfProfProfileName, vdsl2LconfProfVdslMode }
            ::= { vdsl2LineConfProfModeSpecTable 1 }
        
        Vdsl2LineConfProfModeSpecEntry  ::=
            SEQUENCE {
              vdsl2LconfProfVdslMode             Vdsl2OperationModes,
              vdsl2LConfProfMaxNomPsdDs          Integer32,
              vdsl2LConfProfMaxNomPsdUs          Integer32,
              vdsl2LConfProfMaxNomAtpDs          Unsigned32,
              vdsl2LConfProfMaxNomAtpUs          Unsigned32,
              vdsl2LConfProfMaxAggRxPwrUs        Integer32,
              vdsl2LConfProfPsdMaskDs            Vdsl2PsdMaskDs,
              vdsl2LConfProfPsdMaskUs            Vdsl2PsdMaskUs,
              vdsl2LConfProfPsdMaskSelectUs      Unsigned32,
              vdsl2LConfProfPSDClassMask	     Vdsl2PSDClassMask,
              vdsl2LConfProfProfiles		     Vdsl2Profiles,
              vdsl2LConfProfBandOptUsage	     Vdsl2BandOptUsage,
              vdsl2LConfProfModeSpecRowStatus    RowStatus,
              hwVdsl2ConfProfVirtualNoiseModeDs  Vdsl2VirtualNoise,
              hwVdsl2ConfProfVirtualNoiseModeUs  Vdsl2VirtualNoise,
              hwVdsl2ConfProfVirtualNoiseDs      Vdsl2VirtualNoiseDs,
              hwVdsl2ConfProfVirtualNoiseUs      Vdsl2VirtualNoiseUs,
              hwVdsl2ConfProfAutoProfile         Vdsl2AutoProfile
           }
        
        vdsl2LconfProfVdslMode    OBJECT-TYPE
            SYNTAX      Vdsl2OperationModes
            MAX-ACCESS  not-accessible
            STATUS      current
            DESCRIPTION
                "The VDSL Mode is a way of categorizing the various VDSL
                 transmission modes into groups, each group (VDSL Mode) shares
                 the same PSD configuration.
                 There should be multiple entries in this table for a given
                 line profile in case multiple bits are set in
                 vdsl2LConfProfXtuTransSysEna for that profile. 
                "
            REFERENCE    "DSL Forum TR-90, paragraph 5.1.8"
            ::= { vdsl2LineConfProfModeSpecEntry 1 }
        
        vdsl2LConfProfMaxNomPsdDs  OBJECT-TYPE
            SYNTAX      Integer32(-600..-300)
            UNITS       "0.1 dBm/Hz"
            MAX-ACCESS  read-create
            STATUS      current
            DESCRIPTION
                "The maximum nominal transmit PSD in the downstream
                 direction during initialization and Showtime.  It ranges from
                 -600 to -300 units of 0.1 dBm/Hz.  (physical values are -60 to
                 -30 dBm/Hz).  
                 Unit: 0.1 dBm/Hz
                "
            REFERENCE    "ITU-T G.997.1, paragraph 7.3.1.2"
            DEFVAL       { -300 }
            ::= { vdsl2LineConfProfModeSpecEntry 2 }
        
        vdsl2LConfProfMaxNomPsdUs  OBJECT-TYPE
            SYNTAX      Integer32(-600..-300)
            UNITS       "0.1 dBm/Hz"
            MAX-ACCESS  read-create
            STATUS      current
            DESCRIPTION
                "The maximum nominal transmit PSD in the upstream direction
                 during initialization and Showtime.  It ranges from -600 to
                 -300 units of 0.1 dBm/Hz.  (physical values are -60 to
                 -30 dBm/Hz). 
                 Unit: 0.1 dBm/Hz 
                "
            REFERENCE    "ITU-T G.997.1, paragraph 7.3.1.2"
            DEFVAL       { -300 }
            ::= { vdsl2LineConfProfModeSpecEntry 3 }
        
        vdsl2LConfProfMaxNomAtpDs  OBJECT-TYPE
            SYNTAX      Unsigned32 (0..510)
            UNITS       "0.1 dBm"
            MAX-ACCESS  read-create
            STATUS      current
            DESCRIPTION
                "The maximum nominal aggregate transmit power in the
                 downstream direction during initialization and Showtime.  
                 It ranges from 0 to 510 units of 0.1 dBm  (0 to 255 physical 
                 values are 0 to 25.5 dBm, 256 to 510 physical values are 
                 -25.5 to -0.1 dBm).
                 Unit: 0.1 dBm
                "
            REFERENCE    "ITU-T G.997.1, paragraph 7.3.1.2"
            DEFVAL       { 145 }
            ::= { vdsl2LineConfProfModeSpecEntry 4 }
        
        vdsl2LConfProfMaxNomAtpUs  OBJECT-TYPE
            SYNTAX      Unsigned32 (0..510)
            UNITS       "0.1 dBm"
            MAX-ACCESS  read-create
            STATUS      current
            DESCRIPTION
                "The maximum nominal aggregate transmit power in the upstream
                 direction during initialization and Showtime.  
                 It ranges from 0 to 510 units of 0.1 dBm  (0 to 255 physical 
                 values are 0 to 25.5 dBm, 256 to 510 physical values are 
                 -25.5 to -0.1 dBm).
                 Unit: 0.1 dBm
                "
            REFERENCE    "ITU-T G.997.1, paragraph 7.3.1.2"
            DEFVAL       { 145 }
            ::= { vdsl2LineConfProfModeSpecEntry 5 }
        
        vdsl2LConfProfMaxAggRxPwrUs  OBJECT-TYPE
            SYNTAX      Integer32(-255..255)
            UNITS       "0.1 dBm"
            MAX-ACCESS  read-create
            STATUS      current
            DESCRIPTION
                "The maximum upstream aggregate receive power over the relevant
                 set of sub-carriers.  The xTU-C should verify that the
                 upstream power cutback is such that this maximum aggregate
                 receive power value is honored.  It ranges from -255 to 255
                 units of 0.1 dBm (physical values are -25.5 to 25.5 dBm).
                 A value of all means that there is no limit.
                 Unit: 0.1 dBm
                "
            REFERENCE    "ITU-T G.997.1, paragraph 7.3.1.2"
            DEFVAL       { 255 }
            ::= { vdsl2LineConfProfModeSpecEntry 6 }
            
        vdsl2LConfProfPsdMaskDs   OBJECT-TYPE
            SYNTAX      Vdsl2PsdMaskDs
            MAX-ACCESS  read-create
            STATUS      current
            DESCRIPTION
                "This configuration parameter defines the downstream PSD mask 
                 applicable at the U C2 reference point.
                 This MIB PSD mask may impose PSD restrictions in addition 
                 to the Limit PSD mask defined in the relevant Recommendation 
                 (e.g., G.992.5, G.993.2).
                 This is a string of 32 pairs of values in the following
                 structure:
                 Octets 0+1 - Index of 1st sub-carrier used in the context
                              of a first breakpoint.
                 Octet 2    - The PSD reduction for the sub-carrier indicated in
                              octets 0 and 1.
                 Octets 3-5 - Same, for a 2nd breakpoint.
                 Octets 6-8 - Same, for a 3rd breakpoint.
                 This architecture continues until octets 94-95, which are
                 associated with a 32nd breakpoint.
                 Each subcarrier index is an unsigned number in the range 0 and
                 (NSCds - 1).  Each PSD reduction value is in the range 0 (0dBm/Hz) to
                 255 (-127.5dBm/Hz) with steps of 0.5dBm/Hz.  Valid values are
                 in the range 0 to 190 (0 to -95dBm/Hz).
                 When the number of breakpoints is less than 32, all remaining
                 octets are set to the value 0xff.  Note that the content of this
                 object should be correlated with the sub-carriers mask and with
                 the RFI setup. 
                "
            REFERENCE    "ITU-T G.997.1(200604), paragraph 7.3.1.2.9"
            ::= { vdsl2LineConfProfModeSpecEntry 7 }
              
        vdsl2LConfProfPsdMaskUs   OBJECT-TYPE
            SYNTAX      Vdsl2PsdMaskUs
            MAX-ACCESS  read-create
            STATUS      current
            DESCRIPTION
                "This configuration parameter defines the upstream PSD 
                 mask applicable at the U R2 reference point. This MIB 
                 PSD mask may impose PSD restrictions in addition to the 
                 Limit PSD mask defined in the relevant Recommendations 
                 (e.g., ITU-T Recommendations G.992.3, G.993.2).
                 This is a string of 16 pairs of values in the following
                 structure:
                 Octets 0+1 - Index of 1st sub-carrier used in the context
                              of a first breakpoint.
                 Octet 2    - The PSD reduction for the sub-carrier indicated in
                              octets 0 and 1.
                 Octets 3-5 - Same, for a 2nd breakpoint.
                 Octets 45-47 - Same, for a 3rd breakpoint.
                 This architecture continues until octets 45-47, which are
                 associated with a 16th breakpoint.
                 Each subcarrier index is an unsigned number in the range 0 and
                 (NSCus - 1).  Each PSD reduction value is in the range 0 (0dBm/Hz) to
                 255 (-127.5dBm/Hz) with steps of 0.5dBm/Hz.  Valid values are
                 in the range 0 to 190 (0 to -95dBm/Hz).
                 When the number of breakpoints is less than 16, all remaining
                 octets are set to the value 0xff.  Note that the content of this
                 object should be correlated with the sub-carriers mask and with
                 the RFI setup. 
                "
            REFERENCE    "ITU-T G.997.1(200604), paragraph 7.3.1.2.12"
            ::= { vdsl2LineConfProfModeSpecEntry 8 }
        
        vdsl2LConfProfPsdMaskSelectUs  OBJECT-TYPE
            SYNTAX      Unsigned32(0..9)
            MAX-ACCESS  read-create
            STATUS      current
            DESCRIPTION
                "The selected upstream PSD mask. This parameter is used only
                 for annexes J and M of G.992.3 and G.992.5, and the same
                 selection is used for all relevant enabled bits in
                 vdsl2LConfProfXtuTransSysEna.
                 The value is defined as below: 
                 0-Invalid value
                 1-ADLU-32/EU-32       
                 2-ADLU-36/EU-36
                 3-ADLU-40/EU-40       
                 4-ADLU-44/EU-44
                 5-ADLU-48/EU-48       
                 6-ADLU-52/EU-52
                 7-ADLU-56/EU-56       
                 8-ADLU-60/EU-60
                 9-ADLU-64/EU-64
                "
            REFERENCE    "ITU-T G.997.1 (amendment 1), 7.3.1.10"
            ::= { vdsl2LineConfProfModeSpecEntry 9 }
        
        vdsl2LConfProfPSDClassMask  OBJECT-TYPE
            SYNTAX      Vdsl2PSDClassMask
            MAX-ACCESS  read-create
            STATUS      current
            DESCRIPTION
                "In order to reduce the number of configuration possibilities, 
                 the limit PSD masks are grouped in the following PSD mask classes:
                 -  Class 998 Annex A: D-32, D-64.
                 -  Class 997-M1c Annex B: 997-M1c-A-7.
                 -  Class 997-M1x Annex B: 997-M1x-M-8, 997-M1x-M.
                 -  Class 997-M2x Annex B: 997-M2x-M-8, 997-M2x-A, 997-M2x-M.
                 -  Class 998-M1x Annex B: 998-M1x-A, 998-M1x-B, 998-M1x-NUS0.
                 -  Class 998-M2x Annex B: 998-M2x-A, 998-M2x-M, 998-M2x-B, 998-M2x-NUS0.
                 -  Class HPE17 Annex B: HPE17-M1-NUS0.
                 -  Class HPE30 Annex B: HPE30-M1-NUS0.
                 -  Class 997E17-M2x Annex B: 997E17-M2x-NUS0.
                 -  Class 997E30-M2x Annex B: 997E30-M2x-NUS0.
                 -  Class 998E17-M2x Annex B: 998E17-M2x-NUS0, 998E17-M2x-NUS0-M, 998E17-M2x-A.
                 -  Class 998ADE17-M2x Annex B: 998ADE17-M2x-NUS0-M, 998ADE17-M2x-A, 998ADE17-M2x-B.
                 -  Class 998E30-M2x Annex B: 998E30-M2x-NUS0, 998E30-M2x-NUS0-M.
                 -  Class 998ADE30-M2x Annex B: 998ADE30-M2x-NUS0-M, 998ADE30-M2x-NUS0-A.
                 "
            REFERENCE    "ITU-T G.997.1(200604), paragraph 7.3.1.1.12"
            DEFVAL       { 14 }
            ::= { vdsl2LineConfProfModeSpecEntry 10 }
        
        vdsl2LConfProfProfiles  OBJECT-TYPE
            SYNTAX      Vdsl2Profiles
            MAX-ACCESS  read-create
            STATUS      current
            DESCRIPTION
                "This configuration parameter contains the G.993.2 
                 profiles to be allowed by the near-end xTU on this line.
                "
            REFERENCE    "ITU-T G.997.1(200604), paragraph 7.3.1.1.11"
            DEFVAL       { 5 }
             ::= { vdsl2LineConfProfModeSpecEntry 11 }
        
        vdsl2LConfProfBandOptUsage  OBJECT-TYPE
            SYNTAX      Vdsl2BandOptUsage
            MAX-ACCESS  read-create
            STATUS      current
            DESCRIPTION
                "Defines the VDSL link use of the optional frequency
                 range [25kHz - 138kHz] (Opt). 
                 Options:  	  
                 1. unused(1)        - indicates Opt is unused
                 2. used(2)          - indicates Opt usage is for upstream
                 3. invalidValue(-1) -Invalid value
                 Huawei defined.
                "
            DEFVAL       { unused }
            ::= { vdsl2LineConfProfModeSpecEntry 12 }
        
        vdsl2LConfProfModeSpecRowStatus  OBJECT-TYPE
            SYNTAX      RowStatus
            MAX-ACCESS  read-create
            STATUS      current
            DESCRIPTION
                "This object is used to create a new row or to modify or
                 delete an existing row in this table.
                  
                 A profile is activated by setting this object to 'active'.
                 When 'active' is set, the system will validate the profile.
                  
                 Before a profile can be deleted or taken out of service
                 (by setting this object to 'destroy' or 'outOfService'),
                 it must be not referenced from all associated
                 templates.
                "
            ::= { vdsl2LineConfProfModeSpecEntry 13 }
            
        hwVdsl2ConfProfVirtualNoiseModeDs  OBJECT-TYPE
            SYNTAX      Vdsl2VirtualNoise
            MAX-ACCESS  read-create
            STATUS      current
            DESCRIPTION
            	 "This parameter enables the transmitter referred 
            	  virtual noise in the downstream direction. 
            	  If set to 1, the virtual noise is disabled. 
            	  If set to 2, the virtual noise is enabled.
            	 "
            REFERENCE    "ITU-T G.997.1(200604), paragraph 7.3.1.7.1"
            DEFVAL       { disable }
            ::= { vdsl2LineConfProfModeSpecEntry 65535 }
           
        hwVdsl2ConfProfVirtualNoiseModeUs  OBJECT-TYPE
            SYNTAX      Vdsl2VirtualNoise
            MAX-ACCESS  read-create
            STATUS      current
            DESCRIPTION
            	 "This parameter enables the transmitter referred 
            	  virtual noise in the upstream direction. 
            	  If set to 1, the virtual noise is disabled. 
            	  If set to 2, the virtual noise is enabled.
            	 "
            REFERENCE    "ITU-T G.997.1(200604),paragraph 7.3.1.7.2"
            DEFVAL       { disable }
            ::= { vdsl2LineConfProfModeSpecEntry 65536 }
            
        hwVdsl2ConfProfVirtualNoiseDs  OBJECT-TYPE
            SYNTAX      Vdsl2VirtualNoiseDs
            MAX-ACCESS  read-create
            STATUS      current
            DESCRIPTION
                "This configuration parameter defines the downstream 
                 transmitter referred virtual noise (TXREFVNds). 
                 The TXREFVNds shall be specified through a set of breakpoints. 
                 Each breakpoint shall consist of a subcarrier index, 
                 with a subcarrier spacing of 4.3125 kHz, 
                 and a noise PSD level (expressed in dBm/Hz) at that subcarrier. 
                 The set of breakpoints can then be represented as
                 [(t1, PSD1), (t2, PSD2),..., (tN, PSDN)]. 
                 The subcarrier index shall be coded as an unsigned integer. 
                 The noise level shall be coded as an 8-bit unsigned integer 
                 representing the noise level -40 dBm/Hz (coded as 0) to -140 dBm/Hz 
                 (coded as 200), in steps of 0.5 dBm/Hz. 
                 Values from 201 to 255 are special values indicating a noise 
                 level of 0 W/Hz. The maximum number of breakpoints is 32.
                "
            REFERENCE    "ITU-T G.997.1(200604), paragraph 7.3.1.7.3"  
            ::= { vdsl2LineConfProfModeSpecEntry 65537 }
           
        hwVdsl2ConfProfVirtualNoiseUs  OBJECT-TYPE
            SYNTAX      Vdsl2VirtualNoiseUs
            MAX-ACCESS  read-create
            STATUS      current
            DESCRIPTION
                "This configuration parameter defines the upstream 
                 transmitter referred virtual noise (TXREFVNus). 
                 The TXREFVNus shall be specified through a set of breakpoints. 
                 Each breakpoint shall consist of a subcarrier index t, 
                 with a subcarrier spacing of 4.3125 kHz, and a noise PSD level
                 (expressed in dBm/Hz) at that subcarrier. 
                 The set of breakpoints can then be represented as 
                 [(t1, PSD1), (t2, PSD2), ... , (tN, PSDN)]. 
                 The subcarrier index shall be coded as an unsigned integer. 
                 The noise level shall be coded as an 8-bit unsigned integer 
                 representing the noise level -40 dBm/Hz (coded as 0) to -140 dBm/Hz 
                 (coded as 200), in steps of 0.5 dBm/Hz.
                 Values from 201 to 255 are special values indicating 
                 a noise level of 0 W/Hz. The maximum number of breakpoints is 16.
                "
            REFERENCE    "ITU-T G.997.1(200604), paragraph 7.3.1.7.4"
            ::= { vdsl2LineConfProfModeSpecEntry 65538 }
           
        hwVdsl2ConfProfAutoProfile  OBJECT-TYPE
            SYNTAX      Vdsl2AutoProfile
            MAX-ACCESS  read-create
            STATUS      current
            DESCRIPTION
                 "Enable or disable the G.993.2 profiles adaptive function.
                  If set to 1, the G.993.2 profiles adaptive function is disabled. 
            	  If set to 2, the G.993.2 profiles adaptive function is enabled.
            	 "
            REFERENCE    "ITU-T G.997.1(200604), paragraph 7.3.1.1.11"
            DEFVAL       { disable }	 
            ::= { vdsl2LineConfProfModeSpecEntry 65539 }
        
        --        vdsl2ServProfTable          
        vdsl2ServProfTable  OBJECT-TYPE
            SYNTAX      SEQUENCE  OF  Vdsl2ServProfEntry
            MAX-ACCESS  not-accessible
            STATUS      current
            DESCRIPTION
                "The table vdsl2ServProfTable contains xDSL line
                 service configuration.
                 The index of this table is vdsl2ServProfName.  
                 A default profile with an index of 'DEFVAL' will
                 always exist and its parameters will be set to vendor-specific
                 values, unless otherwise specified in this document.
                "
            ::= { vdsl2ProfileTIMode 1 }
        
        vdsl2ServProfEntry  OBJECT-TYPE
            SYNTAX      Vdsl2ServProfEntry
            MAX-ACCESS  not-accessible
            STATUS      current
            DESCRIPTION
                "The table vdsl2ServProfTable contains xDSL line
                 service configuration.
                 The index of this entry is vdsl2ServProfName.
                 A default profile with an index of 'DEFVAL' will
                 always exist and its parameters will be set to vendor-specific
                 values, unless otherwise specified in this document.
                 "
            INDEX  { IMPLIED vdsl2ServProfName }
            ::= { vdsl2ServProfTable 1 }
        
        Vdsl2ServProfEntry  ::=
           SEQUENCE {
              vdsl2ServProfName                     OCTET STRING,
              vdsl2ServProfDataPathMode             Vdsl2DataPathModeType,
              vdsl2ServProfBitSwapEnablingDs        Vdsl2ProfSwitchType,
              vdsl2ServProfBitSwapEnablingUs        Vdsl2ProfSwitchType,
              vdsl2ServProfRaMode                   Vdsl2RaMode,
              vdsl2ServProfCh1Enabling              Vdsl2ChEnabling,
              vdsl2ServProfCh1MinDataRateDs         Unsigned32,
              vdsl2ServProfCh1MinDataRateUs         Unsigned32,
              vdsl2ServProfCh1MinResDataRateDs      Unsigned32,
              vdsl2ServProfCh1MinResDataRateUs      Unsigned32,
              vdsl2ServProfCh1MaxDataRateDs         Unsigned32,
              vdsl2ServProfCh1MaxDataRateUs         Unsigned32,
              vdsl2ServProfCh1MinDataRateLowPwrDs   Unsigned32,
              vdsl2ServProfCh1MinDataRateLowPwrUs   Unsigned32,
              vdsl2ServProfCh1RaRatioDs             Unsigned32,  
              vdsl2ServProfCh1RaRatioUs             Unsigned32,
              vdsl2ServProfCh2Enabling              Vdsl2ChEnabling,
              vdsl2ServProfCh2MinDataRateDs         Unsigned32,
              vdsl2ServProfCh2MinDataRateUs         Unsigned32,
              vdsl2ServProfCh2MinResDataRateDs      Unsigned32,
              vdsl2ServProfCh2MinResDataRateUs      Unsigned32,
              vdsl2ServProfCh2MaxDataRateDs         Unsigned32,
              vdsl2ServProfCh2MaxDataRateUs         Unsigned32,
              vdsl2ServProfCh2MinDataRateLowPwrDs   Unsigned32,
              vdsl2ServProfCh2MinDataRateLowPwrUs   Unsigned32,  
              vdsl2ServProfCh2RaRatioDs             Unsigned32,
              vdsl2ServProfCh2RaRatioUs             Unsigned32,
              vdsl2ServProfRowStatus                RowStatus,
              hwvdsl2ServProfMinEtrRtxDs            Unsigned32,
              hwvdsl2ServProfMinEtrRtxUs            Unsigned32,
              hwvdsl2ServProfMaxEtrRtxDs            Unsigned32,
              hwvdsl2ServProfMaxEtrRtxUs            Unsigned32,
              hwvdsl2ServProfMaxNdrRtxDs            Unsigned32,
              hwvdsl2ServProfMaxNdrRtxUs            Unsigned32
            }
        
        vdsl2ServProfName  OBJECT-TYPE
            SYNTAX      OCTET STRING (SIZE(1..32))
            MAX-ACCESS  not-accessible
            STATUS      current
            DESCRIPTION
                "This object identifies a row in this table."
            ::= { vdsl2ServProfEntry 1 }     
            
        vdsl2ServProfDataPathMode  OBJECT-TYPE
            SYNTAX      Vdsl2DataPathModeType
            MAX-ACCESS  read-create
            STATUS      current
            DESCRIPTION
               "This parameter indicates the VDSL2 line data path modes.  
                Options:
                1. atm (1)   - atm mode
                2. ptm (2)   - ptm mode
               "
            DEFVAL       { ptm }
            ::= { vdsl2ServProfEntry 2 }
           	
         vdsl2ServProfBitSwapEnablingDs  OBJECT-TYPE
             SYNTAX      Vdsl2ProfSwitchType 
             MAX-ACCESS  read-create
             STATUS      current
             DESCRIPTION
                "Enables or disables the bit swap downstream of a line.
                 Options:
                 1. enable(1)       - Enable the bit swap downstream of a line
                 2. disable(2)      - Disable the bit swap downstream of a line
                 huawei defined.
                "
             DEFVAL       { enable }
             ::= { vdsl2ServProfEntry 3 }
                  
         vdsl2ServProfBitSwapEnablingUs  OBJECT-TYPE
             SYNTAX      Vdsl2ProfSwitchType 
             MAX-ACCESS  read-create
             STATUS      current
             DESCRIPTION
             	 "Enables or disables the bit swap upstream of a line.
             	  Options:
             	  1. enable(1)      - Enable the bit swap upstream of a line.
             	  2. disable(2)     - Disable the bit swap upstream of a line.
             	  huawei defined.
             	 "
             DEFVAL       { enable }
             ::= { vdsl2ServProfEntry 4 }   
           
        vdsl2ServProfRaMode  OBJECT-TYPE
            SYNTAX      Vdsl2RaMode
            MAX-ACCESS  read-create
            STATUS      current
            DESCRIPTION
                "The mode of operation of a rate-adaptive xTU-R in the transmit
                 direction.  
                 Options:
                 1. manual (1)           - No Rate-Adaptation.  The initialization
                                           process attempts to synchronize to a
                                           specified rate.
                 2. rainit (2)           - Rate-Adaptation during initialization process
                                           only, which attempts to synchronize to a rate
                                           between minimum and maximum specified values.
                 3. dynamic (3)          - Rate-Adaptation during show time
                "
            REFERENCE    "ITU-T G.997.1, paragraph 7.3.1.4.2"
            DEFVAL       { raInit }
            ::= { vdsl2ServProfEntry 5 }
        
        vdsl2ServProfCh1Enabling  OBJECT-TYPE
            SYNTAX      Vdsl2ChEnabling
            MAX-ACCESS  read-create
            STATUS      current
            DESCRIPTION
                 "This parameter indicates whether the bearer 1 of VDSL2 line is enabling.
             	  Options:
             	  1. enable(1)      - Enable the bearer 1 of VDSL2 line.
             	  2. disable(2)     - Disable the bearer 1 of VDSL2 line.
             	  huawei defined.
                "
            DEFVAL       { enable }
            ::= { vdsl2ServProfEntry 6 }
        
        vdsl2ServProfCh1MinDataRateDs  OBJECT-TYPE
            SYNTAX      Unsigned32(32000..200000000)
            UNITS       "bits/second"
            MAX-ACCESS  read-create
            STATUS      current
            DESCRIPTION
                "If retransmission is not used in downstream direction,this parameter specifics
                 minimum data rate for the bearer channel on downstream direction. coded in bit/s. 
                 Unit: bits/second
                "
            REFERENCE    "ITU-T G.997.1, paragraph 7.3.2.1"
            ::= { vdsl2ServProfEntry 7 }
        
        vdsl2ServProfCh1MinDataRateUs  OBJECT-TYPE
            SYNTAX      Unsigned32(32000..200000000)
            UNITS       "bits/second"
            MAX-ACCESS  read-create
            STATUS      current
            DESCRIPTION
                "If retransmission is not used in upstream direction,this parameter specifics
                 minimum data rate for the bearer channel on upstream direction. coded in bit/s. 
                 Unit: bits/second
                "
            REFERENCE    "ITU-T G.997.1, paragraph 7.3.2.1"
            ::= { vdsl2ServProfEntry 8 }
        
        vdsl2ServProfCh1MinResDataRateDs  OBJECT-TYPE
            SYNTAX      Unsigned32(32000..200000000)
            UNITS       "bits/second"
            MAX-ACCESS  read-create
            STATUS      current
            DESCRIPTION
                "Minimum Reserved Data Rate on Downstream direction.  The
                 minimum reserved net data rate for the bearer channel, coded
                 in bit/s.  This parameter is used only if the Rate Adaptation
                 Mode of the bearer channel (i.e., vdsl2ServProfRaMode) is set 
                 to Dynamic.
                 Unit: bits/second
                "
            REFERENCE    "ITU-T G.997.1, paragraph 7.3.2.1"
            ::= { vdsl2ServProfEntry 9 }
        
        vdsl2ServProfCh1MinResDataRateUs  OBJECT-TYPE
            SYNTAX      Unsigned32(32000..200000000)
            UNITS       "bits/second"
            MAX-ACCESS  read-create
            STATUS      current
            DESCRIPTION
                "Minimum Reserved Data Rate on Upstream direction.  The minimum
                 reserved net data rate for the bearer channel, coded in
                 bit/s.  This parameter is used only if the Rate Adaptation
                 Mode of the bearer channel (i.e., vdsl2ServProfRaMode) is set 
                 to Dynamic.
                 Unit: bits/second
                "
            REFERENCE    "ITU-T G.997.1, paragraph 7.3.2.1"
            ::= { vdsl2ServProfEntry 10 }
            
        vdsl2ServProfCh1MaxDataRateDs  OBJECT-TYPE
            SYNTAX      Unsigned32(32000..200000000)
            UNITS       "bits/second"
            MAX-ACCESS  read-create
            STATUS      current
            DESCRIPTION
                "If retransmission is not used in downstream direction,this parameter specifics
                 maximum data rate for the bearer channel on downstream direction. coded in bit/s. 
                 Unit: bits/second
                "
            REFERENCE    "ITU-T G.997.1, paragraph 7.3.2.1"
            ::= { vdsl2ServProfEntry 11 }
        
        vdsl2ServProfCh1MaxDataRateUs  OBJECT-TYPE
            SYNTAX      Unsigned32(32000..200000000)
            UNITS       "bits/second"
            MAX-ACCESS  read-create
            STATUS      current
            DESCRIPTION
                "If retransmission is not used in upstream direction,this parameter specifics
                 maximum data rate for the bearer channel on upstream direction. coded in bit/s. 
                 Unit: bits/second
                "
            REFERENCE    "ITU-T G.997.1, paragraph 7.3.2.1"
            ::= { vdsl2ServProfEntry 12 }
        
        vdsl2ServProfCh1MinDataRateLowPwrDs  OBJECT-TYPE
            SYNTAX      Unsigned32(32000..200000000)
            UNITS       "bits/second"
            MAX-ACCESS  read-create
            STATUS      current
            DESCRIPTION
                "Minimum Data Rate in Low Power state on Downstream direction.
                 The minimum net data rate for the bearer channel, coded in
                 bit/s., during the low power state (L1 in G.992.2, L2 in
                 G.992.3).
                 Unit: bits/second
                "
            REFERENCE    "ITU-T G.997.1, paragraph 7.3.2.1"
            ::= { vdsl2ServProfEntry 13 }
            
        vdsl2ServProfCh1MinDataRateLowPwrUs  OBJECT-TYPE
            SYNTAX      Unsigned32(32000..200000000)
            UNITS       "bits/second"
            MAX-ACCESS  read-create
            STATUS      current
            DESCRIPTION
                "Minimum Data Rate in Low Power state on Upstream direction.
                 The minimum net data rate for the bearer channel, coded in
                 bit/s, during the low power state (L1 in G.992.2, L2 in
                 G.992.3).
                 Unit: bits/second
                "
            REFERENCE    "ITU-T G.997.1, paragraph 7.3.2.1"
            ::= { vdsl2ServProfEntry 14 }      
           
        vdsl2ServProfCh1RaRatioDs  OBJECT-TYPE
            SYNTAX      Unsigned32(0..100)
            UNITS       "percents"
            MAX-ACCESS  read-create
            STATUS      current
            DESCRIPTION
                "Rate Adaptation Ratio.  The ratio (in %) that should be taken
                 into account for the bearer channel #1 when performing rate
                 adaptation on Downstream.  The ratio refers to the available
                 data rate in excess of the Minimum Data Rate, summed over all
                 bearer channels.  Also, the 100 -
                 vdsl2ServProfCh1RaRatioDs is the ratio of excess data
                 rate to be assigned to all other bearer channels on Downstream
                 direction.  The sum of rate adaptation ratios over all bearers
                 on the same direction shall be equal to 100%.
                 Unit: percents
                "
            REFERENCE    "ITU-T G.997.1, paragraph 7.3.2.1"
            DEFVAL       { 100 }
            ::= { vdsl2ServProfEntry 15 }
        
        vdsl2ServProfCh1RaRatioUs  OBJECT-TYPE
            SYNTAX      Unsigned32(0..100)
            UNITS       "percents"
            MAX-ACCESS  read-create
            STATUS      current
            DESCRIPTION
                "Rate Adaptation Ratio.  The ratio (in %) that should be taken
                 into account for the bearer channel #1 when performing rate
                 adaptation on Upstream.  The ratio refers to the available
                 data rate in excess of the Minimum Data Rate, summed over all
                 bearer channels.  Also, the 100 -
                 vdsl2ServProfCh1RaRatioUs is the ratio of excess data
                 rate to be assigned to all other bearer channels on Upstream
                 direction.  The sum of rate adaptation ratios over all bearers
                 on the same direction shall be equal to 100%.
                 Unit: percents
                "
            REFERENCE    "ITU-T G.997.1, paragraph 7.3.2.1"
            DEFVAL       { 100 }
            ::= { vdsl2ServProfEntry 16 } 
                                             
        vdsl2ServProfCh2Enabling  OBJECT-TYPE
            SYNTAX      Vdsl2ChEnabling
            MAX-ACCESS  read-create
            STATUS      current
            DESCRIPTION
                 "This parameter indicates whether the bearer 2 of VDSL2 line is enabling.
             	  Options:
             	  1. enable(1)      - Enable the bearer 2 of VDSL2 line.
             	  2. disable(2)     - Disable the bearer 2 of VDSL2 line.
             	  huawei defined.
                 "
            DEFVAL       { disable }
            ::= { vdsl2ServProfEntry 17 }
           
        vdsl2ServProfCh2MinDataRateDs  OBJECT-TYPE
            SYNTAX      Unsigned32(32000..200000000)
            UNITS       "bits/second"
            MAX-ACCESS  read-create
            STATUS      current
            DESCRIPTION
                "Minimum Data Rate on Downstream direction.  The minimum net
                 data rate for the bearer channel, coded in bit/s.
                 Unit: bits/second
                "
            REFERENCE    "ITU-T G.997.1, paragraph 7.3.2.1"
            ::= { vdsl2ServProfEntry 18 }
        
        vdsl2ServProfCh2MinDataRateUs  OBJECT-TYPE
            SYNTAX      Unsigned32(32000..200000000)
            UNITS       "bits/second"
            MAX-ACCESS  read-create
            STATUS      current
            DESCRIPTION
                "Minimum Data Rate on Upstream direction.  The minimum net data
                 rate for the bearer channel, coded in bit/s.
                 Unit: bits/second
                "
            REFERENCE    "ITU-T G.997.1, paragraph 7.3.2.1"
            ::= { vdsl2ServProfEntry 19 }
            
        vdsl2ServProfCh2MinResDataRateDs  OBJECT-TYPE
            SYNTAX      Unsigned32(32000..200000000)
            UNITS       "bits/second"
            MAX-ACCESS  read-create
            STATUS      current
            DESCRIPTION
                "Minimum Reserved Data Rate on Downstream direction.  The
                 minimum reserved net data rate for the bearer channel, coded
                 in bit/s.  This parameter is used only if the Rate Adaptation
                 Mode of the bearer channel (i.e., vdsl2ServProfRaMode) is set 
                 to Dynamic.
                 Unit: bits/second
                "
            REFERENCE    "ITU-T G.997.1, paragraph 7.3.2.1"
            ::= { vdsl2ServProfEntry 20 }
        
        vdsl2ServProfCh2MinResDataRateUs  OBJECT-TYPE
            SYNTAX      Unsigned32(32000..200000000)
            UNITS       "bits/second"
            MAX-ACCESS  read-create
            STATUS      current
            DESCRIPTION
                "Minimum Reserved Data Rate on Upstream direction.  The minimum
                 reserved net data rate for the bearer channel, coded in
                 bit/s.  This parameter is used only if the Rate Adaptation
                 Mode of the bearer channel (i.e., vdsl2ServProfRaMode) is set 
                 to Dynamic.
                 Unit: bits/second
                "
            REFERENCE    "ITU-T G.997.1, paragraph 7.3.2.1"
            ::= { vdsl2ServProfEntry 21 }
        
        vdsl2ServProfCh2MaxDataRateDs  OBJECT-TYPE
            SYNTAX      Unsigned32(32000..200000000)
            UNITS       "bits/second"
            MAX-ACCESS  read-create
            STATUS      current
            DESCRIPTION
                "Maximum Data Rate on Downstream direction.  The maximum net
                 data rate for the bearer channel, coded in bit/s.
                 Unit: bits/second
                "
            REFERENCE    "ITU-T G.997.1, paragraph 7.3.2.1"
            ::= { vdsl2ServProfEntry 22 }
        
        vdsl2ServProfCh2MaxDataRateUs  OBJECT-TYPE
            SYNTAX      Unsigned32(32000..200000000)
            UNITS       "bits/second"
            MAX-ACCESS  read-create
            STATUS      current
            DESCRIPTION
                "Maximum Data Rate on Upstream direction.  The maximum net data
                 rate for the bearer channel, coded in bit/s.
                 Unit: bits/second
                "
            REFERENCE    "ITU-T G.997.1, paragraph 7.3.2.1"
            ::= { vdsl2ServProfEntry 23 }
        
        vdsl2ServProfCh2MinDataRateLowPwrDs  OBJECT-TYPE
            SYNTAX      Unsigned32(32000..200000000)
            UNITS       "bits/second"
            MAX-ACCESS  read-create
            STATUS      current
            DESCRIPTION
                "Minimum Data Rate in Low Power state on Downstream direction.
                 The minimum net data rate for the bearer channel, coded in
                 bit/s, during the low power state (L1 in G.992.2, L2 in
                 G.992.3).
                 Unit: bits/second
                "
            REFERENCE    "ITU-T G.997.1, paragraph 7.3.2.1"
            ::= { vdsl2ServProfEntry 24 }
        
        vdsl2ServProfCh2MinDataRateLowPwrUs  OBJECT-TYPE
            SYNTAX      Unsigned32(32000..200000000)
            UNITS       "bits/second"
            MAX-ACCESS  read-create
            STATUS      current
            DESCRIPTION
                "Minimum Data Rate in Low Power state on Upstream direction.
                 The minimum net data rate for the bearer channel, coded in
                 bit/s, during the low power state (L1 in G.992.2, L2 in
                 G.992.3).
                 Unit: bits/second
                "
            REFERENCE    "ITU-T G.997.1, paragraph 7.3.2.1"
            ::= { vdsl2ServProfEntry 25 }   
           
        vdsl2ServProfCh2RaRatioDs  OBJECT-TYPE
            SYNTAX      Unsigned32(0..100)
            UNITS       "percents"
            MAX-ACCESS  read-create
            STATUS      current
            DESCRIPTION
                "Rate Adaptation Ratio.  The ratio (in %) that should be taken
                 into account for the bearer channel #2 when performing rate
                 adaptation on Downstream.  The ratio refers to the available
                 data rate in excess of the Minimum Data Rate, summed over all
                 bearer channels.  Also, the 100 -
                 vdsl2ServProfCh2RaRatioDs is the ratio of excess data
                 rate to be assigned to all other bearer channels on Downstream
                 direction.  The sum of rate adaptation ratios over all bearers
                 on the same direction shall be equal to 100%.
                 Unit: percents
                "
            REFERENCE    "ITU-T G.997.1, paragraph 7.3.2.1"
            DEFVAL       { 0 }
            ::= { vdsl2ServProfEntry 26 }
        
        vdsl2ServProfCh2RaRatioUs  OBJECT-TYPE
            SYNTAX      Unsigned32(0..100)
            UNITS       "percents"
            MAX-ACCESS  read-create
            STATUS      current
            DESCRIPTION
                "Rate Adaptation Ratio.  The ratio (in %) that should be taken
                 into account for the bearer channel #2 when performing rate
                 adaptation on Upstream.  The ratio refers to the available
                 data rate in excess of the Minimum Data Rate, summed over all
                 bearer channels.  Also, the 100 -
                 vdsl2ServProfCh2RaRatioUs is the ratio of excess data
                 rate to be assigned to all other bearer channels on Upstream
                 direction.  The sum of rate adaptation ratios over all bearers
                 on the same direction shall be equal to 100%.
                 Unit: percents
                "
            REFERENCE    "ITU-T G.997.1, paragraph 7.3.2.1"
            DEFVAL       { 0 }
            ::= { vdsl2ServProfEntry 27 }       
        
        vdsl2ServProfRowStatus  OBJECT-TYPE
            SYNTAX      RowStatus
            MAX-ACCESS  read-create
            STATUS      current
            DESCRIPTION
                "This object is used to create a new row or to modify or
                delete an existing row in this table.
                
                A profile is activated by setting this object to 'active'.
                When 'active' is set, the system will validate the profile.
                
                Before a profile can be deleted or taken out of service
                (by setting this object to 'destroy' or 'outOfService'),
                it must be not referenced from all associated
                lines.
               "
            ::= { vdsl2ServProfEntry 28 }     
            
        hwvdsl2ServProfMinEtrRtxDs  OBJECT-TYPE
            SYNTAX      Unsigned32(32000..200000000)
            UNITS       "bits/second"
            MAX-ACCESS  read-create
            STATUS      current
            DESCRIPTION
               "If retransmission is used in downstream direction, this parameter specifies the
                minimum expected throughput for the bearer channel.The values range in steps of 
                1000 bit/s.
               "
            REFERENCE    "ITU-T G.997.1, paragraph 7.3.2.1.8"
            ::= { vdsl2ServProfEntry 29 }            
            
        hwvdsl2ServProfMinEtrRtxUs  OBJECT-TYPE
            SYNTAX      Unsigned32(32000..200000000)
            UNITS       "bits/second"
            MAX-ACCESS  read-create
            STATUS      current
            DESCRIPTION
               "If retransmission is used in upstream direction, this parameter specifies the
                minimum expected throughput for the bearer channel.The values range in steps of 
                1000 bit/s. 
               "
            REFERENCE    "ITU-T G.997.1, paragraph 7.3.2.1.8"
            ::= { vdsl2ServProfEntry 30 }               
            
        hwvdsl2ServProfMaxEtrRtxDs  OBJECT-TYPE
            SYNTAX      Unsigned32(32000..200000000)
            UNITS       "bits/second"
            MAX-ACCESS  read-create
            STATUS      current
            DESCRIPTION
               "If retransmission is used in downstream direction, this parameter specifies the
                maximum expected throughput for the bearer channel.The values range in steps of 
                1000 bit/s. 
               "
            REFERENCE    "ITU-T G.997.1, paragraph 7.3.2.1.9"
            ::= { vdsl2ServProfEntry 31 }            
            
        hwvdsl2ServProfMaxEtrRtxUs  OBJECT-TYPE
            SYNTAX      Unsigned32(32000..200000000)
            UNITS       "bits/second"
            MAX-ACCESS  read-create
            STATUS      current
            DESCRIPTION
               "If retransmission is used in upstream direction, this parameter specifies the
                maximum expected throughput for the bearer channel.The values range in steps of 
                1000 bit/s. 
               "
            REFERENCE    "ITU-T G.997.1, paragraph 7.3.2.1.9"
            ::= { vdsl2ServProfEntry 32 } 
            
        hwvdsl2ServProfMaxNdrRtxDs  OBJECT-TYPE
            SYNTAX      Unsigned32(32000..200000000)
            UNITS       "bits/second"
            MAX-ACCESS  read-create
            STATUS      current
            DESCRIPTION
               "If retransmission is used in downstream direction, this parameter specifies the 
                maximum net data rate for the bearer channel. The values range in steps of 1000 bit/s.
               "
            REFERENCE    "ITU-T G.997.1, paragraph 7.3.2.1.10"
            ::= { vdsl2ServProfEntry 33 }            
            
        hwvdsl2ServProfMaxNdrRtxUs  OBJECT-TYPE
            SYNTAX      Unsigned32(32000..200000000)
            UNITS       "bits/second"
            MAX-ACCESS  read-create
            STATUS      current
            DESCRIPTION
               "If retransmission is used in upstream direction, this parameter specifies the 
                maximum net data rate for the bearer channel.The values range in steps of 1000 bit/s.
               "
            REFERENCE    "ITU-T G.997.1, paragraph 7.3.2.1.10"
            ::= { vdsl2ServProfEntry 34 }      
           
        --        vdsl2SpectrumProfTable              
        vdsl2SpectrumProfTable  OBJECT-TYPE
            SYNTAX      SEQUENCE  OF  Vdsl2SpectrumProfEntry
            MAX-ACCESS  not-accessible
            STATUS      current
            DESCRIPTION
                "The table vdsl2SpectrumProfTable contains VDSL2 line
                 spectrum configuration. 
                 The index of this table is vdsl2SpectrumProfName.  
                 A default profile with an index of 'DEFVAL' will
                 always exist and its parameters will be set to vendor-specific
                 values, unless otherwise specified in this document.
                "
            ::= { vdsl2ProfileTIMode 2 }
        
        vdsl2SpectrumProfEntry  OBJECT-TYPE
            SYNTAX      Vdsl2SpectrumProfEntry
            MAX-ACCESS  not-accessible
            STATUS      current
            DESCRIPTION
                "The table vdsl2SpectrumProfTable contains VDSL2 line
                 spectrum configuration.
                 The index of this entry is vdsl2SpectrumProfName.
                 A default profile with an index of 'DEFVAL' will
                 always exist and its parameters will be set to vendor-specific
                 values, unless otherwise specified in this document.
                "
            INDEX  { IMPLIED vdsl2SpectrumProfName }
            ::= { vdsl2SpectrumProfTable 1 }
           
        Vdsl2SpectrumProfEntry  ::=
            SEQUENCE {
              vdsl2SpectrumProfName              OCTET STRING,
              vdsl2SpectrumProfXtuTransSysEna    Vdsl2TransmissionModeType,
              vdsl2SpectrumProfScMaskDs          Vdsl2ScMaskDs,
              vdsl2SpectrumProfScMaskUs          Vdsl2ScMaskUs,   
              vdsl2SpectrumProfVDSLtoneblackout  OCTET STRING, 
              vdsl2SpectrumProfRfiBands          OCTET STRING,          
              vdsl2SpectrumProfRowStatus         RowStatus,
              hwvdsl2SpectrumProfRtxModeDs       INTEGER,
              hwvdsl2SpectrumProfRtxModeUs       INTEGER,
              hwvdsl2SpectrumProfProfLeftrThreshDs  Unsigned32,
              hwvdsl2SpectrumProfProfLeftrThreshUs  Unsigned32
            }
        
        vdsl2SpectrumProfName  OBJECT-TYPE
            SYNTAX      OCTET STRING (SIZE(1..32))
            MAX-ACCESS  not-accessible
            STATUS      current
            DESCRIPTION
                "This object identifies a row in this table."
            REFERENCE    "DSL Forum TR-90, paragraph 5.1.4"
            ::= { vdsl2SpectrumProfEntry 1 } 
            
        vdsl2SpectrumProfXtuTransSysEna  OBJECT-TYPE
            SYNTAX      Vdsl2TransmissionModeType
            MAX-ACCESS  read-create
            STATUS      current
            DESCRIPTION
                "xTU Transmission System Enabling (xTSE).  A list of the
                 different coding types enabled in this profile.  It is coded
                 in a bit-map representation with 1 or more bits set.  A bit
                 set to  '1' means that the XTUs may apply the respective
                 coding for the VDSL line.  A bit set to '0' means that
                 the XTUs cannot apply the respective coding for the VDSL
                 line.  All 'reserved' bits should be set to '0'.
                "
            REFERENCE    "ITU-T G.997.1, paragraph 7.3.1.1.1"
            ::= { vdsl2SpectrumProfEntry 2 }
        
        vdsl2SpectrumProfScMaskDs  OBJECT-TYPE
            SYNTAX      Vdsl2ScMaskDs
            MAX-ACCESS  read-create
            STATUS      current
            DESCRIPTION
                "Sub-carriers mask.  A bitmap of 512 bits that allows masking
                 up to 512 downstream sub-carriers, depending on NSCds.  If bit
                 i (0 &lt;= i &lt; NSCds) is set to '1', the respective
                 downstream sub-carrier i is masked, and if set to '0', the
                 respective sub-carrier is unmasked.  Note that there should
                 always be unmasked sub-carriers (i.e., the object cannot be
                 all 1's).  Also note that if NSCds &lt; 512, all bits
                 i (NSCds i &lt;= 512) should be set to '1'.
                "
            REFERENCE    "ITU-T G.997.1, paragraph 7.3.1.2.6"
            ::= { vdsl2SpectrumProfEntry 3 }
        
        vdsl2SpectrumProfScMaskUs  OBJECT-TYPE
            SYNTAX      Vdsl2ScMaskUs
            MAX-ACCESS  read-create
            STATUS      current
            DESCRIPTION
                "Sub-carriers mask.  A bitmap of 64 bits that allows masking
                 up to 64 downstream sub-carriers, depending on NSCds.  If
                 bit i (0 &lt;= i &lt; NSCus) is set to '1', the respective
                 upstream sub-carrier i is masked, and if set to '0', the
                 respective sub-carrier is unmasked.  Note that there
                 should always be unmasked sub-carriers (i.e., the object
                 cannot be all 1's).  Also note that if NSCus &lt;
                 64, all bits i (NSCus &lt; i &lt;= 64) should be set to '1'.
                "
            REFERENCE    "ITU-T G.997.1, paragraph 7.3.1.2.7"
            ::= { vdsl2SpectrumProfEntry 4 }
        
        vdsl2SpectrumProfVDSLtoneblackout  OBJECT-TYPE
            SYNTAX      OCTET STRING(SIZE(0..79))
            MAX-ACCESS  read-create
            STATUS      current
            DESCRIPTION
                "The subset of subcarriermask that shall be
                 used to mask the subcarriers.
                 It is a string of bands consist of begin tone index
                 and end tone index.
                 for example :0-10,20-50,100-4095
                 It can contain as most as 8 bands.
                "
            REFERENCE    "ITU-T G.997.1(200604), paragraph 7.3.1.2.8"
            ::= { vdsl2SpectrumProfEntry 5 }    
        
        vdsl2SpectrumProfRfiBands  OBJECT-TYPE
            SYNTAX      OCTET STRING(SIZE(0..159))
            MAX-ACCESS  read-create
            STATUS      current
            DESCRIPTION
                "The subset of PSD mask breakpoints that shall be
                 used to notch an RFI band.
                 It is a string of bands consist of begin tone index
                 and end tone index.
                 for example :0-10,20-50,100-4095
                 It can contain as most as 16 bands.
                "
            REFERENCE    "ITU-T G.997.1(200604), paragraph 7.3.1.2.10"
            ::= { vdsl2SpectrumProfEntry 6 }  
           
        vdsl2SpectrumProfRowStatus  OBJECT-TYPE
            SYNTAX      RowStatus
            MAX-ACCESS  read-create
            STATUS      current
            DESCRIPTION
                "This object is used to create a new row or to modify or
                 delete an existing row in this table.          
                 A profile is activated by setting this object to 'active'.
                 When 'active' is set, the system will validate the profile.          
                 Before a profile can be deleted or taken out of service
                 (by setting this object to 'destroy' or 'outOfService'),
                 it must be not referenced from all associated
                 lines.
                "
            ::= { vdsl2SpectrumProfEntry 7 }  
             
        hwvdsl2SpectrumProfRtxModeDs  OBJECT-TYPE
            SYNTAX      INTEGER
                        {
                         forbidden(0),
                         preferred(1),
                         forced(2),
                         testmode(3)
                        }            
            MAX-ACCESS  read-create
            STATUS      current
            DESCRIPTION
                "The mode of operation of G.998.4 retransmission in downstream direction. 
                 Options:          
                 1. forbidden(0)    - G.998.4 retransmission not allowed.
                 2. preferred(1)    - G.998.4 retransmission is preferred.
                 3. forced(2)       - Force the use of the G.998.4 retransmission.               
                 4. testmode(3)     - Force the use of the G.998.4 retransmission in test mode.
                "
            REFERENCE    "ITU-T G.997.1, paragraph 7.3.1.11"
            DEFVAL       { forbidden }
            ::= { vdsl2SpectrumProfEntry 8 }
            
        hwvdsl2SpectrumProfRtxModeUs  OBJECT-TYPE
            SYNTAX      INTEGER
                        {
                         forbidden(0),
                         preferred(1),
                         forced(2),
                         testmode(3)
                        }            
            MAX-ACCESS  read-create
            STATUS      current
            DESCRIPTION
                "The mode of operation of G.998.4 retransmission in upstream direction. 
                 Options:          
                 1. forbidden(0)    - G.998.4 retransmission not allowed.
                 2. preferred(1)    - G.998.4 retransmission is preferred.
                 3. forced(2)       - Force the use of the G.998.4 retransmission.               
                 4. testmode(3)     - Force the use of the G.998.4 retransmission in test mode.
                "
            REFERENCE    "ITU-T G.997.1, paragraph 7.3.1.11"
            DEFVAL       { forbidden }
            ::= { vdsl2SpectrumProfEntry 9 }            

        hwvdsl2SpectrumProfProfLeftrThreshDs  OBJECT-TYPE
            SYNTAX      Unsigned32(0..99)
            UNITS       "0.01"
            MAX-ACCESS  read-create
            STATUS      current
            DESCRIPTION
                "If retransmission is used in downstream direction, this parameter specifies the 
                 threshold for declaring a near-end leftr defect. The value is coded as a fraction of the 
                 NDR with valid range from 0.01 to 0.99 with increments of 0.01. A special value means the
                 ETR shall be used as the default threshold for declaring a leftr defect.
                "
            REFERENCE    "ITU-T G.997.1, paragraph 7.3.1.12"
            DEFVAL       { 0 }
            ::= { vdsl2SpectrumProfEntry 10 }
            
        hwvdsl2SpectrumProfProfLeftrThreshUs  OBJECT-TYPE
            SYNTAX      Unsigned32(0..99)
            UNITS       "0.01"
            MAX-ACCESS  read-create
            STATUS      current
            DESCRIPTION
                "If retransmission is used in upstream direction, this parameter specifies the 
                 threshold for declaring a near-end leftr defect. The value is coded as a fraction of the 
                 NDR with valid range from 0.01 to 0.99 with increments of 0.01. A special value means the
                 ETR shall be used as the default threshold for declaring a leftr defect.
                "
            REFERENCE    "ITU-T G.997.1, paragraph 7.3.1.12"
            DEFVAL       { 0 }
            ::= { vdsl2SpectrumProfEntry 11 }   
                 
        --    vdsl2SpectrumProfModeSpecTable    
        vdsl2SpectrumProfModeSpecTable  OBJECT-TYPE
            SYNTAX      SEQUENCE  OF  Vdsl2SpectrumProfModeSpecEntry
            MAX-ACCESS  not-accessible
            STATUS      current
            DESCRIPTION
                "The table vdsl2SpectrumProfModeSpecTable extends the
                 VDSL2 line configuration profile by VDSL Mode Specific
                 parameters.
                 A row in this table that has an index of
                 vdsl2LconfProfVdslMode == defMode(1), is called a
                 'mandatory' row.
                 A row in this table that has an index such that
                 vdsl2LconfProfVdslMode is not equal to defMode(1),
                 is called an 'optional' row.
                 When a row in the vdsl2LineConfProfTable table
                 (the parent row) is created, the SNMP agent will
                 automatically create a 'mandatory' row in this table.
                 When the parent row is deleted, the SNMP agent will
                 automatically delete all associated rows in this table.
                 Any attempt to delete the 'mandatory' row using the
                 vdsl2LConfProfModeSpecRowStatus attribute will be
                 rejected by the SNMP agent.
                 The manager MAY create an 'optional' row in this table
                 using the vdsl2LConfProfModeSpecRowStatus attribute if
                 the parent row exists.
                 The manager MAY delete an 'optional' row in this table
                 using the vdsl2LConfProfModeSpecRowStatus attribute at
                 any time.
                 If the actual transmission mode of a DSL line does not
                 match one of the 'optional' rows in this table, then
                 the line will use the PSD configuration from the
                 'mandatory' row.
                 The indexes of this table are vdsl2SpectrumProfName and 
                 vdsl2SpectrumProfXdslMode.
                "
            ::= { vdsl2ProfileTIMode 3 }      
        
        vdsl2SpectrumProfModeSpecEntry  OBJECT-TYPE
            SYNTAX      Vdsl2SpectrumProfModeSpecEntry
            MAX-ACCESS  not-accessible
            STATUS      current
            DESCRIPTION
                "The table vdsl2SpectrumProfModeSpecTable extends the
                 VDSL2 line configuration profile by VDSL Mode Specific
                 parameters. 
                 A row in this table that has an index of
                 vdsl2LconfProfVdslMode == defMode(1), is called a
                 'mandatory' row.
                 A row in this table that has an index such that
                 vdsl2LconfProfVdslMode is not equal to defMode(1),
                 is called an 'optional' row.
                 When a row in the vdsl2LineConfProfTable table
                 (the parent row) is created, the SNMP agent will
                 automatically create a 'mandatory' row in this table.
                 When the parent row is deleted, the SNMP agent will
                 automatically delete all associated rows in this table.
                 Any attempt to delete the 'mandatory' row using the
                 vdsl2LConfProfModeSpecRowStatus attribute will be
                 rejected by the SNMP agent.
                 The manager MAY create an 'optional' row in this table
                 using the vdsl2LConfProfModeSpecRowStatus attribute if
                 the parent row exists.
                 The manager MAY delete an 'optional' row in this table
                 using the vdsl2LConfProfModeSpecRowStatus attribute at
                 any time.
                 If the actual transmission mode of a DSL line does not
                 match one of the 'optional' rows in this table, then
                 the line will use the PSD configuration from the
                 'mandatory' row.
                 The indexes of this entry are vdsl2SpectrumProfName 
                 and vdsl2SpectrumProfXdslMode.
                "
            INDEX  { vdsl2SpectrumProfName, vdsl2SpectrumProfXdslMode }
            ::= { vdsl2SpectrumProfModeSpecTable 1 }
        
        Vdsl2SpectrumProfModeSpecEntry ::=
            SEQUENCE {
              vdsl2SpectrumProfXdslMode             Vdsl2OperationModes,
              vdsl2SpectrumProfMaxNomPsdDs          Integer32,
              vdsl2SpectrumProfMaxNomPsdUs          Integer32,
              vdsl2SpectrumProfMaxNomAtpDs          Unsigned32,
              vdsl2SpectrumProfMaxNomAtpUs          Unsigned32,
              vdsl2SpectrumProfMaxAggRxPwrUs        Integer32,
              vdsl2SpectrumProfPsdMaskDs            Vdsl2PsdMaskDs,
              vdsl2SpectrumProfPsdMaskUs            Vdsl2PsdMaskUs,
              vdsl2SpectrumProfUpsPsdMaskSelection  Vdsl2UpsPsdMaskSelection,
              vdsl2SpectrumProfPmMode               Vdsl2LConfProfPmMode,
              vdsl2SpectrumProfL0Time               Unsigned32,
              vdsl2SpectrumProfL2Time               Unsigned32,
              vdsl2SpectrumProfL2Atpr               Unsigned32,
              vdsl2SpectrumProfL2Atprt              Unsigned32,          
              vdsl2SpectrumProfModeSpecRowStatus    RowStatus
           }                         
        
        vdsl2SpectrumProfXdslMode    OBJECT-TYPE
            SYNTAX      Vdsl2OperationModes
            MAX-ACCESS  not-accessible
            STATUS      current
            DESCRIPTION
                "The xDSL Mode is a way of categorizing the various xDSL
                 transmission modes into groups, each group (xDSL Mode) shares
                 the same PSD configuration.
                 There should be multiple entries in this table for a given
                 line profile in case multiple bits are set in
                 vdsl2LConfProfXtuTransSysEna for that profile. 
                "
            REFERENCE    "DSL Forum TR-90, paragraph 5.1.8"
            ::= { vdsl2SpectrumProfModeSpecEntry 1 }
            
        vdsl2SpectrumProfMaxNomPsdDs  OBJECT-TYPE
            SYNTAX      Integer32(-600..-300)
            UNITS       "0.1 dBm/Hz"
            MAX-ACCESS  read-create
            STATUS      current
            DESCRIPTION
                "The maximum nominal transmit PSD in the downstream
                 direction during initialization and Showtime.  It ranges from
                 -600 to -300 units of 0.1 dBm/Hz.  (physical values are -60 to
                 -30 dBm/Hz).  
                 Unit: 0.1 dBm/Hz
                "
            REFERENCE    "ITU-T G.997.1, paragraph 7.3.1.2"
            DEFVAL       { -400 }
            ::= { vdsl2SpectrumProfModeSpecEntry 2 }
        
        vdsl2SpectrumProfMaxNomPsdUs  OBJECT-TYPE
            SYNTAX      Integer32(-600..-300)
            UNITS       "0.1 dBm/Hz"
            MAX-ACCESS  read-create
            STATUS      current
            DESCRIPTION
                "The maximum nominal transmit PSD in the upstream direction
                 during initialization and Showtime.  It ranges from -600 to
                 -300 units of 0.1 dBm/Hz.  (physical values are -60 to
                 -30 dBm/Hz).  
                 Unit: 0.1 dBm/Hz
                "
            REFERENCE    "ITU-T G.997.1, paragraph 7.3.1.2"
            DEFVAL       { -380 }
            ::= { vdsl2SpectrumProfModeSpecEntry 3 }
        
        vdsl2SpectrumProfMaxNomAtpDs  OBJECT-TYPE
            SYNTAX      Unsigned32 (0..510)
            UNITS       "0.1 dBm"
            MAX-ACCESS  read-create
            STATUS      current
            DESCRIPTION
                "The maximum nominal aggregate transmit power in the
                 downstream direction during initialization and Showtime. It 
                 ranges from 0 to 510 units of 0.1 dBm (0 to 255 physical 
                 values are 0 to 25.5 dBm, 256 to 510 physical values are 
                 -25.5 to -0.1 dBm).
                 Unit: 0.1 dBm
                "
            REFERENCE    "ITU-T G.997.1, paragraph 7.3.1.2"
            DEFVAL       { 200 }
            ::= { vdsl2SpectrumProfModeSpecEntry 4 }
        
        vdsl2SpectrumProfMaxNomAtpUs  OBJECT-TYPE
            SYNTAX      Unsigned32 (0..510)
            UNITS       "0.1 dBm"
            MAX-ACCESS  read-create
            STATUS      current
            DESCRIPTION
               "The maximum nominal aggregate transmit power in the
                 upstream direction during initialization and Showtime. It 
                 ranges from 0 to 510 units of 0.1 dBm (0 to 255 physical 
                 values are 0 to 25.5 dBm, 256 to 510 physical values are 
                 -25.5 to -0.1 dBm).
                 Unit: 0.1 dBm
                "
            REFERENCE    "ITU-T G.997.1, paragraph 7.3.1.2"
            DEFVAL       { 125 }
            ::= { vdsl2SpectrumProfModeSpecEntry 5 }
        
        vdsl2SpectrumProfMaxAggRxPwrUs  OBJECT-TYPE
            SYNTAX      Integer32(-255..255)
            UNITS       "0.1 dBm"
            MAX-ACCESS  read-create
            STATUS      current
            DESCRIPTION
                "The maximum upstream aggregate receive power over the relevant
                 set of sub-carriers.  The xTU-C should verify that the
                 upstream power cutback is such that this maximum aggregate
                 receive power value is honored.  It ranges from -255 to 255
                 units of 0.1 dBm (physical values are -25.5 to 25.5 dBm).
                 A value of all means that there is no limit.
                 Unit: 0.1 dBm
                "
            REFERENCE    "ITU-T G.997.1, paragraph 7.3.1.2"
            DEFVAL       { 125 }
            ::= { vdsl2SpectrumProfModeSpecEntry 6 }
        
        vdsl2SpectrumProfPsdMaskDs   OBJECT-TYPE
            SYNTAX      Vdsl2PsdMaskDs
            MAX-ACCESS  read-create
            STATUS      current
            DESCRIPTION
                "This configuration parameter defines the downstream PSD mask 
                 applicable at the U-C2 reference point.
                 This MIB PSD mask may impose PSD restrictions in addition 
                 to the Limit PSD mask defined in the relevant Recommendation 
                 (e.g., G.992.5, G.993.2).
                 This is a string of 32 pairs of values in the following
                 structure:
                 Octets 0+1 - Index of 1st sub-carrier used in the context
                              of a first breakpoint.
                 Octet 2    - The PSD reduction for the sub-carrier indicated in
                              octets 0 and 1.
                 Octets 3-5 - Same, for a 2nd breakpoint.
                 Octets 6-8 - Same, for a 3rd breakpoint.
                 This architecture continues until octets 94-95, which are
                 associated with a 32nd breakpoint.
                 Each subcarrier index is an unsigned number in the range 0 and
                 (NSCds - 1).  Each PSD reduction value is in the range 0 (0dBm/Hz) to
                 255 (-127.5dBm/Hz) with steps of 0.5dBm/Hz.  Valid values are
                 in the range 0 to 190 (0 to -95dBm/Hz).
                 When the number of breakpoints is less than 32, all remaining
                 octets are set to the value 0xff.  Note that the content of this
                 object should be correlated with the sub-carriers mask and with
                 the RFI setup. 
                "
            REFERENCE    "ITU-T G.997.1(200604), paragraph 7.3.1.2.9"
            ::= { vdsl2SpectrumProfModeSpecEntry 7 }
             
        vdsl2SpectrumProfPsdMaskUs   OBJECT-TYPE
            SYNTAX      Vdsl2PsdMaskUs
            MAX-ACCESS  read-create
            STATUS      current
            DESCRIPTION
                "This configuration parameter defines the upstream PSD 
                 mask applicable at the U R2 reference point. This MIB 
                 PSD mask may impose PSD restrictions in addition to the 
                 Limit PSD mask defined in the relevant Recommendations 
                 (e.g., ITU-T Recommendations G.992.3, G.993.2).
                 This is a string of 16 pairs of values in the following
                 structure:
                 Octets 0+1 - Index of 1st sub-carrier used in the context
                              of a first breakpoint.
                 Octet 2    - The PSD reduction for the sub-carrier indicated in
                              octets 0 and 1.
                 Octets 3-5 - Same, for a 2nd breakpoint.
                 Octets 45-47 - Same, for a 3rd breakpoint.
                 This architecture continues until octets 45-47, which are
                 associated with a 16th breakpoint.
                 Each subcarrier index is an unsigned number in the range 0 and
                 (NSCus - 1).  Each PSD reduction value is in the range 0 (0dBm/Hz) to
                 255 (-127.5dBm/Hz) with steps of 0.5dBm/Hz.  Valid values are
                 in the range 0 to 190 (0 to -95dBm/Hz).
                 When the number of breakpoints is less than 16, all remaining
                 octets are set to the value 0xff.  Note that the content of this
                 object should be correlated with the sub-carriers mask and with
                 the RFI setup. 
                "
            REFERENCE    "ITU-T G.997.1(200604), paragraph 7.3.1.2.12"
            ::= { vdsl2SpectrumProfModeSpecEntry 8 }
             
        vdsl2SpectrumProfUpsPsdMaskSelection    OBJECT-TYPE
            SYNTAX      Vdsl2UpsPsdMaskSelection
            MAX-ACCESS  read-create
            STATUS      current
            DESCRIPTION
                "This configuration parameter defines which upstream PSD mask is enabled. 
                 This parameter is used only for Annexes J and M of ITU T Recs G.992.3 and G.992.5. 
                 As only one selection parameter is defined in the MIB, 
                 the same selection value applies to all relevant modes enabled in the XTSE line configuration parameter. 
                 It ranges from 1 to 9 and selects the mask with the following definition
                 This object is defaulted adlu-32/eu-32. 
                "
            REFERENCE    "ITU-T G.997.1 (amendment 1), 7.3.1.1.10"      
            ::= { vdsl2SpectrumProfModeSpecEntry 9 }        
             
        vdsl2SpectrumProfPmMode  OBJECT-TYPE
            SYNTAX      Vdsl2LConfProfPmMode
            MAX-ACCESS  read-create
            STATUS      current
            DESCRIPTION
                "Power management state Enabling.  Defines the power states the
                 ATU-C or ATU-R may autonomously transition to on this line.
                 Options: 
                 1. allowTransitionsToIdle (0) 
                 2. allowTransitionsToLowPower (1)  
                 A bit with a '1' value means that the ATU is allowed to transit 
                 into the respective state and a '0' value means that the ATU is 
                 not allowed to transit into the respective state.
                "
            REFERENCE    "ITU-T G.997.1, paragraph 7.3.1.1.4"
            DEFVAL  { { allowTransitionsToIdle, allowTransitionsToLowPower } }
            ::= { vdsl2SpectrumProfModeSpecEntry 10 }
        
        vdsl2SpectrumProfL0Time  OBJECT-TYPE
            SYNTAX      Unsigned32 (0..255)
            UNITS       "seconds"
            MAX-ACCESS  read-create
            STATUS      current
            DESCRIPTION
                "This minimum time (in seconds) between an Exit from the L2
                 state and the next Entry into the L2 state.  It ranges from 0
                 to 255 seconds.
                 Unit: seconds
                "
            REFERENCE    "ITU-T G.997.1, paragraph 7.3.1.1.5"
            DEFVAL       { 255 }
            ::= { vdsl2SpectrumProfModeSpecEntry 11 }
        
        vdsl2SpectrumProfL2Time  OBJECT-TYPE
            SYNTAX      Unsigned32 (0..255)
            UNITS       "seconds"
            MAX-ACCESS  read-create
            STATUS      current
            DESCRIPTION
                "This minimum time (in seconds) between an Entry into the
                 L2 state and the first Power Trim in the L2 state and between
                 two consecutive Power Trims in the L2 State.
                 It ranges from 0 to 255 seconds.
                 Unit: seconds
                "
            REFERENCE    "ITU-T G.997.1, paragraph 7.3.1.1.6"
            DEFVAL       { 30 }
            ::= { vdsl2SpectrumProfModeSpecEntry 12 }
        
        vdsl2SpectrumProfL2Atpr  OBJECT-TYPE
            SYNTAX      Unsigned32 (0..31)
            UNITS       "dB"
            MAX-ACCESS  read-create
            STATUS      current
            DESCRIPTION
                "The maximum aggregate transmit power reduction (in dB) that
                 can be performed at transition of L0 to L2 state or through a
                 single Power Trim in the L2 state.
                 Unit: dB
                "
            REFERENCE    "ITU-T G.997.1 (amendment 1), 7.3.1.1.7"
            DEFVAL       { 3 }
            ::= { vdsl2SpectrumProfModeSpecEntry 13 }
        
        vdsl2SpectrumProfL2Atprt  OBJECT-TYPE
            SYNTAX      Unsigned32 (0..31)
            UNITS       "dB"
            MAX-ACCESS  read-create
            STATUS      current
            DESCRIPTION
                "The total maximum aggregate transmit power reduction
                 (in dB) that can be performed in an L2 state. This is the
                 sum of all reductions of L2 Request (i.e., at transition of
                 L0 to L2 state) and Power Trims.
                 Unit: dB
                "
            REFERENCE    "ITU-T G.997.1 (amendment 1), 7.3.1.1.9"
            DEFVAL       { 9 }
            ::= { vdsl2SpectrumProfModeSpecEntry 14 }
        
        vdsl2SpectrumProfModeSpecRowStatus  OBJECT-TYPE
            SYNTAX      RowStatus
            MAX-ACCESS  read-create
            STATUS      current
            DESCRIPTION
                "This object is used to create a new row or to modify or
                 delete an existing row in this table.
                 
                 A profile is activated by setting this object to 'active'.
                 When 'active' is set, the system will validate the profile.
                 
                 Before a profile can be deleted or taken out of service
                 (by setting this object to 'destroy' or 'outOfService'),
                 it must be not referenced from all associated
                 lines.
                "
            ::= { vdsl2SpectrumProfModeSpecEntry 15 }  
           
        --    vdsl2SpectrumProfSubProfTable    
        vdsl2SpectrumProfSubProfTable  OBJECT-TYPE
            SYNTAX      SEQUENCE  OF  Vdsl2SpectrumProfSubProfEntry
            MAX-ACCESS  not-accessible
            STATUS      current
            DESCRIPTION
                "The table vdsl2SpectrumProfSubProfTable extends the
                 VDSL2 line configuration profile by profile parameters.
                 The indexes of this table are vdsl2SpectrumProfName, 
                 vdsl2SpectrumProfXdslMode, and vdsl2SpectrumProfSubProfiles.
                "
            ::= { vdsl2ProfileTIMode 4 }
        
        vdsl2SpectrumProfSubProfEntry  OBJECT-TYPE
            SYNTAX      Vdsl2SpectrumProfSubProfEntry
            MAX-ACCESS  not-accessible
            STATUS      current
            DESCRIPTION
                "The table vdsl2SpectrumProfSubProfTable extends the
                 VDSL2 line configuration profile by profile parameters.
                 The indexes of this entry are vdsl2SpectrumProfName, 
                 vdsl2SpectrumProfXdslMode, and vdsl2SpectrumProfSubProfiles.
                "
            INDEX  { vdsl2SpectrumProfName, vdsl2SpectrumProfXdslMode, vdsl2SpectrumProfSubProfiles}
            ::= { vdsl2SpectrumProfSubProfTable 1 }
        
        Vdsl2SpectrumProfSubProfEntry ::=
            SEQUENCE {
              vdsl2SpectrumProfSubProfiles          Vdsl2SubProfiles,
              vdsl2SpectrumProfSubProfilesWeight    Vdsl2SubProfilesWeight,         
              vdsl2SpectrumProfPsdClassMask         Vdsl2TIPsdClassMask,
              vdsl2SpectrumProfPsdLimitMask         Vdsl2PsdLimitMask,  
              vdsl2SpectrumProfUs0PsdMask           Vdsl2Us0PsdMask,        
              vdsl2SpectrumProfUs0Disable           Vdsl2Us0Disable,         
              vdsl2SpectrumProfSubProfRowStatus     RowStatus
            }                         
        
        vdsl2SpectrumProfSubProfiles    OBJECT-TYPE
            SYNTAX      Vdsl2SubProfiles
            MAX-ACCESS  not-accessible
            STATUS      current
            DESCRIPTION
                "This configuration parameter contains the G.993.2 profiles 
                 to be allowed by the near-end xTU on this line.
                 This object is defaulted Profile17a. 
                "
            REFERENCE    "ITU-T G.997.1 (amendment 1), 7.3.1.1.11"
            
            ::= { vdsl2SpectrumProfSubProfEntry 1 }
           
        vdsl2SpectrumProfSubProfilesWeight    OBJECT-TYPE
            SYNTAX      Vdsl2SubProfilesWeight
            MAX-ACCESS  read-create
            STATUS      current
            DESCRIPTION
                "This configuration parameter contains the G.993.2 profiles' weight 
                 to be allowed by the near-end xTU on this line. This object is defaulted
                 priorityWeight1.
                "
            REFERENCE    "ITU-T G.997.1 (amendment 1), 7.3.1.1.11"           
            ::= { vdsl2SpectrumProfSubProfEntry 2 }
                 
        vdsl2SpectrumProfPsdClassMask    OBJECT-TYPE
            SYNTAX      Vdsl2TIPsdClassMask
            MAX-ACCESS  read-create
            STATUS      current
            DESCRIPTION
                "(CLASSMASK).
                 In order to reduce the number of configuration
                 possibilities, the limit Power Spectral Density masks
                 (see LIMITMASK) are grouped in PSD mask classes.
                 Each class is designed such that the PSD levels of each
                 limit PSD mask of a specific class are equal in their
                 respective passband above 276 kHz.
                 This parameter is defined per VDSL2 Annex enabled in the
                 xdsl2LConfProfXtuTransSysEna object. It selects a single
                 PSD mask class per Annex that is activated at the
                 VTU-O. This object is defaulted  A998/B997M1c/C998.
                "
            REFERENCE    "ITU-T G.997.1, paragraph #7.3.1.1.12"            
            ::= { vdsl2SpectrumProfSubProfEntry 3 }
           
        vdsl2SpectrumProfPsdLimitMask    OBJECT-TYPE
            SYNTAX      Vdsl2PsdLimitMask
            MAX-ACCESS  read-create
            STATUS      current
            DESCRIPTION
                "(LIMITMASK).
                 This configuration parameter contains the G.993.2 limit
                 PSD masks of the selected PSD mask class, enabled by the
                 near-end xTU on this line for each class of profiles.
                 This parameter is defined per VDSL2 Annex enabled in the
                 xdsl2LConfProfXtuTransSysEna object.
                 Through this parameter several limit PSD masks of the
                 selected PSD mask class (xdsl2LConfProfClassMask) may be
                 enabled. The enabling parameter is coded in a bitmap
                 representation (0 if the associated mask is not allowed,
                 1 if it is allowed).This object is defaulted AnnexB998-M2x-B.
                "
            REFERENCE    "ITU-T G.997.1, paragraph #7.3.1.1.13"            
            ::= { vdsl2SpectrumProfSubProfEntry 4 }
                 
        vdsl2SpectrumProfUs0PsdMask    OBJECT-TYPE
            SYNTAX      Vdsl2Us0PsdMask
            MAX-ACCESS  read-create
            STATUS      current
            DESCRIPTION
                "This parameter contains the US0 PSD masks to be allowed by 
                 the near-end xTU on the line. This parameter is only defined for G.993.2 Annex A. 
                 It is represented as a bitmap (0 if not allowed and 1 if allowed) with the following definitions.
                 This object is defaulted ADLU-32/EU-32.
                "
            REFERENCE    "ITU-T G.997.1 (amendment 1), 7.3.1.1.15"               
            ::= { vdsl2SpectrumProfSubProfEntry 5 }       
           
        vdsl2SpectrumProfUs0Disable    OBJECT-TYPE
            SYNTAX      Vdsl2Us0Disable
            MAX-ACCESS  read-create
            STATUS      current
            DESCRIPTION
                "This configuration parameter indicates if the use of US0 is disabled 
                 for each limit PSD mask enabled in the LIMITMASK parameter. This object is defaulted Unused.
                "
            REFERENCE    "ITU-T G.997.1 (amendment 1), 7.3.1.1.14"            
            ::= { vdsl2SpectrumProfSubProfEntry 6 }  
           
        vdsl2SpectrumProfSubProfRowStatus  OBJECT-TYPE
            SYNTAX      RowStatus
            MAX-ACCESS  read-create
            STATUS      current
            DESCRIPTION
                "This object is used to create a new row or to modify or
                 delete an existing row in this table.
                 
                 A profile is activated by setting this object to 'active'.
                 When 'active' is set, the system will validate the profile.
                 
                 Before a profile can be deleted or taken out of service
                 (by setting this object to 'destroy' or 'outOfService'),
                 it must be not referenced from all associated
                 lines.
                "
            ::= { vdsl2SpectrumProfSubProfEntry 7 } 
                                 
        
        --        vdsl2DpboProfTable                      
        vdsl2DpboProfTable  OBJECT-TYPE
            SYNTAX      SEQUENCE  OF  Vdsl2DpboProfEntry
            MAX-ACCESS  not-accessible
            STATUS      current
            DESCRIPTION
                "The table vdsl2DpboProfTable contains VDSL2 DPBO
                 configuration. 
                 The index of this table is vdsl2DpboProfName.   
                 A default profile with an index of 'DEFVAL' will
                 always exist and its parameters will be set to vendor-specific
                 values, unless otherwise specified in this document.   
                "
            ::= { vdsl2ProfileTIMode 5 }
            
        vdsl2DpboProfEntry  OBJECT-TYPE
            SYNTAX      Vdsl2DpboProfEntry
            MAX-ACCESS  not-accessible
            STATUS      current
            DESCRIPTION
                "The table vdsl2DpboProfTable contains VDSL2 DPBO
                 configuration.
                 The index of this entry is vdsl2DpboProfName.
                 A default profile with an index of 'DEFVAL' will
                 always exist and its parameters will be set to vendor-specific
                 values, unless otherwise specified in this document.
                "
            INDEX  { IMPLIED vdsl2DpboProfName }
            ::= { vdsl2DpboProfTable 1 }
        
        Vdsl2DpboProfEntry  ::=
            SEQUENCE {
              vdsl2DpboProfName       OCTET STRING,  
              vdsl2DpboProfWkMdMask   Unsigned32,
              vdsl2DpboProfEpsd       Vdsl2DpboEpsd,
              vdsl2DpboProfEsel       Unsigned32,
              vdsl2DpboProfEscm       Vdsl2DpboEscm,
              vdsl2DpboProfMus	      Unsigned32,
              vdsl2DpboProfFmin	      Unsigned32,
              vdsl2DpboProfFmax	      Unsigned32,
              vdsl2DpboProfRowStatus  RowStatus,
              vdsl2DpboProfEselMin    Unsigned32
            }
        
        vdsl2DpboProfName  OBJECT-TYPE
            SYNTAX      OCTET STRING (SIZE(1..32))
            MAX-ACCESS  not-accessible
            STATUS      current
            DESCRIPTION
                "This object identifies a row in this table."
            REFERENCE    "DSL Forum TR-90, paragraph 5.1.4"
            ::= { vdsl2DpboProfEntry 1 }    
           
        vdsl2DpboProfWkMdMask  OBJECT-TYPE
            SYNTAX      Unsigned32 (0..511)
            MAX-ACCESS  read-create
            STATUS      current
            DESCRIPTION
                "This configuration parameter defines the current enabled DPBO working mode mask.
                 DPBO working mode enabling:1-ADSL, 2-ADSL2+ 3-VDSL2.
                 Options:
                 1. current enabled dpbo work mode:ADSL
                 2. current enabled dpbo work mode:ADSL2+
                 3. current enabled dpbo work mode:ADSL,ADSL2+
                 4. current enabled dpbo work mode:VDSL2
                 5. current enabled dpbo work mode:ADSL,VDSL2
                 6. current enabled dpbo work mode:ADSL2+,VDSL2
                 7. current enabled dpbo work mode:ADSL,ADSL2+,VDSL2 
                "
            DEFVAL       { 7 }
            ::= { vdsl2DpboProfEntry 2 }           
        
        vdsl2DpboProfEpsd  OBJECT-TYPE
            SYNTAX      Vdsl2DpboEpsd
            MAX-ACCESS  read-create
            STATUS      current
            DESCRIPTION
               "This parameter defines the PSD mask that is assumed to be permitted at the exchange. 
                This parameter shall use the same format as PSDMASKds.The maximum number of breakpoints 
                for DPBOEPSD is 16.
                This is a string of 16 pairs of values in the following
                structure:
                Octets 0+1 - Index of 1st sub-carrier used in the context
                             of a first breakpoint.
                Octet 2    - The PSD reduction for the sub-carrier indicated in
                            octets 0 and 1.
                Octets 3-5 - Same, for a 2nd breakpoint.
                Octets 6-8 - Same, for a 3rd breakpoint.
                This architecture continues until octets 45-47, which are
                associated with a 16th breakpoint.
                Each subcarrier index is an unsigned number in the range 1 and
                NSCds.  Each PSD reduction value is in the range 0 (0dBm/Hz) to
                255 (-127.5dBm/Hz) with steps of 0.5dBm/Hz.  Valid values are
                in the range 0 to 190 (0 to -95dBm/Hz).
                When the number of breakpoints is less than 16, all remaining
                octets are set to the value 0xff. 
               "
             REFERENCE    "ITU-T G.997.1(200604), paragraph 7.3.1.2.13"         
            ::= { vdsl2DpboProfEntry 3 }     
               
        vdsl2DpboProfEsel  OBJECT-TYPE
            SYNTAX      Unsigned32 (0..511)
            UNITS       "0.5dB"
            MAX-ACCESS  read-create
            STATUS      current
            DESCRIPTION
               "This configuration parameter defines the assumed electrical length of 
                cables (E-side cables) connecting exchange based DSL services to a remote
                flexibility point (cabinet), that hosts the xTU-C that is subject to 
                spectrally shaped downstream power back-off depending on this length. 
                For this parameter the electrical length is defined as the loss (in dB) 
                of an equivalent length of hypothetical cable at a reference frequency 
                defined by the network operator or in spectrum management regulations. 
                DPBOESEL shall be coded as an unsigned integer representing an electrical 
                length from 0 dB (coded as 0) to 255.5 dB (coded as 511) in steps of 0.5 dB. 
                All values in the range are valid.If DPBOESEL is set to zero, the DPBO in 
                this section shall be disabled.
                Unit: 0.5dB
               "
             REFERENCE    "ITU-T G.997.1(200604), paragraph 7.3.1.2.13"
             DEFVAL       { 0 }
            ::= { vdsl2DpboProfEntry 4 }        
           
        vdsl2DpboProfEscm  OBJECT-TYPE
            SYNTAX      Vdsl2DpboEscm
            MAX-ACCESS  read-create
            STATUS      current
            DESCRIPTION
                "This configuration parameter defines a cable model in terms of three scalars 
                 DPBOESCMA, DPBOESCMB and DPBOESCMC that shall be used to describe the frequency
                 dependent loss of E-side cables.Parameters DPBOESCMA, DPBOESCMB, DPBOESCMC shall be
                 coded as unsigned integers representing a scalar value from -1 (coded as 0) to 1.5 
                 (coded as 640) in step of 1/256. All values in the range are valid.
                 Octets 0+1 DPBOESCMA
                 Octets 2+3 DPBOESCMB
                 Octets 4+5 DPBOESCMC
                "
             REFERENCE    "ITU-T G.997.1(200604), paragraph 7.3.1.2.13"          
            ::= { vdsl2DpboProfEntry 5 }       
           
        vdsl2DpboProfMus  OBJECT-TYPE
            SYNTAX      Unsigned32 (0..255)
            UNITS       "-0.5dBm/Hz"
            MAX-ACCESS  read-create
            STATUS      current
            DESCRIPTION
                "DPBOMUS defines the assumed Minimum Usable receive Signal PSD (in dBm/Hz) for 
                 exchange based services, used to modify parameter DPBOFMAX defined below. It 
                 shall be coded as an unsigned integer representing a PSD level from 0 dBm/Hz 
                 (coded as 0) to -127.5 dBm/Hz (coded as 255) in steps of 0.5 dBm/Hz. 
                 All values in the range are valid.
                 Unit: -0.5dBm/Hz
                " 
             REFERENCE    "ITU-T G.997.1(200604), paragraph 7.3.1.2.13"    
             DEFVAL       { 180 }                  
            ::= { vdsl2DpboProfEntry 6 }   
           
        vdsl2DpboProfFmin  OBJECT-TYPE
            SYNTAX      Unsigned32 (0..2048)
            UNITS       "4.3125 KHz"
            MAX-ACCESS  read-create
            STATUS      current
            DESCRIPTION
                "DPBOFMIN defines the minimum frequency from which the DPBO shall be applied. 
                 It shall be coded as a 16 bits unsigned integer representing a frequency in 
                 multiple of 4.3125 KHz. The range of valid values is from 0 kHz (coded as 0)
                 to 8832 kHz (coded as 2048).
                 Unit: 4.3125 KHz
                "  
             REFERENCE    "ITU-T G.997.1(200604), paragraph 7.3.1.2.13"  
             DEFVAL       { 0 }          
            ::= { vdsl2DpboProfEntry 7 }        
            
        vdsl2DpboProfFmax  OBJECT-TYPE
            SYNTAX      Unsigned32 (32..6956)
            UNITS       "4.3125 KHz"
            MAX-ACCESS  read-create
            STATUS      current
            DESCRIPTION
                "DPBOFMAX defines the maximum frequency at which DPBO may be applied. It shall be
                 coded as a 16 bits unsigned integer representing a frequency in multiple of 4.3125 KHz. 
                 The range of valid values is from 138 kHz (coded as 32) to 29997.75 kHz (coded as 6956).
                 Unit: 4.3125 KHz
                "  
             REFERENCE    "ITU-T G.997.1(200604), paragraph 7.3.1.2.13"  
             DEFVAL       { 511 }                    
            ::= { vdsl2DpboProfEntry 8 }     
        
        vdsl2DpboProfRowStatus  OBJECT-TYPE
            SYNTAX      RowStatus
            MAX-ACCESS  read-create
            STATUS      current
            DESCRIPTION
                "This object is used to create a new row or to modify or
                 delete an existing row in this table.
                 
                 A profile is activated by setting this object to 'active'.
                 When 'active' is set, the system will validate the profile.
                 
                 Before a profile can be deleted or taken out of service
                 (by setting this object to 'destroy' or 'outOfService'),
                 it must be not referenced from all associated
                 lines.
                "
            ::= { vdsl2DpboProfEntry 9 }   
           
        vdsl2DpboProfEselMin  OBJECT-TYPE
            SYNTAX      Unsigned32 (0..511)
            UNITS       "0.5dB"
            MAX-ACCESS  read-create
            STATUS      current
            DESCRIPTION
                "DPBOESELMIN in dB is the minimum of all main cable losses for the KVz supplied when using
                 the SOL model (expansion of a KVz and VDSL2 provision of additional KVz areas from this KVz
                 using cross-cables to additional KVz), including the KVz at the MSAN site. This value must 
                 be adjustable as the minimum requirement via the SNMP interface in the configuration profile
                 for each VDSL2 port, and is set individually for each MSAN site and usage. As an option, 
                 As an option, adjustment can be done for each MSAN or line card, thus taking effect for 
                 entire port groups. It is used only for determining the MUF.
                 Unit: 0.5dB
                "
            ::= { vdsl2DpboProfEntry 65535 } 
        
        --        vdsl2UpboProfTable                  
        vdsl2UpboProfTable  OBJECT-TYPE
            SYNTAX      SEQUENCE  OF  Vdsl2UpboProfEntry
            MAX-ACCESS  not-accessible
            STATUS      current
            DESCRIPTION
                "The table vdsl2UpboProfTable contains VDSL2 upbo
                 configuration. The index of this table is vdsl2UpboProfName.  
                 A default profile with an index of 'DEFVAL' will
                 always exist and its parameters will be set to vendor-specific
                 values, unless otherwise specified in this document.
                "
            ::= { vdsl2ProfileTIMode 6 }
        
        vdsl2UpboProfEntry  OBJECT-TYPE
            SYNTAX      Vdsl2UpboProfEntry
            MAX-ACCESS  not-accessible
            STATUS      current
            DESCRIPTION
                "The table vdsl2UpboProfTable contains VDSL2 upbo
                 configuration . 
                 The index of this entry is vdsl2UpboProfName.
                 A default profile with an index of 'DEFVAL' will
                 always exist and its parameters will be set to vendor-specific
                 values, unless otherwise specified in this document.
                "
            INDEX  { IMPLIED vdsl2UpboProfName }
            ::= { vdsl2UpboProfTable 1 }
        
        Vdsl2UpboProfEntry  ::=
            SEQUENCE {
              vdsl2UpboProfName        OCTET STRING,
              vdsl2UpboProfPsdBand     Vdsl2UpboPsdBand,
              vdsl2UpboProfKl          Unsigned32,
              vdsl2UpboProfKlf         Vdsl2UpboKlf,
              vdsl2UpboProfKlAuto 	   Unsigned32,
              vdsl2UpboProfRowStatus   RowStatus,
              vdsl2UpboProfBoostMode   Vdsl2UpboBoostMode, 
              vdsl2UpboProfKl0RefBand  Vdsl2UpboKl0RefBand
            }
        
        vdsl2UpboProfName  OBJECT-TYPE
            SYNTAX      OCTET STRING (SIZE(1..32))
            MAX-ACCESS  not-accessible
            STATUS      current
            DESCRIPTION
                "This object identifies a row in this table."
            REFERENCE    "DSL Forum TR-90, paragraph 5.1.4"
            ::= { vdsl2UpboProfEntry 1 }  
            
        vdsl2UpboProfPsdBand  OBJECT-TYPE
            SYNTAX      Vdsl2UpboPsdBand
            MAX-ACCESS  read-create
            STATUS      current
            DESCRIPTION
                "This parameter defines the UPBO reference PSD used to compute the upstream power back-off
                 for each upstream band. A UPBOPSD defined for each band shall consist of two 
                 parameters [a, b]. Parameter a shall be coded as an unsigned 12-bit number from 40 dBm/Hz
                 (coded as 0) to 80.95 dBm/Hz (coded as 4095) in steps of 0.01 dBm/Hz; and b shall be coded
                 as an unsigned 12 bit number from 0 (coded as 0) to 40.95 dBm/Hz (coded as 4095) in steps 
                 of 0.01 dBm/Hz. The UPBO reference PSD at the frequency f expressed in MHz shall be equal 
                 to '-a-b(SQRT(f))'. The set of parameter values a = 40 dBm/Hz, b = 0 dBm/Hz is a special configuration
                 to disable UPBO in the respective upstream band.
                 Octets 0+1 -   a[0]
                 Octets 2+3 -   b[0]
                 Octets 4+5 -   a[1]
                 Octets 6+7 -   b[1]
                 Octets 8+9 -   a[2]
                 Octets 10+11 - b[2] 
                 Octets 12+13 - a[3]
                 Octets 14+15 - b[3]
                 Octets 16+17 - a[4]
                 Octets 18+19 - b[4]
                "
           REFERENCE    "ITU-T G.997.1(200604), paragraph 7.3.1.2.14"                                
           ::= { vdsl2UpboProfEntry 2 }      
           
        vdsl2UpboProfKl  OBJECT-TYPE
            SYNTAX      Unsigned32 (0..1280)
            UNITS       "0.1 dB"
            MAX-ACCESS  read-create
            STATUS      current
            DESCRIPTION
                "This parameter defines the electrical loop length expressed in dB at 1MHz, kl0, configured by
                 the CO-MIB. The value shall be coded as an unsigned 16 bit number in the range 0 (coded as 0) 
                 to 128 dB (coded as 1280) in steps of 0.1 dB.
                 Unit: 0.1 dB
                "
            REFERENCE    "ITU-T G.997.1(200604), paragraph 7.3.1.2.14"      
            DEFVAL       { 0 }                                          
            ::= { vdsl2UpboProfEntry 3 }        
           
        vdsl2UpboProfKlf  OBJECT-TYPE
            SYNTAX      Vdsl2UpboKlf
            MAX-ACCESS  read-create
            STATUS      current
            DESCRIPTION
                "This parameter is a flag that forces the VTU-R to use the electrical loop length of the CO-MIB
                 (UPBOKL) to compute the UPBO. The value shall be forced if the flag is set to 1. Otherwise, the
                 electrical loop length shall be autonomously selected by the VTU-O.
                "  
            REFERENCE    "ITU-T G.997.1(200604), paragraph 7.3.1.2.14"   
            DEFVAL       { auto }                                                       
            ::= { vdsl2UpboProfEntry 4 }                     
            
        vdsl2UpboProfKlAuto  OBJECT-TYPE
            SYNTAX      Unsigned32(1..4)
            MAX-ACCESS  read-create
            STATUS      current
            DESCRIPTION        
                "This parameter defines the mode in which kl0 is computed when Vdsl2UpboKlf is auto. 
                 The value is defined as below:
                 1-max(kl0CO,kl0CPE)
                 2-min(kl0CO,kl0CPE)
                 3-kl0CO                         
                 4-kl0CPE                        
                 The default value is 3           
                 "                                
            DEFVAL       { 3 }              
            ::= { vdsl2UpboProfEntry 5 }        
                       
        vdsl2UpboProfRowStatus  OBJECT-TYPE
            SYNTAX      RowStatus
            MAX-ACCESS  read-create
            STATUS      current
            DESCRIPTION
                "This object is used to create a new row or to modify or
                 delete an existing row in this table.
                
                 A profile is activated by setting this object to 'active'.
                 When 'active' is set, the system will validate the profile.
                
                 Before a profile can be deleted or taken out of service
                 (by setting this object to 'destroy' or 'outOfService'),
                 it must be not referenced from all associated
                 lines.
                "
            ::= { vdsl2UpboProfEntry 6 }      
            
        vdsl2UpboProfBoostMode  OBJECT-TYPE
            SYNTAX      Vdsl2UpboBoostMode 
            MAX-ACCESS  read-create
                  STATUS      current
            DESCRIPTION
            	 "This object indicates whether the equalized FEXT UPBO method is supported or not.
            	 Options:
            	 1. disable(1)  - The Equalized FEXT UPBO method is not supported
            	 2. enable(2)   - The Equalized FEXT UPBO method is supported
            	"
            DEFVAL       { enable }
            ::= { vdsl2UpboProfEntry 65535 }
           
        vdsl2UpboProfKl0RefBand  OBJECT-TYPE
            SYNTAX      Vdsl2UpboKl0RefBand
            MAX-ACCESS  read-create
            STATUS      current
            DESCRIPTION
               "Octets 0+1 - length[1]
                Octets 2+3 - length[2]
                Octets 4+5 - length[3]
                Octets 6+7 - length[4] 
               "
            REFERENCE    
               "This parameter defines the UPBO reference electrical length used to compute the 
                upstream power back-off for each upstream band except US0, for the optional Equalized FEXT UPBO 
                method. The value ranges from 1.8 to 63.5 dB in steps of 0.1 dB with special value 0.The special 
                value 0 indicates optional Equalized FEXT UPBO method is not supported.
               "                                
            ::= { vdsl2UpboProfEntry 65536 }     
        
        --        vdsl2NoiseMarginProfTable           
        vdsl2NoiseMarginProfTable  OBJECT-TYPE
            SYNTAX      SEQUENCE  OF  Vdsl2NoiseMarginProfEntry
            MAX-ACCESS  not-accessible
            STATUS      current
            DESCRIPTION
                "The table vdsl2NoiseMarginProfTable contains VDSL2 noise margin
                 configuration. 
                 The index of this table is vdsl2NoiseMarginProfName.  
                 A default profile with an index of 'DEFVAL' will
                 always exist and its parameters will be set to vendor-specific
                 values, unless otherwise specified in this document.
                "
            ::= { vdsl2ProfileTIMode 7 }
        
        vdsl2NoiseMarginProfEntry  OBJECT-TYPE
            SYNTAX      Vdsl2NoiseMarginProfEntry
            MAX-ACCESS  not-accessible
            STATUS      current
            DESCRIPTION
                "The table vdsl2NoiseMarginProfTable contains VDSL2 noise margin
                 configuration.
                 The index of this entry is vdsl2NoiseMarginProfName.
                 A default profile with an index of 'DEFVAL' will
                 always exist and its parameters will be set to vendor-specific
                 values, unless otherwise specified in this document.
                "
            INDEX  { IMPLIED vdsl2NoiseMarginProfName }
            ::= { vdsl2NoiseMarginProfTable 1 }
            
        Vdsl2NoiseMarginProfEntry  ::=
            SEQUENCE {
              vdsl2NoiseMarginProfName              OCTET STRING,
              vdsl2NoiseMarginProfTargetSnrmDs      Unsigned32,
              vdsl2NoiseMarginProfTargetSnrmUs      Unsigned32,
              vdsl2NoiseMarginProfMaxSnrmDs         Unsigned32,
              vdsl2NoiseMarginProfMaxSnrmUs         Unsigned32,
              vdsl2NoiseMarginProfMinSnrmDs         Unsigned32,
              vdsl2NoiseMarginProfMinSnrmUs         Unsigned32,    
              vdsl2NoiseMarginProfRaUsNrmDs         Unsigned32,
              vdsl2NoiseMarginProfRaUsNrmUs         Unsigned32,
              vdsl2NoiseMarginProfRaUsTimeDs        Unsigned32,
              vdsl2NoiseMarginProfRaUsTimeUs        Unsigned32,
              vdsl2NoiseMarginProfRaDsNrmsDs        Unsigned32,
              vdsl2NoiseMarginProfRaDsNrmsUs        Unsigned32,
              vdsl2NoiseMarginProfRaDsTimeDs        Unsigned32,
              vdsl2NoiseMarginProfRaDsTimeUs        Unsigned32,
              vdsl2NoiseMarginProfDsThresholdDs     Unsigned32,
              vdsl2NoiseMarginProfUsThresholdDs     Unsigned32,
              vdsl2NoiseMarginProfDsThresholdUs     Unsigned32,
              vdsl2NoiseMarginProfUsThresholdUs     Unsigned32,
              vdsl2NoiseMarginProfRowStatus         RowStatus  
            }
        
        vdsl2NoiseMarginProfName  OBJECT-TYPE
            SYNTAX      OCTET STRING (SIZE(1..32))
            MAX-ACCESS  not-accessible
            STATUS      current
            DESCRIPTION
                "This object identifies a row in this table."
            REFERENCE    "DSL Forum TR-90, paragraph 5.1.4"
            ::= { vdsl2NoiseMarginProfEntry 1 }  
        
        vdsl2NoiseMarginProfTargetSnrmDs  OBJECT-TYPE
            SYNTAX      Unsigned32(0..310)
            UNITS       "0.1 dB"
            MAX-ACCESS  read-create
            STATUS      current
            DESCRIPTION
                "The minimum Noise Margin the xTU-R receiver shall achieve,
                 relative to the BER requirement for each of the downstream
                 bearer channels, to successfully complete initialization.
                 The target noise margin ranges from 0 to 310 units of 0.1 dB
                 (Physical values are 0 to 31 dB).
                 Unit: 0.1 dB
                "
            REFERENCE    "ITU-T G.997.1, paragraph 7.3.1.3.1"   
            DEFVAL       { 60 }
            ::= { vdsl2NoiseMarginProfEntry 2 }
        
        vdsl2NoiseMarginProfTargetSnrmUs  OBJECT-TYPE
            SYNTAX      Unsigned32(0..310)
            UNITS       "0.1 dB"
            MAX-ACCESS  read-create
            STATUS      current
            DESCRIPTION
                "The minimum Noise Margin the xTU-C receiver shall achieve,
                 relative to the BER requirement for each of the upstream
                 bearer channels, to successfully complete initialization.
                 The target noise margin ranges from 0 to 310 units of 0.1 dB
                 (Physical values are 0 to 31 dB).
                 Unit: 0.1 dB
                "
            REFERENCE    "ITU-T G.997.1, paragraph 7.3.1.3.2"
            DEFVAL       { 60 }
            ::= { vdsl2NoiseMarginProfEntry 3 }
        
        vdsl2NoiseMarginProfMaxSnrmDs  OBJECT-TYPE
            SYNTAX      Unsigned32
            UNITS       "0.1 dB"
            MAX-ACCESS  read-create
            STATUS      current
            DESCRIPTION
                "The maximum Noise Margin the xTU-R receiver shall try to
                 sustain.  If the Noise Margin is above this level, the xTU-R
                 shall request that the xTU-C reduce the xTU-C transmit power
                 to get a noise margin below this limit (if this functionality
                 is supported).  The maximum noise margin ranges from 0 to 310
                 units of 0.1 dB (Physical values are 0 to 31 dB).  A value of
                 all 1's means that there is no maximum.
                 Unit: 0.1 dB
                "
            REFERENCE    "ITU-T G.997.1, paragraph 7.3.1.3.3"
            DEFVAL       { 310 }
            ::= { vdsl2NoiseMarginProfEntry 4 }
        
        vdsl2NoiseMarginProfMaxSnrmUs  OBJECT-TYPE
            SYNTAX      Unsigned32
            UNITS       "0.1 dB"
            MAX-ACCESS  read-create
            STATUS      current
            DESCRIPTION
                "The maximum Noise Margin the xTU-C receiver shall try to
                 sustain.  If the Noise Margin is above this level, the xTU-C
                 shall request that the xTU-R reduce the xTU-R transmit power
                 to get a noise margin below this limit (if this functionality
                 is supported).  The maximum noise margin ranges from 0 to 310
                 units of 0.1 dB (Physical values are 0 to 31 dB).  A value of
                 all 1's means that there is no maximum.
                 Unit: 0.1 dB
                "
            REFERENCE    "ITU-T G.997.1, paragraph 7.3.1.3.4"
            DEFVAL       { 310 }
            ::= { vdsl2NoiseMarginProfEntry 5 }
        
        vdsl2NoiseMarginProfMinSnrmDs  OBJECT-TYPE
            SYNTAX      Unsigned32(0..310)
            UNITS       "0.1 dB"
            MAX-ACCESS  read-create
            STATUS      current
            DESCRIPTION
                "The minimum Noise Margin the xTU-R receiver shall tolerate.
                 If the noise margin falls below this level, the xTU-R shall
                 request that the xTU-C increase the xTU-C transmit power.
                 If an increase to xTU-C transmit power is not possible, a
                 loss-of-margin (LOM) defect occurs, the xTU-R shall fail and
                 attempt to reinitialize and the NMS shall be notified.  The
                 minimum noise margin ranges from 0 to 310 units of
                 0.1 dB (Physical values are 0 to 31 dB).  A value of 0 means
                 that there is no minimum.
                 Unit: 0.1 dB
                "
            REFERENCE    "ITU-T G.997.1, paragraph 7.3.1.3.5"
            DEFVAL       { 10 }
            ::= { vdsl2NoiseMarginProfEntry 6 }
        
        vdsl2NoiseMarginProfMinSnrmUs  OBJECT-TYPE
            SYNTAX      Unsigned32(0..310)
            UNITS       "0.1 dB"
            MAX-ACCESS  read-create
            STATUS      current
            DESCRIPTION
                "The minimum Noise Margin the xTU-C receiver shall tolerate.
                 If the noise margin falls below this level, the xTU-C shall
                 request that the xTU-R increase the xTU-R transmit power.
                 If an increase of xTU-R transmit power is not possible, a
                 loss-of-margin (LOM) defect occurs, the xTU-C shall fail and
                 attempt to re-initialize and the NMS shall be notified.  The
                 minimum noise margin ranges from 0 to 310 units of
                 0.1 dB (Physical values are 0 to 31 dB).  A value of 0 means
                 that there is no minimum.
                 Unit: 0.1 dB
                "
            REFERENCE    "ITU-T G.997.1, paragraph 7.3.1.3.6"
            DEFVAL       { 10 }
            ::= { vdsl2NoiseMarginProfEntry 7 }
        
        vdsl2NoiseMarginProfRaUsNrmDs  OBJECT-TYPE
            SYNTAX      Unsigned32(0..310)
            UNITS       "0.1 dB"
            MAX-ACCESS  read-create
            STATUS      current
            DESCRIPTION
                "The Downstream Up-Shift Noise Margin value, to be used when
                 Vdsl2LineConfRaModeDs is set to DynamicRa.  If the downstream
                 noise margin is above this value and stays above it for
                 more than the time specified by the Vdsl2ServProfRaUsTimeDs,
                 the xTU-R shall attempt to increase the downstream net data
                 rate.  The Downstream Up-shift Noise Margin ranges from 0 to
                 310 units of 0.1 dB (Physical values are 0 to 31 dB).
                 Unit: 0.1 dB
                "
            REFERENCE    "ITU-T G.997.1, paragraph 7.3.1.4.3"
            DEFVAL       { 310 }
            ::= { vdsl2NoiseMarginProfEntry 8 }
        
        vdsl2NoiseMarginProfRaUsNrmUs  OBJECT-TYPE
            SYNTAX      Unsigned32(0..310)
            UNITS       "0.1 dB"
            MAX-ACCESS  read-create
            STATUS      current
            DESCRIPTION
                "The Upstream Up-Shift Noise Margin value, to be used when
                 Vdsl2LineConfRaModeUs is set to DynamicRa.  If the upstream
                 noise margin is above this value and stays above it for more
                 than the time specified by the Vdsl2LineConfRaUsTimeUs, the
                 xTU-C shall attempt to increase the upstream net data rate.
                 The Upstream Up-shift Noise Margin ranges from 0 to 310 units
                 of 0.1 dB (Physical values are 0 to 31 dB).
                 Unit: 0.1 dB
                "
            REFERENCE    "ITU-T G.997.1, paragraph 7.3.1.4.4"
            DEFVAL       { 310 }
            ::= { vdsl2NoiseMarginProfEntry 9 }
        
        vdsl2NoiseMarginProfRaUsTimeDs  OBJECT-TYPE
            SYNTAX      Unsigned32(0..16383)
            UNITS       "seconds"
            MAX-ACCESS  read-create
            STATUS      current
            DESCRIPTION
                "The Downstream Up-Shift Time Interval, to be used when
                 Vdsl2LineConfRaModeDs is set to DynamicRa.  The interval of
                 time that the downstream noise margin should stay above the
                 Downstream Up-shift Noise Margin before the xTU-R shall
                 attempt to increase the downstream net data rate.  
                 Unit: seconds
                "
            REFERENCE    "ITU-T G.997.1, paragraph 7.3.1.4.5"
            DEFVAL       { 3600 }            
            ::= { vdsl2NoiseMarginProfEntry 10 }
        
        vdsl2NoiseMarginProfRaUsTimeUs  OBJECT-TYPE
            SYNTAX      Unsigned32(0..16383)
            UNITS       "seconds"
            MAX-ACCESS  read-create
            STATUS      current
            DESCRIPTION
                "The Upstream Up-Shift Time Interval, to be used when
                 Vdsl2LineConfRaModeUs is set to DynamicRa.  The interval of
                 time the upstream noise margin should stay above the
                 Upstream Up-shift Noise Margin before the xTU-C shall
                 attempt to increase the upstream net data rate.  
                 Unit: seconds
                "
            REFERENCE    "ITU-T G.997.1, paragraph 7.3.1.4.6"
            DEFVAL       { 3600 }
            ::= { vdsl2NoiseMarginProfEntry 11 }
        
        vdsl2NoiseMarginProfRaDsNrmsDs  OBJECT-TYPE
            SYNTAX      Unsigned32(0..310)
            UNITS       "0.1 dB"
            MAX-ACCESS  read-create
            STATUS      current
            DESCRIPTION
                "The Downstream Down-Shift Noise Margin value, to be used when
                 Vdsl2LineConfRaModeDs is set to DynamicRa.  If the downstream
                 noise margin is below this value and stays below that for more
                 than the time specified by the Vdsl2LineConfRaDsTimeDs, the
                 xTU-R shall attempt to decrease the downstream net data rate.
                 The Downstream Down-shift Noise Margin ranges from 0 to 310
                 units of 0.1 dB (Physical values are 0 to 31 dB).
                 Unit: 0.1 dB
                "
            REFERENCE    "ITU-T G.997.1, paragraph 7.3.1.4.7"
            DEFVAL       { 10 }
            ::= { vdsl2NoiseMarginProfEntry 12 }
        
        vdsl2NoiseMarginProfRaDsNrmsUs  OBJECT-TYPE
            SYNTAX      Unsigned32(0..310)
            UNITS       "0.1 dB"
            MAX-ACCESS  read-create
            STATUS      current
            DESCRIPTION
                "The Upstream Downshift Noise Margin value, to be used when
                 Vdsl2LineConfRaModeUs is set to DynamicRa.  If the upstream
                 noise margin is below this value and stays below that for more
                 than the time specified by the Vdsl2LineConfRaDsTimeUs, the
                 xTU-C shall attempt to decrease the upstream net data rate.
                 The Upstream Down-shift Noise Margin ranges from 0 to 310
                 units of 0.1 dB (Physical values are 0 to 31 dB).
                 Unit: 0.1 dB
                "
            
            REFERENCE    "ITU-T G.997.1, paragraph 7.3.1.4.8"
            DEFVAL       { 10 }
            ::= { vdsl2NoiseMarginProfEntry 13 }
        
        vdsl2NoiseMarginProfRaDsTimeDs  OBJECT-TYPE
            SYNTAX      Unsigned32(0..16383)
            UNITS       "seconds"
            MAX-ACCESS  read-create
            STATUS      current
            DESCRIPTION
                "The Downstream Downshift Time Interval, to be used when
                 Vdsl2LineConfRaModeDs is set to DynamicRa.  The interval of
                 time the downstream noise margin should stay below the
                 Downstream Down-shift Noise Margin before the xTU-R shall
                 attempt to decrease the downstream net data rate.  
                 Unit: seconds
                "
            REFERENCE    "ITU-T G.997.1, paragraph 7.3.1.4.9"
            DEFVAL       { 3600 }
            ::= { vdsl2NoiseMarginProfEntry 14 }
        
        vdsl2NoiseMarginProfRaDsTimeUs  OBJECT-TYPE
            SYNTAX      Unsigned32(0..16383)
            UNITS       "seconds"
            MAX-ACCESS  read-create
            STATUS      current
            DESCRIPTION
                "The Upstream Down-Shift Time Interval, to be used when
                 Vdsl2LineConfRaModeUs is set to DynamicRa.  The interval of
                 time the upstream noise margin should stay below the Upstream
                 Down-shift Noise Margin before the xTU-C shall attempt to
                 decrease the upstream net data rate.  
                 Unit: seconds
                "
            REFERENCE    "ITU-T G.997.1, paragraph 7.3.1.4.10"
            DEFVAL       { 3600 }
            ::= { vdsl2NoiseMarginProfEntry 15 }	
            
        vdsl2NoiseMarginProfDsThresholdDs  OBJECT-TYPE
            SYNTAX      Unsigned32(0..200000000)
            UNITS       "bits/second"
            MAX-ACCESS  read-create
            STATUS      current
            DESCRIPTION
                "Data Rate Threshold Downshift for downstream direction.  A
                 'Down-shift rate change' event is triggered when the actual
                 downstream data rate is below the data rate at the last entry
                 into Showtime, by more than the threshold.  The parameter is
                 coded in bit/s.
                 Unit: bits/second
                "
            REFERENCE    "ITU-T G.997.1, paragraph 7.3.2.6"
            DEFVAL       { 0 }
            ::= { vdsl2NoiseMarginProfEntry 16 }
           	
        vdsl2NoiseMarginProfUsThresholdDs  OBJECT-TYPE
            SYNTAX      Unsigned32(0..200000000)
            UNITS       "bits/second"
            MAX-ACCESS  read-create
            STATUS      current
            DESCRIPTION
                "Data Rate Threshold Up shift for downstream direction.  An
                 'Up-shift rate change' event is triggered when the actual
                 downstream data rate exceeds, by more than the threshold, the
                 data rate at the last entry into Showtime.  The parameter is
                 coded in bit/s.
                 Unit: bits/second
                "
            REFERENCE    "ITU-T G.997.1, paragraph 7.3.2.6"
            DEFVAL       { 0 }
            ::= { vdsl2NoiseMarginProfEntry 17 }
        
        vdsl2NoiseMarginProfDsThresholdUs  OBJECT-TYPE
            SYNTAX      Unsigned32(0..200000000)
            UNITS       "bits/second"
            MAX-ACCESS  read-create
            STATUS      current
            DESCRIPTION
                "Data Rate Threshold Downshift for upstream direction.  A
                 'Down-shift rate change' event is triggered when the actual
                 upstream data rate is below the data rate at the last entry
                 into Showtime, by more than the threshold.  The parameter is
                 coded in bit/s.
                 Unit: bits/second
                "
            REFERENCE    "ITU-T G.997.1, paragraph 7.3.2.6"
            DEFVAL       { 0 }
            ::= { vdsl2NoiseMarginProfEntry 18 }
           
        vdsl2NoiseMarginProfUsThresholdUs  OBJECT-TYPE
            SYNTAX      Unsigned32(0..200000000)
            UNITS       "bits/second"
            MAX-ACCESS  read-create
            STATUS      current
            DESCRIPTION
                "Data Rate Threshold Up shift for upstream direction.  An
                 'Up-shift rate change' event is triggered when the actual
                 upstream data rate exceeds, by more than the threshold, the
                 data rate at the last entry into Showtime.  The parameter is
                 coded in bit/s.
                 Unit: bits/second
                "
            REFERENCE    "ITU-T G.997.1, paragraph 7.3.2.6"
            DEFVAL       { 0 }
            ::= { vdsl2NoiseMarginProfEntry 19 }
           
        vdsl2NoiseMarginProfRowStatus  OBJECT-TYPE
            SYNTAX      RowStatus
            MAX-ACCESS  read-create
            STATUS      current
            DESCRIPTION
                "This object is used to create a new row or to modify or
                delete an existing row in this table.
               
                A profile is activated by setting this object to 'active'.
                When 'active' is set, the system will validate the profile.
               
                Before a profile can be deleted or taken out of service
                (by setting this object to 'destroy' or 'outOfService'),
                it must be not referenced from all associated
                lines.
               "
            ::= { vdsl2NoiseMarginProfEntry 20 }   
        
          --        vdsl2DelayInpProfTable           
        vdsl2DelayInpProfTable  OBJECT-TYPE
            SYNTAX      SEQUENCE  OF  Vdsl2DelayInpProfEntry
            MAX-ACCESS  not-accessible
            STATUS      current
            DESCRIPTION
                "The table vdsl2DelayInpProfTable contains VDSL2 delay inp
                 configuration. The index of this table is vdsl2DelayInpProfName.  
                 A default profile with an index of 'DEFVAL' will
                 always exist and its parameters will be set to vendor-specific
                 values, unless otherwise specified in this document.
                "
            ::= { vdsl2ProfileTIMode 8 }
        
        vdsl2DelayInpProfEntry  OBJECT-TYPE
            SYNTAX      Vdsl2DelayInpProfEntry
            MAX-ACCESS  not-accessible
            STATUS      current
            DESCRIPTION
                "The table vdsl2DelayInpProfTable contains VDSL2 delay inp
                 configuration. The index of this entry is vdsl2DelayInpProfName.
                 A default profile with an index of 'DEFVAL' will
                 always exist and its parameters will be set to vendor-specific
                 values, unless otherwise specified in this document.
                "
            INDEX  { IMPLIED vdsl2DelayInpProfName }
            ::= { vdsl2DelayInpProfTable 1 }
        
        Vdsl2DelayInpProfEntry  ::=
            SEQUENCE {
              vdsl2DelayInpProfName                     OCTET STRING,
              vdsl2DelayInpProfForceINP                 Vdsl2ForceINP, 
              vdsl2DelayInpProfCh1MaxDelayDs            Unsigned32,
              vdsl2DelayInpProfCh1MaxDelayUs            Unsigned32,  
              vdsl2DelayInpProfCh1MinProtectionDs       Vdsl2SymbolProtectionDs,
              vdsl2DelayInpProfCh1MinProtectionUs       Vdsl2SymbolProtectionUs,
              vdsl2DelayInpProfCh2MaxDelayDs            Unsigned32,
              vdsl2DelayInpProfCh2MaxDelayUs            Unsigned32,  
              vdsl2DelayInpProfCh2MinProtectionDs       Vdsl2SymbolProtectionDs,
              vdsl2DelayInpProfCh2MinProtectionUs       Vdsl2SymbolProtectionUs,
              vdsl2DelayInpProfRowStatus                RowStatus,
              vdsl2DelayInpProfCh1PhyRcontrolDs	        Vdsl2PhyRControl,		 		   
              vdsl2DelayInpProfCh1PhyRcontrolUs	        Vdsl2PhyRControl,
              vdsl2DelayInpProfCh1INPmaxDs		Vdsl2SymbolProtectionDs,
              vdsl2DelayInpProfCh1INPmaxUs		Vdsl2SymbolProtectionUs,
              vdsl2DelayInpProfCh1MinRtxRatioDs	        Integer32,
              vdsl2DelayInpProfCh1MinRtxRatioUs	        Integer32,
              vdsl2DelayInpProfCh1MinRSoverheadDs       Integer32,
              vdsl2DelayInpProfCh1MinRSoverheadUs	Integer32,
              vdsl2DelayInpProfCh2PhyRcontrolDs	        Vdsl2PhyRControl,
              vdsl2DelayInpProfCh2PhyRcontrolUs         Vdsl2PhyRControl,
              vdsl2DelayInpProfCh2INPmaxDs		Vdsl2SymbolProtectionDs,
              vdsl2DelayInpProfCh2INPmaxUs		Vdsl2SymbolProtectionUs,
              vdsl2DelayInpProfCh2MinRtxRatioDs	        Integer32,
              vdsl2DelayInpProfCh2MinRtxRatioUs	        Integer32,
              vdsl2DelayInpProfCh2MinRSoverheadDs	Integer32,
              vdsl2DelayInpProfCh2MinRSoverheadUs	Integer32,
              hwvdsl2DelayInpProfCh1MaxDelayRtxDs       Unsigned32,
              hwvdsl2DelayInpProfCh1MaxDelayRtxUs       Unsigned32,
              hwvdsl2DelayInpProfCh1MinDelayRtxDs       Unsigned32,
              hwvdsl2DelayInpProfCh1MinDelayRtxUs       Unsigned32,
              hwvdsl2DelayInpProfCh1MinInpShineRtxDs    Unsigned32,
              hwvdsl2DelayInpProfCh1MinInpShineRtxUs    Unsigned32,
              hwvdsl2DelayInpProfCh1MinInp8ShineRtxDs   Unsigned32,
              hwvdsl2DelayInpProfCh1MinInp8ShineRtxUs   Unsigned32,
              hwvdsl2DelayInpProfCh1ShineRatioRtxDs     Unsigned32,
              hwvdsl2DelayInpProfCh1ShineRatioRtxUs     Unsigned32,
              hwvdsl2DelayInpProfCh1MinInpReinRtxDs     Unsigned32,
              hwvdsl2DelayInpProfCh1MinInpReinRtxUs     Unsigned32,
              hwvdsl2DelayInpProfCh1MinInp8ReinRtxDs    Unsigned32,
              hwvdsl2DelayInpProfCh1MinInp8ReinRtxUs    Unsigned32,
              hwvdsl2DelayInpProfCh1IatReinRtxDs        INTEGER, 
              hwvdsl2DelayInpProfCh1IatReinRtxUs        INTEGER   
              }
        
        vdsl2DelayInpProfName  OBJECT-TYPE
            SYNTAX      OCTET STRING (SIZE(1..32))
            MAX-ACCESS  not-accessible
            STATUS      current
            DESCRIPTION
                "This object identifies a row in this table."
            REFERENCE    "DSL Forum TR-90, paragraph 5.1.4"
            ::= { vdsl2DelayInpProfEntry 1 }  
        
        vdsl2DelayInpProfForceINP  OBJECT-TYPE
            SYNTAX      Vdsl2ForceINP 
            MAX-ACCESS  read-create
            STATUS      current
            DESCRIPTION
            	 "This parameter indicates that the framer settings of the 
            	  bearer shall be selected such that the impulse noise protection 
            	  computed according to the formula specified in the relevant 
            	  Recommendation is greater or equal to the minimal impulse noise 
            	  protection requirement.
            	  This flag shall have the same value for all the bearers of one
            	  line in the same direction.
                 "
            REFERENCE    "ITU-T G.997.1, paragraph 7.3.2.5"
            DEFVAL       { force }
            ::= { vdsl2DelayInpProfEntry 2 }      
           
        vdsl2DelayInpProfCh1MaxDelayDs  OBJECT-TYPE
            SYNTAX      Unsigned32(0..200)
            UNITS       "milliseconds"
            MAX-ACCESS  read-create
            STATUS      current
            DESCRIPTION
                "If retransmission is not used in downstream direction,this parameter
                 is maximum interleave delay on downstream direction. The maximum
                 one-way interleaving delay introduced by the PMS-TC on
                 Downstream direction. The XTUs shall choose the S (factor)
                 and D (depth) values such that the actual one-way interleaving
                 delay (Vdsl2ChanStatusActDelay) is as close as possible to,
                 but less than or equal to, Vdsl2ChanConfMaxDelayDs. The
                 delay is coded in ms, with the value 0 indicating no delay
                 bound is being imposed.
                 Unit: milliseconds
                "
            REFERENCE    "ITU-T G.997.1, paragraph 7.3.2.2"
            DEFVAL       { 20 }
            ::= { vdsl2DelayInpProfEntry 3 }
        
        vdsl2DelayInpProfCh1MaxDelayUs  OBJECT-TYPE
            SYNTAX      Unsigned32(0..200)
            UNITS       "milliseconds"
            MAX-ACCESS  read-create
            STATUS      current
            DESCRIPTION
                "If retransmission is not used in upstream direction.  The maximum
                 one-way interleaving delay introduced by the PMS-TC on
                 Upstream direction. The XTUs shall choose the S (factor) and
                 D (depth) values such that the actual one-way interleaving
                 delay (Vdsl2ChanStatusActDelay) is as close as possible to,
                 but less than or equal to, Vdsl2ChanConfMaxDelayUs.  The
                 delay is coded in ms, with the value 0 indicating no delay
                 bound is being imposed.
                 Unit: milliseconds
                "
            REFERENCE    "ITU-T G.997.1, paragraph 7.3.2.2"
            DEFVAL       { 20 }
            ::= { vdsl2DelayInpProfEntry 4 } 
           
        vdsl2DelayInpProfCh1MinProtectionDs  OBJECT-TYPE
            SYNTAX      Vdsl2SymbolProtectionDs
            UNITS       "symbols"
            MAX-ACCESS  read-create
            STATUS      current
            DESCRIPTION
                "If retransmission is not used in downstream direction,this parameter
                 is minimum impulse noise protection for the bearer channel on downstream
                 direction. The minimum impulse noise protection for the bearer channel,
                 expressed in symbols. The parameter can take the following
                 values: noProtection (i.e., INP not required), halfSymbol
                 (i.e., INP length is 1/2 symbol) and 1-16 symbols in steps
                 of 1 symbol.
                 Unit: symbols
                "
            REFERENCE    "ITU-T G.997.1, paragraph 7.3.2.3"
            DEFVAL       { noProtection }
            ::= { vdsl2DelayInpProfEntry 5 }
            
        vdsl2DelayInpProfCh1MinProtectionUs  OBJECT-TYPE
            SYNTAX      Vdsl2SymbolProtectionUs
            UNITS       "symbols"
            MAX-ACCESS  read-create
            STATUS      current
            DESCRIPTION
                "If retransmission is not used in upstream direction,this parameter
                 is minimum impulse noise protection for the bearer channel on upstream
                 direction. The minimum impulse noise protection for the bearer channel,
                 expressed in symbols. The parameter can take the following
                 values: noProtection (i.e., INP not required), halfSymbol
                 (i.e., INP length is 1/2 symbol) and 1-16 symbols in steps
                 of 1 symbol.
                 Unit: symbols
                "
            REFERENCE    "ITU-T G.997.1, paragraph 7.3.2.3"
            DEFVAL       { noProtection }
            ::= { vdsl2DelayInpProfEntry 6 }
        
        vdsl2DelayInpProfCh2MaxDelayDs  OBJECT-TYPE
            SYNTAX      Unsigned32(0..200)
            UNITS       "milliseconds"
            MAX-ACCESS  read-create
            STATUS      current
            DESCRIPTION
                "Maximum Interleave Delay on Downstream direction.  The maximum
                 one-way interleaving delay introduced by the PMS-TC on
                 Downstream direction.  The XTUs shall choose the S (factor)
                 and D (depth) values such that the actual one-way interleaving
                 delay (Vdsl2ChanStatusActDelay) is as close as possible to,
                 but less than or equal to, Vdsl2ChanConfMaxDelayDs.  The
                 delay is coded in ms, with the value 0 indicating no delay
                 bound is being imposed.
                 Unit: milliseconds
                "
            REFERENCE    "ITU-T G.997.1, paragraph 7.3.2.2"
            DEFVAL       { 20 }
            ::= { vdsl2DelayInpProfEntry 7 }
        
        vdsl2DelayInpProfCh2MaxDelayUs  OBJECT-TYPE
            SYNTAX      Unsigned32(0..200)
            UNITS       "milliseconds"
            MAX-ACCESS  read-create
            STATUS      current
            DESCRIPTION
                "Maximum Interleave Delay on Upstream direction.  The maximum
                 one-way interleaving delay introduced by the PMS-TC on
                 Upstream direction.  The XTUs shall choose the S (factor) and
                 D (depth) values such that the actual one-way interleaving
                 delay (Vdsl2ChanStatusActDelay) is as close as possible to,
                 but less than or equal to, Vdsl2ChanConfMaxDelayUs.  The
                 delay is coded in ms, with the value 0 indicating no delay
                 bound is being imposed.
                 Unit: milliseconds
                "
            REFERENCE    "ITU-T G.997.1, paragraph 7.3.2.2"
            DEFVAL       { 20 }
            ::= { vdsl2DelayInpProfEntry 8 } 
           
        vdsl2DelayInpProfCh2MinProtectionDs  OBJECT-TYPE
            SYNTAX      Vdsl2SymbolProtectionDs
            UNITS       "symbols"
            MAX-ACCESS  read-create
            STATUS      current
            DESCRIPTION
                "Minimum Impulse Noise Protection on Downstream direction.  The
                 minimum impulse noise protection for the bearer channel,
                 expressed in symbols.  The parameter can take the following
                 values: noProtection (i.e., INP not required), halfSymbol
                 (i.e., INP length is 1/2 symbol) and 1-16 symbols in steps
                 of 1 symbol.
                 Unit: symbols
                "
            REFERENCE    "ITU-T G.997.1, paragraph 7.3.2.3"
            DEFVAL       { noProtection }
            ::= { vdsl2DelayInpProfEntry 9 }
        
        vdsl2DelayInpProfCh2MinProtectionUs  OBJECT-TYPE
            SYNTAX      Vdsl2SymbolProtectionUs
            UNITS       "symbols"
            MAX-ACCESS  read-create
            STATUS      current
            DESCRIPTION
                "Minimum Impulse Noise Protection on Upstream direction.  The
                 minimum impulse noise protection for the bearer channel,
                 expressed in symbols.  The parameter can take the following
                 values: noProtection (i.e., INP not required), halfSymbol
                 (i.e., INP length is 1/2 symbol) and 1-16 symbols in steps
                 of 1 symbol.
                 Unit: symbols
                "
            REFERENCE    "ITU-T G.997.1, paragraph 7.3.2.3"
            DEFVAL       { noProtection }
            ::= { vdsl2DelayInpProfEntry 10 }
              
        vdsl2DelayInpProfRowStatus  OBJECT-TYPE
            SYNTAX      RowStatus
            MAX-ACCESS  read-create
            STATUS      current
            DESCRIPTION
                "This object is used to create a new row or to modify or
                 delete an existing row in this table.          
                 A profile is activated by setting this object to 'active'.
                 When 'active' is set, the system will validate the profile.          
                 Before a profile can be deleted or taken out of service
                 (by setting this object to 'destroy' or 'outOfService'),
                 it must be not referenced from all associated
                 lines.
                "
            ::= { vdsl2DelayInpProfEntry 11 }  
        
             
        vdsl2DelayInpProfCh1PhyRcontrolDs OBJECT-TYPE
            SYNTAX      Vdsl2PhyRControl
            MAX-ACCESS  read-write
            STATUS      current
            DESCRIPTION
                "To enable or disable the retransmission function on downstream direction."
            DEFVAL { 2 }
            ::= { vdsl2DelayInpProfEntry 12 }
                  
        vdsl2DelayInpProfCh1PhyRcontrolUs OBJECT-TYPE
            SYNTAX      Vdsl2PhyRControl
            MAX-ACCESS  read-write
            STATUS      current
            DESCRIPTION
                "To enable or disable the retransmission function on upstream direction."
            DEFVAL { 2 }
            ::= { vdsl2DelayInpProfEntry 13 }            
        
        vdsl2DelayInpProfCh1INPmaxDs OBJECT-TYPE
            SYNTAX      Vdsl2SymbolProtectionDs
            UNITS       "DMT Symbol"
            MAX-ACCESS  read-write
            STATUS      current
            DESCRIPTION
                "Maximum Impulse Noise Protection on downstream direction.
                 Options:
                 1. noProtection(1)
                 2. halfSymbol(2)
                 3. singleSymbol(3)
                 4. twoSymbols(4)
                 5. threeSymbols(5)
                 6. fourSymbols(6)
                 7. fiveSymbols(7)
                 8. sixSymbols(8)
                 9. sevenSymbols(9)
                 10. eightSymbols(10)
                 11. nineSymbols(11)
                 12. tenSymbols(12)
                 13. elevenSymbols(13)
                 14. twelveSymbols(14)
                 15. thirteeSymbols(15)
                 16. fourteenSymbols(16)
                 17. fifteenSymbols(17)
                 18. sixteenSymbols(18)
                
                 The value multiply 1/2 is the real value of Noise Protection values.
                 Unit: DMT Symbol
        	"
            DEFVAL { 1 }
            ::= { vdsl2DelayInpProfEntry 14 }
             
        vdsl2DelayInpProfCh1INPmaxUs OBJECT-TYPE
            SYNTAX      Vdsl2SymbolProtectionUs
            UNITS       "DMT Symbol"
            MAX-ACCESS  read-write
            STATUS      current
            DESCRIPTION
                "Maximum Impulse Noise Protection on upstream direction.
                 Options:
                 1. noProtection(1)
                 2. halfSymbol(2)
                 3. singleSymbol(3)
                 4. twoSymbols(4)
                 5. threeSymbols(5)
                 6. fourSymbols(6)
                 7. fiveSymbols(7)
                 8. sixSymbols(8)
                 9. sevenSymbols(9)
                 10. eightSymbols(10)
                 11. nineSymbols(11)
                 12. tenSymbols(12)
                 13. elevenSymbols(13)
                 14. twelveSymbols(14)
                 15. thirteeSymbols(15)
                 16. fourteenSymbols(16)
                 17. fifteenSymbols(17)
                 18. sixteenSymbols(18)
                 
                 The value multiply 1/2 is the real value of Noise Protection values.
                 Unit: DMT Symbol
        	     "
            DEFVAL { 1 }
            ::= { vdsl2DelayInpProfEntry 15 }	    
        
        vdsl2DelayInpProfCh1MinRtxRatioDs OBJECT-TYPE
            SYNTAX      Integer32 (0..255)
            UNITS       "1/256"
            MAX-ACCESS  read-write
            STATUS      current
            DESCRIPTION
                "Minimum rtxratio on downstream direction.
                 Unit: 1/256
                "
            DEFVAL { 0 }
            ::= { vdsl2DelayInpProfEntry 16 }
            
        vdsl2DelayInpProfCh1MinRtxRatioUs OBJECT-TYPE
            SYNTAX      Integer32 (0..255)
            UNITS       "1/256"
            MAX-ACCESS  read-write
            STATUS      current
            DESCRIPTION
                "Minimum rtxratio on upstream direction.
                 Unit: 1/256
                "
            DEFVAL { 0 }
            ::= { vdsl2DelayInpProfEntry 17 }
        
        vdsl2DelayInpProfCh1MinRSoverheadDs OBJECT-TYPE
            SYNTAX      Integer32 (0..128)
            UNITS       "1/256"
            MAX-ACCESS  read-write
            STATUS      current
            DESCRIPTION
                "The minimum value of R/N on downstream direction.
                 Unit: 1/256
                "
            DEFVAL { 0 }
            ::= { vdsl2DelayInpProfEntry 18 }
             
        vdsl2DelayInpProfCh1MinRSoverheadUs OBJECT-TYPE
            SYNTAX      Integer32 (0..128)
            UNITS       "1/256"
            MAX-ACCESS  read-write
            STATUS      current
            DESCRIPTION
                "The minimum value of R/N on upstream direction.
                 Unit: 1/256
                "
            DEFVAL { 0 }
            ::= { vdsl2DelayInpProfEntry 19 }
            
        vdsl2DelayInpProfCh2PhyRcontrolDs OBJECT-TYPE
            SYNTAX      Vdsl2PhyRControl
            MAX-ACCESS  read-write
            STATUS      current
            DESCRIPTION
                "To enable or disable the retransmission function on downstream direction."
            DEFVAL { 2 }
            ::= { vdsl2DelayInpProfEntry 20 }
            
        vdsl2DelayInpProfCh2PhyRcontrolUs OBJECT-TYPE
            SYNTAX      Vdsl2PhyRControl
            MAX-ACCESS  read-write
            STATUS      current
            DESCRIPTION
                "To enable or disable the retransmission function on upstream direction."
            DEFVAL { 2 }
            ::= { vdsl2DelayInpProfEntry 21 }            
        
        vdsl2DelayInpProfCh2INPmaxDs OBJECT-TYPE
            SYNTAX      Vdsl2SymbolProtectionDs
            UNITS       "DMT Symbol"
            MAX-ACCESS  read-write
            STATUS      current
            DESCRIPTION
                "Maximum Impulse Noise Protection on downstream direction.
                 Options:
                 1. noProtection(1)
                 2. halfSymbol(2)
                 3. singleSymbol(3)
                 4. twoSymbols(4)
                 5. threeSymbols(5)
                 6. fourSymbols(6)
                 7. fiveSymbols(7)
                 8. sixSymbols(8)
                 9. sevenSymbols(9)
                 10. eightSymbols(10)
                 11. nineSymbols(11)
                 12. tenSymbols(12)
                 13. elevenSymbols(13)
                 14. twelveSymbols(14)
                 15. thirteeSymbols(15)
                 16. fourteenSymbols(16)
                 17. fifteenSymbols(17)
                 18. sixteenSymbols(18)
                
                 The value multiply 1/2 is the real value of Noise Protection values.
                 Unit: DMT Symbol
        	"
            DEFVAL { 1 }
            ::= { vdsl2DelayInpProfEntry 22 }
            
        vdsl2DelayInpProfCh2INPmaxUs OBJECT-TYPE
            SYNTAX      Vdsl2SymbolProtectionUs
            UNITS       "DMT Symbol"
            MAX-ACCESS  read-write
            STATUS      current
            DESCRIPTION
               "Maximum Impulse Noise Protection on upstream direction.
                Options:
                1. noProtection(1)
                2. halfSymbol(2)
                3. singleSymbol(3)
                4. twoSymbols(4)
                5. threeSymbols(5)
                6. fourSymbols(6)
                7. fiveSymbols(7)
                8. sixSymbols(8)
                9. sevenSymbols(9)
                10. eightSymbols(10)
                11. nineSymbols(11)
                12. tenSymbols(12)
                13. elevenSymbols(13)
                14. twelveSymbols(14)
                15. thirteeSymbols(15)
                16. fourteenSymbols(16)
                17. fifteenSymbols(17)
                18. sixteenSymbols(18)
                
                The value multiply 1/2 is the real value of Noise Protection values.
                Unit: DMT Symbol
               "
            DEFVAL { 1 }
            ::= { vdsl2DelayInpProfEntry 23 }	    
        
        vdsl2DelayInpProfCh2MinRtxRatioDs OBJECT-TYPE
            SYNTAX      Integer32 (0..255)
            UNITS       "1/256"
            MAX-ACCESS  read-write
            STATUS      current
            DESCRIPTION
                "Minimum rtxratio on downstream direction.
                 Unit: 1/256
                "
            DEFVAL { 0 }
            ::= { vdsl2DelayInpProfEntry 24 }
            
        vdsl2DelayInpProfCh2MinRtxRatioUs OBJECT-TYPE
            SYNTAX      Integer32 (0..255)
            UNITS       "1/256"
            MAX-ACCESS  read-write
            STATUS      current
            DESCRIPTION
                "Minimum rtxratio on upstream direction.
                 Unit: 1/256
                "
            DEFVAL { 0 }
            ::= { vdsl2DelayInpProfEntry 25 }
        
        vdsl2DelayInpProfCh2MinRSoverheadDs OBJECT-TYPE
            SYNTAX      Integer32 (0..128)
            UNITS       "1/256"
            MAX-ACCESS  read-write
            STATUS      current
            DESCRIPTION
                "The minimum value of R/N on downstream direction.
                 Unit: 1/256
                "
            DEFVAL { 0 }
            ::= { vdsl2DelayInpProfEntry 26 }
            
        vdsl2DelayInpProfCh2MinRSoverheadUs OBJECT-TYPE
            SYNTAX      Integer32 (0..128)
            UNITS       "1/256"
            MAX-ACCESS  read-write
            STATUS      current
            DESCRIPTION
                "The minimum value of R/N on upstream direction.
                 Unit: 1/256
                "
            DEFVAL { 0 }
            ::= { vdsl2DelayInpProfEntry 27 }
            	    	    	    	
        hwvdsl2DelayInpProfCh1MaxDelayRtxDs  OBJECT-TYPE
            SYNTAX      Unsigned32(1..63)
            UNITS       "milliseconds"
            MAX-ACCESS  read-create
            STATUS      current
            DESCRIPTION
               "If retransmission is used in downstream direction, this parameter specifies 
                the maximum for the instantaneous delay due to the effect of retransmission only 
                (see G.998.4 for detailed specification). The delay ranges from 1 to 63 ms by steps of 1 ms. 
                Unit: milliseconds
               "
            REFERENCE    "ITU-T G.997.1, paragraph 7.3.2.11"
            ::= { vdsl2DelayInpProfEntry 28 }   

        hwvdsl2DelayInpProfCh1MaxDelayRtxUs  OBJECT-TYPE
            SYNTAX      Unsigned32(1..63)
            UNITS       "milliseconds"
            MAX-ACCESS  read-create
            STATUS      current
            DESCRIPTION
               "If retransmission is used in upstream direction, this parameter specifies 
                the maximum for the instantaneous delay due to the effect of retransmission only 
                (see G.998.4 for detailed specification). The delay ranges from 1 to 63 ms by steps of 1 ms. 
                Unit: milliseconds
               "
            REFERENCE    "ITU-T G.997.1, paragraph 7.3.2.11"
            ::= { vdsl2DelayInpProfEntry 29 }   

        hwvdsl2DelayInpProfCh1MinDelayRtxDs  OBJECT-TYPE
            SYNTAX      Unsigned32(0..63)
            UNITS       "milliseconds"
            MAX-ACCESS  read-create
            STATUS      current
            DESCRIPTION
               "If retransmission is used in downstream direction, this parameter specifies 
                the minimum for the instantaneous delay due to the effect of retransmission only 
                (see G.998.4 for detailed specification). The delay ranges from 0 to 63 ms by steps of 1 ms. 
                Unit: milliseconds
               "
            REFERENCE    "ITU-T G.997.1, paragraph 7.3.2.12"
            ::= { vdsl2DelayInpProfEntry 30 }   

        hwvdsl2DelayInpProfCh1MinDelayRtxUs  OBJECT-TYPE
            SYNTAX      Unsigned32(0..63)
            UNITS       "milliseconds"
            MAX-ACCESS  read-create
            STATUS      current
            DESCRIPTION
               "If retransmission is used in upstream direction, this parameter specifies 
                the minimum for the instantaneous delay due to the effect of retransmission only 
                (see G.998.4 for detailed specification). The delay ranges from 0 to 63 ms by steps of 1 ms. 
                Unit: milliseconds
               "
            REFERENCE    "ITU-T G.997.1, paragraph 7.3.2.12"
            ::= { vdsl2DelayInpProfEntry 31 } 
                                 
       hwvdsl2DelayInpProfCh1MinInpShineRtxDs  OBJECT-TYPE
            SYNTAX      Unsigned32(0..63)
            UNITS       "symbols"
            MAX-ACCESS  read-create
            STATUS      current
            DESCRIPTION
               "If retransmission is used in downstream direction, this parameter specifies 
                the minimum impulse noise protection against SHINE for the bearer channel if it is 
                transported over DMT symbols with a subcarrier spacing of 4.3125 kHz. The impulse 
                noise protection is expressed in DMT symbols with a subcarrier spacing of 4.3125 kHz 
                and can take any integer value from 0 to 63, inclusive.
                Unit: symbols
               "
            REFERENCE    "ITU-T G.997.1, paragraph 7.3.2.13"
            DEFVAL       { 0 }
            ::= { vdsl2DelayInpProfEntry 32 } 

        hwvdsl2DelayInpProfCh1MinInpShineRtxUs  OBJECT-TYPE
            SYNTAX      Unsigned32(0..63)
            UNITS       "symbols"
            MAX-ACCESS  read-create
            STATUS      current
            DESCRIPTION
               "If retransmission is used in upstream direction, this parameter specifies the 
                minimum impulse noise protection against SHINE for the bearer channel if it is 
                transported over DMT symbols with a subcarrier spacing of 4.3125 kHz. The impulse 
                noise protection is expressed in DMT symbols with a subcarrier spacing of 4.3125 kHz 
                and can take any integer value from 0 to 63, inclusive.
                Unit: symbols
               "
            REFERENCE    "ITU-T G.997.1, paragraph 7.3.2.13"
            DEFVAL       { 0 }
            ::= { vdsl2DelayInpProfEntry 33 } 

       hwvdsl2DelayInpProfCh1MinInp8ShineRtxDs  OBJECT-TYPE
            SYNTAX      Unsigned32(0..127)
            UNITS       "symbols"
            MAX-ACCESS  read-create
            STATUS      current
            DESCRIPTION
               "If retransmission is used in downstream direction, this parameter specifies 
                the minimum impulse noise protection against SHINE for the bearer channel if it is 
                transported over DMT symbols with a subcarrier spacing of 8.625 kHz. The impulse 
                noise protection is expressed in DMT symbols with a subcarrier spacing of 8.625 kHz 
                and can take any integer value from 0 to 127, inclusive.
                Unit: symbols
               "
            REFERENCE    "ITU-T G.997.1, paragraph 7.3.2.14"
            DEFVAL       { 0 }
            ::= { vdsl2DelayInpProfEntry 34 } 

        hwvdsl2DelayInpProfCh1MinInp8ShineRtxUs  OBJECT-TYPE
            SYNTAX      Unsigned32(0..127)
            UNITS       "symbols"
            MAX-ACCESS  read-create
            STATUS      current
            DESCRIPTION
               "If retransmission is used in upstream direction, this parameter specifies the 
                minimum impulse noise protection against SHINE for the bearer channel if it is 
                transported over DMT symbols with a subcarrier spacing of 8.625 kHz. The impulse 
                noise protection is expressed in DMT symbols with a subcarrier spacing of 8.625 kHz 
                and can take any integer value from 0 to 127, inclusive.
                Unit: symbols
               "
            REFERENCE    "ITU-T G.997.1, paragraph 7.3.2.14"
            DEFVAL       { 0 }
            ::= { vdsl2DelayInpProfEntry 35 } 
            
        hwvdsl2DelayInpProfCh1ShineRatioRtxDs  OBJECT-TYPE
            SYNTAX      Unsigned32(0..100)
            MAX-ACCESS  read-create
            STATUS      current
            DESCRIPTION
               "If retransmission is used in downstream direction, this parameter specifies 
                the SHINE ratio (detailed definition see G.998.4).
                The values range from 0 to 0.100 in increments of 0.001.
               "
            REFERENCE    "ITU-T G.997.1, paragraph 7.3.2.15"
            DEFVAL       { 0 }
            ::= { vdsl2DelayInpProfEntry 36 } 

        hwvdsl2DelayInpProfCh1ShineRatioRtxUs  OBJECT-TYPE
            SYNTAX      Unsigned32(0..100)
            MAX-ACCESS  read-create
            STATUS      current
            DESCRIPTION
               "If retransmission is used in upstream direction, this parameter specifies 
                the SHINE ratio (detailed definition see G.998.4).
                The values range from 0 to 0.100 in increments of 0.001.
               "
            REFERENCE    "ITU-T G.997.1, paragraph 7.3.2.15"
            DEFVAL       { 0 }
            ::= { vdsl2DelayInpProfEntry 37 } 
            
        hwvdsl2DelayInpProfCh1MinInpReinRtxDs  OBJECT-TYPE
            SYNTAX      Unsigned32(0..7)
            MAX-ACCESS  read-create
            STATUS      current
            DESCRIPTION
               "If retransmission is used in downstream direction, this parameter specifies 
                the minimum impulse noise protection against REIN for the bearer channel if it is 
                transported over DMT symbols with a subcarrier spacing of 4.3125 kHz. The impulse 
                noise protection is expressed in DMT symbols with a subcarrier spacing of 4.3125 kHz 
                and can take any integer value from 0 to 7, inclusive.
               "
            REFERENCE    "ITU-T G.997.1, paragraph 7.3.2.16"
            DEFVAL       { 0 }
            ::= { vdsl2DelayInpProfEntry 38 }             
            
        hwvdsl2DelayInpProfCh1MinInpReinRtxUs  OBJECT-TYPE
            SYNTAX      Unsigned32(0..7)
            MAX-ACCESS  read-create
            STATUS      current
            DESCRIPTION
               "If retransmission is used in upstream direction, this parameter specifies 
                the minimum impulse noise protection against REIN for the bearer channel if it is 
                transported over DMT symbols with a subcarrier spacing of 4.3125 kHz. The impulse 
                noise protection is expressed in DMT symbols with a subcarrier spacing of 4.3125 kHz 
                and can take any integer value from 0 to 7, inclusive.
               "
            REFERENCE    "ITU-T G.997.1, paragraph 7.3.2.16"
            DEFVAL       { 0 }
            ::= { vdsl2DelayInpProfEntry 39 }   
            
        hwvdsl2DelayInpProfCh1MinInp8ReinRtxDs  OBJECT-TYPE
            SYNTAX      Unsigned32(0..13)
            MAX-ACCESS  read-create
            STATUS      current
            DESCRIPTION
               "If retransmission is used in downstream direction, this parameter specifies 
                the minimum impulse noise protection against REIN for the bearer channel if it is 
                transported over DMT symbols with a subcarrier spacing of 8.625 kHz. The impulse 
                noise protection is expressed in DMT symbols with a subcarrier spacing of 8.625 kHz 
                and can take any integer value from 0 to 13, inclusive.
               "
            REFERENCE    "ITU-T G.997.1, paragraph 7.3.2.17"
            DEFVAL       { 0 }
            ::= { vdsl2DelayInpProfEntry 40 }             
            
        hwvdsl2DelayInpProfCh1MinInp8ReinRtxUs  OBJECT-TYPE
            SYNTAX      Unsigned32(0..13)
            MAX-ACCESS  read-create
            STATUS      current
            DESCRIPTION
               "If retransmission is used in upstream direction, this parameter specifies 
                the minimum impulse noise protection against REIN for the bearer channel if it is 
                transported over DMT symbols with a subcarrier spacing of 8.625 kHz. The impulse 
                noise protection is expressed in DMT symbols with a subcarrier spacing of 8.625 kHz 
                and can take any integer value from 0 to 13, inclusive.
               "
            REFERENCE    "ITU-T G.997.1, paragraph 7.3.2.17"
            DEFVAL       { 0 }
            ::= { vdsl2DelayInpProfEntry 41 }        
            
        hwvdsl2DelayInpProfCh1IatReinRtxDs  OBJECT-TYPE
            SYNTAX      INTEGER
                        {       
                         frequency100Hz(0),
 	                 frequency120Hz(1)
                        }
            MAX-ACCESS  read-create
            STATUS      current
            DESCRIPTION
               "If retransmission is used in downstream direction, this parameter specifies 
                the inter-arrival time that shall be assumed for REIN protection.
                Options:
	        1. frequency100Hz(0)    - an inter-arrival time derived from a REIN at 100 Hz
                2. frequency120Hz(1)    - an inter-arrival time derived from a REIN at 120 Hz
               "
            REFERENCE    "ITU-T G.997.1, paragraph 7.3.2.18"
            DEFVAL       { frequency100Hz }
            ::= { vdsl2DelayInpProfEntry 42 }               
            
        hwvdsl2DelayInpProfCh1IatReinRtxUs  OBJECT-TYPE
            SYNTAX      INTEGER
                        {       
                         frequency100Hz(0),
                         frequency120Hz(1)
                        }
            MAX-ACCESS  read-create
            STATUS      current
            DESCRIPTION
               "If retransmission is used in upstream direction, this parameter specifies 
                the inter-arrival time that shall be assumed for REIN protection.
                Options:
                1. frequency100Hz(0)    - an inter-arrival time derived from a REIN at 100 Hz
                2. frequency120Hz(1)    - an inter-arrival time derived from a REIN at 120 Hz
               "
            REFERENCE    "ITU-T G.997.1, paragraph 7.3.2.18"
            DEFVAL       { frequency100Hz }
            ::= { vdsl2DelayInpProfEntry 43 }         
          
          --          vdsl2ChConfProfileTable           
        vdsl2ChConfProfileTable  OBJECT-TYPE
            SYNTAX      SEQUENCE  OF  Vdsl2ChConfProfileEntry
            MAX-ACCESS  not-accessible
            STATUS      current
            DESCRIPTION
               "The table vdsl2ChConfProfileTable contains VDSL2 channel
                profile configuration. The index of this table is 
                vdsl2ChConfProfProfileName.   
                A default profile with an index of 'DEFVAL' will
                always exist and its parameters will be set to vendor-specific
                values, unless otherwise specified in this document.
               "
            ::= { vdsl2ProfileChannel 1 }
        
        vdsl2ChConfProfileEntry  OBJECT-TYPE
            SYNTAX      Vdsl2ChConfProfileEntry
            MAX-ACCESS  not-accessible
            STATUS      current
            DESCRIPTION
               "The table vdsl2ChConfProfileTable contains VDSL2 channel
                profile configuration.
                The index of this entry is vdsl2ChConfProfProfileName.
                A default profile with an index of 'DEFVAL' will
                always exist and its parameters will be set to vendor-specific
                values, unless otherwise specified in this document.
               "
            INDEX  { IMPLIED vdsl2ChConfProfProfileName }
            ::= { vdsl2ChConfProfileTable 1 }
        
        Vdsl2ChConfProfileEntry  ::=
           SEQUENCE {
              vdsl2ChConfProfProfileName          OCTET STRING,
              vdsl2ChConfProfMinDataRateDs        Unsigned32,
              vdsl2ChConfProfMinDataRateUs        Unsigned32,
              vdsl2ChConfProfMinResDataRateDs     Unsigned32,
              vdsl2ChConfProfMinResDataRateUs     Unsigned32,
              vdsl2ChConfProfMaxDataRateDs        Unsigned32,
              vdsl2ChConfProfMaxDataRateUs        Unsigned32,
              vdsl2ChConfProfMinDataRateLowPwrDs  Unsigned32,
              vdsl2ChConfProfMinDataRateLowPwrUs  Unsigned32,
              vdsl2ChConfProfMaxDelayDs           Unsigned32,
              vdsl2ChConfProfMaxDelayUs           Unsigned32,
              vdsl2ChConfProfMinProtectionDs      Vdsl2SymbolProtectionDs,
              vdsl2ChConfProfMinProtectionUs      Vdsl2SymbolProtectionUs,
              vdsl2ChConfProfMaxBerDs             Vdsl2MaxBer,
              vdsl2ChConfProfMaxBerUs             Vdsl2MaxBer,
              vdsl2ChConfProfUsDataRateDs         Unsigned32,
              vdsl2ChConfProfDsDataRateDs         Unsigned32,
              vdsl2ChConfProfUsDataRateUs         Unsigned32,
              vdsl2ChConfProfDsDataRateUs         Unsigned32,
              vdsl2ChConfProfImaEnabled           TruthValue,
              vdsl2ChConfProfDataPathMode	  Vdsl2DataPathMode,
              vdsl2ChConfProfRowStatus            RowStatus,
              vdsl2ChConfProfPhyRcontrolDs        Vdsl2PhyRControl,
              vdsl2ChConfProfPhyRcontrolUs        Vdsl2PhyRControl,
              vdsl2ChConfProfInpMaxDs             Vdsl2SymbolProtectionDs,
              vdsl2ChConfProfInpMaxUs             Vdsl2SymbolProtectionDs,
              vdsl2ChConfProfMinRtxRatioDs        Unsigned32,
              vdsl2ChConfProfMinRtxRatioUs        Unsigned32,
              vdsl2ChConfProfMinRSoverheadDs      Unsigned32,
              vdsl2ChConfProfMinRSoverheadUs      Unsigned32,
              vdsl2ChConfProfErasureDecoding	  Vdsl2ProfSwitchType,
              vdsl2ChConfProfMinSosBrDs           Unsigned32,
              vdsl2ChConfProfMinSosBrUs           Unsigned32,
              vdsl2ChConfProfMinEtrRtxDs          Unsigned32, 
              vdsl2ChConfProfMinEtrRtxUs          Unsigned32, 
              vdsl2ChConfProfMaxEtrRtxDs          Unsigned32, 
              vdsl2ChConfProfMaxEtrRtxUs          Unsigned32, 
              vdsl2ChConfProfMaxNdrRtxDs          Unsigned32, 
              vdsl2ChConfProfMaxNdrRtxUs          Unsigned32, 
              vdsl2ChConfProfMaxDelayRtxDs        Unsigned32,  
              vdsl2ChConfProfMaxDelayRtxUs        Unsigned32,
              vdsl2ChConfProfMinDelayRtxDs        Unsigned32,
              vdsl2ChConfProfMinDelayRtxUs        Unsigned32,
              vdsl2ChConfProfMinInpShineRtxDs     Unsigned32,
              vdsl2ChConfProfMinInpShineRtxUs     Unsigned32,
              vdsl2ChConfProfMinInp8ShineRtxDs    Unsigned32,
              vdsl2ChConfProfMinInp8ShineRtxUs    Unsigned32,
              vdsl2ChConfProfShineRatioRtxDs      Unsigned32,
              vdsl2ChConfProfShineRatioRtxUs      Unsigned32,
              vdsl2ChConfProfMinInpReinRtxDs      Unsigned32,
              vdsl2ChConfProfMinInpReinRtxUs      Unsigned32,
              vdsl2ChConfProfMinInp8ReinRtxDs     Unsigned32,
              vdsl2ChConfProfMinInp8ReinRtxUs     Unsigned32,
              vdsl2ChConfProfIatReinRtxDs         INTEGER,
              vdsl2ChConfProfIatReinRtxUs         INTEGER,
              vdsl2ChConfProfInitPolicy           INTEGER              
           }
        
        vdsl2ChConfProfProfileName  OBJECT-TYPE
            SYNTAX      OCTET STRING (SIZE(1..32))
            MAX-ACCESS  not-accessible
            STATUS      current
            DESCRIPTION
               "This object identifies a row in this table.
               "
            ::= { vdsl2ChConfProfileEntry 1 }
            
        vdsl2ChConfProfMinDataRateDs  OBJECT-TYPE
            SYNTAX      Unsigned32(32000..200000000)
            UNITS       "bits/second"
            MAX-ACCESS  read-create
            STATUS      current
            DESCRIPTION
               "If retransmission is not used in downstream direction,this parameter specifics
                minimum data rate for the bearer channel on downstream direction. The rate is 
                coded in steps of 1000 bit/s.
                Unit: bits/second
               "
            REFERENCE    "ITU-T G.997.1, paragraph 7.3.2.1"
            ::= { vdsl2ChConfProfileEntry 2 }
        
        vdsl2ChConfProfMinDataRateUs  OBJECT-TYPE
            SYNTAX      Unsigned32(32000..200000000)
            UNITS       "bits/second"
            MAX-ACCESS  read-create
            STATUS      current
            DESCRIPTION
               "If retransmission is not used in upstream direction,this parameter specifics
                minimum data rate for the bearer channel on upstream direction. The rate is 
                coded in steps of 1000 bit/s
                Unit: bits/second
               "
            REFERENCE    "ITU-T G.997.1, paragraph 7.3.2.1"
            ::= { vdsl2ChConfProfileEntry 3 }
        
        vdsl2ChConfProfMinResDataRateDs  OBJECT-TYPE
            SYNTAX      Unsigned32(32000..200000000)
            UNITS       "bits/second"
            MAX-ACCESS  read-create
            STATUS      current
            DESCRIPTION
                "Minimum Reserved Data Rate on Downstream direction.  The
                 minimum reserved net data rate for the bearer channel, coded
                 in bit/s.  This parameter is used only if the Rate Adaptation
                 Mode in the direction of the bearer channel (i.e.,
                 Vdsl2LineConfRaModeDs) is set to DynamicRa.
                 Unit: bits/second
                "
            REFERENCE    "ITU-T G.997.1, paragraph 7.3.2.1"
            ::= { vdsl2ChConfProfileEntry 4 }
        
        vdsl2ChConfProfMinResDataRateUs  OBJECT-TYPE
            SYNTAX      Unsigned32(32000..200000000)
            UNITS       "bits/second"
            MAX-ACCESS  read-create
            STATUS      current
            DESCRIPTION
               "Minimum Reserved Data Rate on Upstream direction.  The minimum
                reserved net data rate for the bearer channel, coded in
                bit/s.  This parameter is used only if the Rate Adaptation
                Mode in the direction of the bearer channel (i.e.,
                Vdsl2LineConfRaModeUs) is set to DynamicRa.
                Unit: bits/second
               "
            REFERENCE    "ITU-T G.997.1, paragraph 7.3.2.1"
            ::= { vdsl2ChConfProfileEntry 5 }
        
        vdsl2ChConfProfMaxDataRateDs  OBJECT-TYPE
            SYNTAX      Unsigned32(32000..200000000)
            UNITS       "bits/second"
            MAX-ACCESS  read-create
            STATUS      current
            DESCRIPTION
               "If retransmission is not used in downstream direction,this parameter specifics
                maximum data rate for the bearer channel on downstream direction. The rate is 
                coded in steps of 1000 bit/s.          
                Unit: bits/second
               "
            REFERENCE    "ITU-T G.997.1, paragraph 7.3.2.1"
            ::= { vdsl2ChConfProfileEntry 6 }
        
        vdsl2ChConfProfMaxDataRateUs  OBJECT-TYPE
            SYNTAX      Unsigned32(32000..200000000)
            UNITS       "bits/second"
            MAX-ACCESS  read-create
            STATUS      current
            DESCRIPTION
               "If retransmission is not used in upstream direction,this parameter specifics
                maximum data rate for the bearer channel on upstream direction. The rate is 
                coded in steps of 1000 bit/s.
                Unit: bits/second
               "
            REFERENCE    "ITU-T G.997.1, paragraph 7.3.2.1"
            ::= { vdsl2ChConfProfileEntry 7 }
        
        vdsl2ChConfProfMinDataRateLowPwrDs  OBJECT-TYPE
            SYNTAX      Unsigned32(0..200000000)
            UNITS       "bits/second"
            MAX-ACCESS  read-create
            STATUS      current
            DESCRIPTION
                "Minimum Data Rate in Low Power state on Downstream direction.
                 The minimum net data rate for the bearer channel, coded in
                 bit/s, during the low power state (L1 in G.992.2, L2 in
                 G.992.3).
                 Unit: bits/second
                "
            REFERENCE    "ITU-T G.997.1, paragraph 7.3.2.1"
            ::= { vdsl2ChConfProfileEntry 8 }
        
        vdsl2ChConfProfMinDataRateLowPwrUs  OBJECT-TYPE
            SYNTAX      Unsigned32(0..200000000)
            UNITS       "bits/second"
            MAX-ACCESS  read-create
            STATUS      current
            DESCRIPTION
               "Minimum Data Rate in Low Power state on Upstream direction.
                The minimum net data rate for the bearer channel, coded in
                bit/s, during the low power state (L1 in G.992.2, L2 in
                G.992.3).
                Unit: bits/second
               "
            REFERENCE    "ITU-T G.997.1, paragraph 7.3.2.1"
            ::= { vdsl2ChConfProfileEntry 9 }
        
        vdsl2ChConfProfMaxDelayDs  OBJECT-TYPE
            SYNTAX Unsigned32 (0..200 | 255)
            UNITS       "milliseconds"
            MAX-ACCESS  read-create
            STATUS      current
            DESCRIPTION
                "If retransmission is not used in downstream direction,this parameter
                 is maximum interleave delay on downstream direction. The maximum
                 one-way interleaving delay introduced by the PMS-TC on
                 Downstream direction.  The XTUs shall choose the S (factor)
                 and D (depth) values such that the actual one-way interleaving
                 delay (Vdsl2ChanStatusActDelay) is as close as possible to,
                 but less than or equal to, Vdsl2ChanConfMaxDelayDs.  The
                 delay is coded in ms, with the value 0 indicating no delay bound is being imposed.
                 
                 The delay is coded in ms, with the special values 0, 1 and 255.
                 - The value 0 indicates no delay bound is being imposed.
                 - The value 1 indicates the Fast Latency Path shall be used in the G.992.1 operating mode
                   and S and D shall be selected such that S <= 1 and D = 1 in ITU-T Recs G.992.2, G.992.3
                   and G.992.4 operating modes (G.997.1 special value S1).
                 - The value 255 indicates a delay bound of 1 ms in ITU-T Recs G.993.2 (G.997.1 special value S2).
                 Unit: milliseconds
                "
            REFERENCE    "ITU-T G.997.1, paragraph 7.3.2.2 (Maximum interleaving delay)"
            ::= { vdsl2ChConfProfileEntry 10 }
        
        vdsl2ChConfProfMaxDelayUs  OBJECT-TYPE
            SYNTAX Unsigned32 (0..200 | 255)
            UNITS       "milliseconds"
            MAX-ACCESS  read-create
            STATUS      current
            DESCRIPTION
                "If retransmission is not used in upstream direction,this parameter
                 is maximum interleave delay on upstream direction. The maximum
                 one-way interleaving delay introduced by the PMS-TC on
                 Upstream direction.  The XTUs shall choose the S (factor) and
                 D (depth) values such that the actual one-way interleaving
                 delay (Vdsl2ChanStatusActDelay) is as close as possible to,
                 but less than or equal to, Vdsl2ChanConfMaxDelayUs.  The
                 delay is coded in ms, with the value 0 indicating no delay bound is being imposed.
                 
                 The delay is coded in ms, with the special values 0, 1 and 255.
                 - The value 0 indicates no delay bound is being imposed.
                 - The value 1 indicates the Fast Latency Path shall be used in the G.992.1 operating mode
                   and S and D shall be selected such that S <= 1 and D = 1 in ITU-T Recs G.992.2, G.992.3
                   and G.992.4 operating modes (G.997.1 special value S1).
                 - The value 255 indicates a delay bound of 1 ms in ITU-T Recs G.993.2 (G.997.1 special value S2).
                 Unit: milliseconds
                "
            REFERENCE    "ITU-T G.997.1, paragraph 7.3.2.2 (Maximum interleaving delay)"
            ::= { vdsl2ChConfProfileEntry 11 }
           
        vdsl2ChConfProfMinProtectionDs  OBJECT-TYPE
            SYNTAX      Vdsl2SymbolProtectionDs
            UNITS       "symbols"
            MAX-ACCESS  read-create
            STATUS      current
            DESCRIPTION
                "If retransmission is not used in downstream direction,this parameter
                 is minimum impulse noise protection for the bearer channel on downstream
                 direction. The minimum impulse noise protection for the bearer channel,
                 expressed in symbols.  The parameter can take the following
                 values: noProtection (i.e., INP not required), halfSymbol
                 (i.e., INP length is 1/2 symbol) and 1-16 symbols in steps
                 of 1 symbol.
                 Unit: symbols
                "
            REFERENCE    "ITU-T G.997.1, paragraph 7.3.2.3"
            DEFVAL       { noProtection }
            ::= { vdsl2ChConfProfileEntry 12 }
        
        vdsl2ChConfProfMinProtectionUs  OBJECT-TYPE
            SYNTAX      Vdsl2SymbolProtectionUs
            UNITS       "symbols"
            MAX-ACCESS  read-create
            STATUS      current
            DESCRIPTION
                "If retransmission is not used in upstream direction,this parameter
                 is minimum impulse noise protection for the bearer channel on upstream
                 direction. The minimum impulse noise protection for the bearer channel,
                 expressed in symbols.  The parameter can take the following
                 values: noProtection (i.e., INP not required), halfSymbol
                 (i.e., INP length is 1/2 symbol) and 1-16 symbols in steps
                 of 1 symbol.
                 Unit: symbols
                "
            REFERENCE    "ITU-T G.997.1, paragraph 7.3.2.3"
            DEFVAL       { noProtection }
            ::= { vdsl2ChConfProfileEntry 13 }
        
        vdsl2ChConfProfMaxBerDs  OBJECT-TYPE
            SYNTAX      Vdsl2MaxBer
            MAX-ACCESS  read-create
            STATUS      current
            DESCRIPTION
                "Maximum Bit Error Ratio on Downstream direction.  The maximum
                 bit error ratio for the bearer channel.  The parameter can
                 take the following values (for 1E-3, 1E-5 or 1E-7).
                 Options:
                 1. eminus3 (1) - 1E-3
                 2. eminus5 (2) - 1E-5
                 3. eminus7 (3) - 1E-7
                "
            REFERENCE    "ITU-T G.997.1, paragraph 7.3.2.4"
            DEFVAL       { eminus5 }
            ::= { vdsl2ChConfProfileEntry 14 }
        
        vdsl2ChConfProfMaxBerUs  OBJECT-TYPE
            SYNTAX      Vdsl2MaxBer
            MAX-ACCESS  read-create
            STATUS      current
            DESCRIPTION
                "Maximum Bit Error Ratio on Upstream direction.  The maximum
                 bit error ratio for the bearer channel.  The parameter can
                 take the following values (for 1E-3, 1E-5 or 1E-7).
                 Options:
                 1. eminus3 (1)  - 1E-3
                 2. eminus5 (2)  - 1E-5
                 3. eminus7 (3)  - 1E-7
                 "
            REFERENCE    "ITU-T G.997.1, paragraph 7.3.2.4"
            DEFVAL       { eminus5 }
            ::= { vdsl2ChConfProfileEntry 15 }
        
        vdsl2ChConfProfUsDataRateDs  OBJECT-TYPE
            SYNTAX      Unsigned32(0..200000000)
            UNITS       "bits/second"
            MAX-ACCESS  read-create
            STATUS      current
            DESCRIPTION
                "If retransmission is not used in downstream direction,this parameter
                 is data rate threshold upshift for downstream direction. An
                 'Up-shift rate change' event is triggered when the actual
                 downstream data rate exceeds, by more than the threshold, the
                 data rate at the last entry into Showtime.  The parameter is
                 coded in bit/s.
                 Unit: bits/second
                "
            REFERENCE    "ITU-T G.997.1, paragraph 7.3.2.8"
            ::= { vdsl2ChConfProfileEntry 16 }
        
        vdsl2ChConfProfDsDataRateDs  OBJECT-TYPE
            SYNTAX      Unsigned32(0..200000000)
            UNITS       "bits/second"
            MAX-ACCESS  read-create
            STATUS      current
            DESCRIPTION
                "If retransmission is not used in downstream direction,this parameter
                 is data rate threshold downshift for downstream direction.  A
                 'Down-shift rate change' event is triggered when the actual
                 downstream data rate is below the data rate at the last entry
                 into Showtime, by more than the threshold.  The parameter is
                 coded in bit/s.
                 Unit: bits/second
                "
            REFERENCE    "ITU-T G.997.1, paragraph 7.3.2.8"
            ::= { vdsl2ChConfProfileEntry 17 }
        
        vdsl2ChConfProfUsDataRateUs  OBJECT-TYPE
            SYNTAX      Unsigned32(0..200000000)
            UNITS       "bits/second"
            MAX-ACCESS  read-create
            STATUS      current
            DESCRIPTION
                "If retransmission is not used in upstream direction,this parameter
                 is data rate threshold up shift for upstream direction.  An
                 'Up-shift rate change' event is triggered when the actual
                 upstream data rate exceeds, by more than the threshold, the
                 data rate at the last entry into Showtime.  The parameter is
                 coded in bit/s.
                 Unit: bits/second
                 "
            REFERENCE    "ITU-T G.997.1, paragraph 7.3.2.8"
            ::= { vdsl2ChConfProfileEntry 18 }
            
        vdsl2ChConfProfDsDataRateUs  OBJECT-TYPE
            SYNTAX      Unsigned32(0..200000000)
            UNITS       "bits/second"
            MAX-ACCESS  read-create
            STATUS      current
            DESCRIPTION
                "If retransmission is not used in upstream direction,this parameter
                 is data rate threshold downshift for upstream direction.  A
                 'Down-shift rate change' event is triggered when the actual
                 upstream data rate is below the data rate at the last entry
                 into Showtime, by more than the threshold.  The parameter is
                 coded in bit/s.
                 Unit: bits/second
                "
            REFERENCE    "ITU-T G.997.1, paragraph 7.3.2.8"
            ::= { vdsl2ChConfProfileEntry 19 }
        
        vdsl2ChConfProfImaEnabled  OBJECT-TYPE
            SYNTAX      TruthValue
            MAX-ACCESS  read-create
            STATUS      current
            DESCRIPTION
                "IMA Mode Enable.  The parameter enables the IMA operation mode
                 in the ATM Data Path.  Relevant only if the channel is of ATM
                 Data Path.  When in 'enable' state, the ATM data path should
                 comply with the requirements for IMA transmission.
                "
            REFERENCE    "ITU-T G.997.1, paragraph 7.3.4.1"
            DEFVAL       { false }
            ::= { vdsl2ChConfProfileEntry 20 }
        
        vdsl2ChConfProfDataPathMode  OBJECT-TYPE
            SYNTAX      Vdsl2DataPathMode
            MAX-ACCESS  read-create
            STATUS      current
            DESCRIPTION
                "The channel data path mode.
                 Options:
                 1. atm(1)               - ATM
                 2. ptm(2)               - PTM 
                 3. both(3)              - ATM and PTM 
                 Huawei defined.
                "
            DEFVAL       { both }
            ::= { vdsl2ChConfProfileEntry 21 }
        
        vdsl2ChConfProfRowStatus  OBJECT-TYPE
            SYNTAX      RowStatus
            MAX-ACCESS  read-create
            STATUS      current
            DESCRIPTION
                "This object is used to create a new row or to modify or
                 delete an existing row in this table.
                 
                 A profile is activated by setting this object to 'active'.
                 When 'active' is set, the system will validate the profile.
                 
                 Before a profile can be deleted or taken out of service
                 (by setting this object to 'destroy' or 'outOfService'),
                 it must be not referenced from all associated
                 templates.
                "
            ::= { vdsl2ChConfProfileEntry 22 }
        vdsl2ChConfProfPhyRcontrolDs  OBJECT-TYPE
            SYNTAX      Vdsl2PhyRControl
            MAX-ACCESS  read-create
            STATUS      current
            DESCRIPTION
                "To enable or disable the retransmission function."
            DEFVAL       { disable }
            ::= { vdsl2ChConfProfileEntry 23 }
           
        vdsl2ChConfProfPhyRcontrolUs  OBJECT-TYPE
            SYNTAX      Vdsl2PhyRControl
            MAX-ACCESS  read-create
            STATUS      current
            DESCRIPTION
               "To enable or disable the retransmission function."
            DEFVAL       { disable }
            ::= { vdsl2ChConfProfileEntry 24 }
           
        vdsl2ChConfProfInpMaxDs  OBJECT-TYPE
            SYNTAX      Vdsl2SymbolProtectionDs
            MAX-ACCESS  read-create
            STATUS      current
            DESCRIPTION
               "Maximum Impulse Noise Protection on downstream direction."
            ::= { vdsl2ChConfProfileEntry 25 }
           
        vdsl2ChConfProfInpMaxUs  OBJECT-TYPE
            SYNTAX      Vdsl2SymbolProtectionDs
            MAX-ACCESS  read-create
            STATUS      current
            DESCRIPTION
               "Maximum Impulse Noise Protection on upstream direction."
            ::= { vdsl2ChConfProfileEntry 26 }
            
        vdsl2ChConfProfMinRtxRatioDs  OBJECT-TYPE
            SYNTAX      Unsigned32(0..255)
            MAX-ACCESS  read-create
            STATUS      current
            DESCRIPTION
               "This object is used to config the minimum retransmission band width parameter downstream."
            ::= { vdsl2ChConfProfileEntry 27 }
           
        vdsl2ChConfProfMinRtxRatioUs  OBJECT-TYPE
            SYNTAX      Unsigned32(0..255)
            MAX-ACCESS  read-create
            STATUS      current
            DESCRIPTION
               "This object is used to config the minimum retransmission band width parameter upstream."
            ::= { vdsl2ChConfProfileEntry 28 }
           
        vdsl2ChConfProfMinRSoverheadDs  OBJECT-TYPE
            SYNTAX      Unsigned32(0..128)
            MAX-ACCESS  read-create
            STATUS      current
            DESCRIPTION
                "This object is used to config the minimum RSoverhead parameter downstream.."
            ::= { vdsl2ChConfProfileEntry 29 }
         
        vdsl2ChConfProfMinRSoverheadUs  OBJECT-TYPE
            SYNTAX      Unsigned32(0..128)
            MAX-ACCESS  read-create
            STATUS      current
            DESCRIPTION
               "This object is used to config the minimum RSoverhead parameter upstream.."
            ::= { vdsl2ChConfProfileEntry 30 }
         
        vdsl2ChConfProfErasureDecoding  OBJECT-TYPE
            SYNTAX      Vdsl2ProfSwitchType
            MAX-ACCESS  read-create
            STATUS      current
            DESCRIPTION
               "To enable or disable the erasure decoding of a channel.
                Options:
                1. enable(1)
                2. disable(2)
                "
            DEFVAL       { disable }
            ::= { vdsl2ChConfProfileEntry 31 }
         
        vdsl2ChConfProfMinSosBrDs  OBJECT-TYPE
            SYNTAX      Unsigned32(0..65535)
            UNITS       "8Kbps"
            MAX-ACCESS  read-create
            STATUS      current
            DESCRIPTION
               "This parameter specifies the minimum net data rate required for a valid SOS request in 
                the downstream direction. The valid range of values is from 0 to 524280Kbps in steps of 8Kbps.
                Unit: 8Kbps
               "
            REFERENCE    "ITU-T G.997.1, paragraph 7.3.2.1.6"
            ::= { vdsl2ChConfProfileEntry 32 }
           
        vdsl2ChConfProfMinSosBrUs  OBJECT-TYPE
            SYNTAX      Unsigned32(0..65535)
            UNITS       "8Kbps"
            MAX-ACCESS  read-create
            STATUS      current
            DESCRIPTION
               "This parameter specifies the minimum net data rate required for a valid SOS request in 
                the upstream direction.The valid range of values is from 0 to 524280Kbps in steps of 8Kbps.
                Unit: 8Kbps
               "
            REFERENCE    "ITU-T G.997.1, paragraph 7.3.2.1.7"
            ::= { vdsl2ChConfProfileEntry 33 }
            
        vdsl2ChConfProfMinEtrRtxDs  OBJECT-TYPE
            SYNTAX      Unsigned32(32000..200000000)
            UNITS       "bits/second"
            MAX-ACCESS  read-create
            STATUS      current
            DESCRIPTION
               "If retransmission is used in downstream direction, this parameter specifies the
                minimum expected throughput for the bearer channel.The values range in steps of 
                1000 bit/s.
               "
            REFERENCE    "ITU-T G.997.1, paragraph 7.3.2.1.8"
            ::= { vdsl2ChConfProfileEntry 34 }            
            
        vdsl2ChConfProfMinEtrRtxUs  OBJECT-TYPE
            SYNTAX      Unsigned32(32000..200000000)
            UNITS       "bits/second"
            MAX-ACCESS  read-create
            STATUS      current
            DESCRIPTION
               "If retransmission is used in upstream direction, this parameter specifies the
                minimum expected throughput for the bearer channel.The values range in steps of 
                1000 bit/s. 
               "
            REFERENCE    "ITU-T G.997.1, paragraph 7.3.2.1.8"
            ::= { vdsl2ChConfProfileEntry 35 }               
            
        vdsl2ChConfProfMaxEtrRtxDs  OBJECT-TYPE
            SYNTAX      Unsigned32(32000..200000000)
            UNITS       "bits/second"
            MAX-ACCESS  read-create
            STATUS      current
            DESCRIPTION
               "If retransmission is used in downstream direction, this parameter specifies the
                maximum expected throughput for the bearer channel.The values range in steps of 
                1000 bit/s. 
               "
            REFERENCE    "ITU-T G.997.1, paragraph 7.3.2.1.9"
            ::= { vdsl2ChConfProfileEntry 36 }            
            
        vdsl2ChConfProfMaxEtrRtxUs  OBJECT-TYPE
            SYNTAX      Unsigned32(32000..200000000)
            UNITS       "bits/second"
            MAX-ACCESS  read-create
            STATUS      current
            DESCRIPTION
               "If retransmission is used in upstream direction, this parameter specifies the
                maximum expected throughput for the bearer channel.The values range in steps of 
                1000 bit/s. 
               "
            REFERENCE    "ITU-T G.997.1, paragraph 7.3.2.1.9"
            ::= { vdsl2ChConfProfileEntry 37 } 
            
        vdsl2ChConfProfMaxNdrRtxDs  OBJECT-TYPE
            SYNTAX      Unsigned32(32000..200000000)
            UNITS       "bits/second"
            MAX-ACCESS  read-create
            STATUS      current
            DESCRIPTION
               "If retransmission is used in downstream direction, this parameter specifies the 
                maximum net data rate for the bearer channel. The values range in steps of 1000 bit/s.
               "
            REFERENCE    "ITU-T G.997.1, paragraph 7.3.2.1.10"
            ::= { vdsl2ChConfProfileEntry 38 }            
            
        vdsl2ChConfProfMaxNdrRtxUs  OBJECT-TYPE
            SYNTAX      Unsigned32(32000..200000000)
            UNITS       "bits/second"
            MAX-ACCESS  read-create
            STATUS      current
            DESCRIPTION
               "If retransmission is used in upstream direction, this parameter specifies the 
                maximum net data rate for the bearer channel.The values range in steps of 1000 bit/s.
               "
            REFERENCE    "ITU-T G.997.1, paragraph 7.3.2.1.10"
            ::= { vdsl2ChConfProfileEntry 39 }             
            
        vdsl2ChConfProfMaxDelayRtxDs  OBJECT-TYPE
            SYNTAX      Unsigned32(1..63)
            UNITS       "milliseconds"
            MAX-ACCESS  read-create
            STATUS      current
            DESCRIPTION
               "If retransmission is used in downstream direction, this parameter specifies 
                the maximum for the instantaneous delay due to the effect of retransmission only 
                (see G.998.4 for detailed specification). The delay ranges from 1 to 63 ms by steps of 1 ms. 
                Unit: milliseconds
               "
            REFERENCE    "ITU-T G.997.1, paragraph 7.3.2.11"
            ::= { vdsl2ChConfProfileEntry 40 }   

        vdsl2ChConfProfMaxDelayRtxUs  OBJECT-TYPE
            SYNTAX      Unsigned32(1..63)
            UNITS       "milliseconds"
            MAX-ACCESS  read-create
            STATUS      current
            DESCRIPTION
               "If retransmission is used in upstream direction, this parameter specifies 
                the maximum for the instantaneous delay due to the effect of retransmission only 
                (see G.998.4 for detailed specification). The delay ranges from 1 to 63 ms by steps of 1 ms. 
                Unit: milliseconds
               "
            REFERENCE    "ITU-T G.997.1, paragraph 7.3.2.11"
            ::= { vdsl2ChConfProfileEntry 41 }   

        vdsl2ChConfProfMinDelayRtxDs  OBJECT-TYPE
            SYNTAX      Unsigned32(0..63)
            UNITS       "milliseconds"
            MAX-ACCESS  read-create
            STATUS      current
            DESCRIPTION
               "If retransmission is used in downstream direction, this parameter specifies 
                the minimum for the instantaneous delay due to the effect of retransmission only 
                (see G.998.4 for detailed specification). The delay ranges from 0 to 63 ms by steps of 1 ms. 
                Unit: milliseconds
               "
            REFERENCE    "ITU-T G.997.1, paragraph 7.3.2.12"
            ::= { vdsl2ChConfProfileEntry 42 }   

        vdsl2ChConfProfMinDelayRtxUs  OBJECT-TYPE
            SYNTAX      Unsigned32(0..63)
            UNITS       "milliseconds"
            MAX-ACCESS  read-create
            STATUS      current
            DESCRIPTION
               "If retransmission is used in upstream direction, this parameter specifies 
                the minimum for the instantaneous delay due to the effect of retransmission only 
                (see G.998.4 for detailed specification). The delay ranges from 0 to 63 ms by steps of 1 ms. 
                Unit: milliseconds
               "
            REFERENCE    "ITU-T G.997.1, paragraph 7.3.2.12"
            ::= { vdsl2ChConfProfileEntry 43 } 

        vdsl2ChConfProfMinInpShineRtxDs  OBJECT-TYPE
            SYNTAX      Unsigned32(0..63)
            UNITS       "symbols"
            MAX-ACCESS  read-create
            STATUS      current
            DESCRIPTION
               "If retransmission is used in downstream direction, this parameter specifies 
                the minimum impulse noise protection against SHINE for the bearer channel if it is 
                transported over DMT symbols with a subcarrier spacing of 4.3125 kHz. The impulse 
                noise protection is expressed in DMT symbols with a subcarrier spacing of 4.3125 kHz 
                and can take any integer value from 0 to 63, inclusive.
                Unit: symbols
               "
            REFERENCE    "ITU-T G.997.1, paragraph 7.3.2.13"
            DEFVAL       { 0 }
            ::= { vdsl2ChConfProfileEntry 44 } 

        vdsl2ChConfProfMinInpShineRtxUs  OBJECT-TYPE
            SYNTAX      Unsigned32(0..63)
            UNITS       "symbols"
            MAX-ACCESS  read-create
            STATUS      current
            DESCRIPTION
               "If retransmission is used in upstream direction, this parameter specifies the 
                minimum impulse noise protection against SHINE for the bearer channel if it is 
                transported over DMT symbols with a subcarrier spacing of 4.3125 kHz. The impulse 
                noise protection is expressed in DMT symbols with a subcarrier spacing of 4.3125 kHz 
                and can take any integer value from 0 to 63, inclusive.
                Unit: symbols
               "
            REFERENCE    "ITU-T G.997.1, paragraph 7.3.2.13"
            DEFVAL       { 0 }
            ::= { vdsl2ChConfProfileEntry 45 } 

        vdsl2ChConfProfMinInp8ShineRtxDs  OBJECT-TYPE
            SYNTAX      Unsigned32(0..127)
            UNITS       "symbols"
            MAX-ACCESS  read-create
            STATUS      current
            DESCRIPTION
               "If retransmission is used in downstream direction, this parameter specifies 
                the minimum impulse noise protection against SHINE for the bearer channel if it is 
                transported over DMT symbols with a subcarrier spacing of 8.625 kHz. The impulse 
                noise protection is expressed in DMT symbols with a subcarrier spacing of 8.625 kHz 
                and can take any integer value from 0 to 127, inclusive.
                Unit: symbols
               "
            REFERENCE    "ITU-T G.997.1, paragraph 7.3.2.14"
            DEFVAL       { 0 }
            ::= { vdsl2ChConfProfileEntry 46 } 

        vdsl2ChConfProfMinInp8ShineRtxUs  OBJECT-TYPE
            SYNTAX      Unsigned32(0..127)
            UNITS       "symbols"
            MAX-ACCESS  read-create
            STATUS      current
            DESCRIPTION
               "If retransmission is used in upstream direction, this parameter specifies the 
                minimum impulse noise protection against SHINE for the bearer channel if it is 
                transported over DMT symbols with a subcarrier spacing of 8.625 kHz. The impulse 
                noise protection is expressed in DMT symbols with a subcarrier spacing of 8.625 kHz 
                and can take any integer value from 0 to 127, inclusive.
                Unit: symbols
               "
            REFERENCE    "ITU-T G.997.1, paragraph 7.3.2.14"
            DEFVAL       { 0 }
            ::= { vdsl2ChConfProfileEntry 47 } 

        vdsl2ChConfProfShineRatioRtxDs  OBJECT-TYPE
            SYNTAX      Unsigned32(0..100)
            MAX-ACCESS  read-create
            STATUS      current
            DESCRIPTION
               "If retransmission is used in downstream direction, this parameter specifies 
                the SHINE ratio (detailed definition see G.998.4).
                The values range from 0 to 0.100 in increments of 0.001.
               "
            REFERENCE    "ITU-T G.997.1, paragraph 7.3.2.15"
            DEFVAL       { 0 }
            ::= { vdsl2ChConfProfileEntry 48 } 

        vdsl2ChConfProfShineRatioRtxUs  OBJECT-TYPE
            SYNTAX      Unsigned32(0..100)
            MAX-ACCESS  read-create
            STATUS      current
            DESCRIPTION
               "If retransmission is used in upstream direction, this parameter specifies 
                the SHINE ratio (detailed definition see G.998.4).
                The values range from 0 to 0.100 in increments of 0.001.
               "
            REFERENCE    "ITU-T G.997.1, paragraph 7.3.2.15"
            DEFVAL       { 0 }
            ::= { vdsl2ChConfProfileEntry 49 } 
            
        vdsl2ChConfProfMinInpReinRtxDs  OBJECT-TYPE
            SYNTAX      Unsigned32(0..7)
            MAX-ACCESS  read-create
            STATUS      current
            DESCRIPTION
               "If retransmission is used in downstream direction, this parameter specifies 
                the minimum impulse noise protection against REIN for the bearer channel if it is 
                transported over DMT symbols with a subcarrier spacing of 4.3125 kHz. The impulse 
                noise protection is expressed in DMT symbols with a subcarrier spacing of 4.3125 kHz 
                and can take any integer value from 0 to 7, inclusive.
               "
            REFERENCE    "ITU-T G.997.1, paragraph 7.3.2.16"
            DEFVAL       { 0 }
            ::= { vdsl2ChConfProfileEntry 50 }             
            
        vdsl2ChConfProfMinInpReinRtxUs  OBJECT-TYPE
            SYNTAX      Unsigned32(0..7)
            MAX-ACCESS  read-create
            STATUS      current
            DESCRIPTION
               "If retransmission is used in upstream direction, this parameter specifies 
                the minimum impulse noise protection against REIN for the bearer channel if it is 
                transported over DMT symbols with a subcarrier spacing of 4.3125 kHz. The impulse 
                noise protection is expressed in DMT symbols with a subcarrier spacing of 4.3125 kHz 
                and can take any integer value from 0 to 7, inclusive.
               "
            REFERENCE    "ITU-T G.997.1, paragraph 7.3.2.16"
            DEFVAL       { 0 }
            ::= { vdsl2ChConfProfileEntry 51 }   
            
        vdsl2ChConfProfMinInp8ReinRtxDs  OBJECT-TYPE
            SYNTAX      Unsigned32(0..13)
            MAX-ACCESS  read-create
            STATUS      current
            DESCRIPTION
               "If retransmission is used in downstream direction, this parameter specifies 
                the minimum impulse noise protection against REIN for the bearer channel if it is 
                transported over DMT symbols with a subcarrier spacing of 8.625 kHz. The impulse 
                noise protection is expressed in DMT symbols with a subcarrier spacing of 8.625 kHz 
                and can take any integer value from 0 to 13, inclusive.
               "
            REFERENCE    "ITU-T G.997.1, paragraph 7.3.2.17"
            DEFVAL       { 0 }
            ::= { vdsl2ChConfProfileEntry 52 }             
            
        vdsl2ChConfProfMinInp8ReinRtxUs  OBJECT-TYPE
            SYNTAX      Unsigned32(0..13)
            MAX-ACCESS  read-create
            STATUS      current
            DESCRIPTION
               "If retransmission is used in upstream direction, this parameter specifies 
                the minimum impulse noise protection against REIN for the bearer channel if it is 
                transported over DMT symbols with a subcarrier spacing of 8.625 kHz. The impulse 
                noise protection is expressed in DMT symbols with a subcarrier spacing of 8.625 kHz 
                and can take any integer value from 0 to 13, inclusive.
               "
            REFERENCE    "ITU-T G.997.1, paragraph 7.3.2.17"
            DEFVAL       { 0 }
            ::= { vdsl2ChConfProfileEntry 53 }        
            
        vdsl2ChConfProfIatReinRtxDs  OBJECT-TYPE
            SYNTAX      INTEGER
                        {       
                         frequency100Hz(0),
 	                 frequency120Hz(1)
                        }
            MAX-ACCESS  read-create
            STATUS      current
            DESCRIPTION
               "If retransmission is used in downstream direction, this parameter specifies 
                the inter-arrival time that shall be assumed for REIN protection.
                Options:
	        1. frequency100Hz(0)    - an inter-arrival time derived from a REIN at 100 Hz
                2. frequency120Hz(1)    - an inter-arrival time derived from a REIN at 120 Hz
               "
            REFERENCE    "ITU-T G.997.1, paragraph 7.3.2.18"
            DEFVAL       { frequency100Hz }
            ::= { vdsl2ChConfProfileEntry 54 }               
            
        vdsl2ChConfProfIatReinRtxUs  OBJECT-TYPE
            SYNTAX      INTEGER
                        {       
                         frequency100Hz(0),
                         frequency120Hz(1)
                        }
            MAX-ACCESS  read-create
            STATUS      current
            DESCRIPTION
               "If retransmission is used in upstream direction, this parameter specifies 
                the inter-arrival time that shall be assumed for REIN protection.
                Options:
                1. frequency100Hz(0)    - an inter-arrival time derived from a REIN at 100 Hz
                2. frequency120Hz(1)    - an inter-arrival time derived from a REIN at 120 Hz
               "
            REFERENCE    "ITU-T G.997.1, paragraph 7.3.2.18"
            DEFVAL       { frequency100Hz }
            ::= { vdsl2ChConfProfileEntry 55 }                     
          
        vdsl2ChConfProfInitPolicy   OBJECT-TYPE
        SYNTAX INTEGER 
               {
                   policy0(1),
                   policy1(2),
                   policy2(3)
               }
        MAX-ACCESS read-create
        STATUS current
        DESCRIPTION
            "This parameter indicates which policy shall be applied to 
             determine the transceiver configuration parameters at 
             initialization. The valid values for CIPOLICY are 0,1 and 2. 
             Those policies are defined in the respective recommendations.
             Options:
             1. policy0 (1)      - Policy 0 according to the applicable standard
             2. policy1 (2)      - Policy 1 according to the applicable standard
             3. policy2 (3)      - Policy 2 according to the applicable standard
            "
        REFERENCE
            "ITU-T G.997.1 Amendment 1, paragraph #7.3.2.10 (CIPOLICY)"
        DEFVAL { policy0 }
        ::= { vdsl2ChConfProfileEntry 56 }
                      
          --        vdsl2LineAlarmConfTemplateTable          
        vdsl2LineAlarmConfTemplateTable  OBJECT-TYPE
            SYNTAX      SEQUENCE  OF  Vdsl2LineAlarmConfTemplateEntry
            MAX-ACCESS  not-accessible
            STATUS      current
            DESCRIPTION
               "The table vdsl2LineAlarmConfTemplateTable contains VDSL2 line
                alarm configuration template. 
                The index of this table is vdsl2LAlarmConfTempTemplateName.    
                A default template with an index of 'DEFVAL' will
                always exist and its parameters will be set to vendor
                specific values, unless otherwise specified in this
                document.
               "           
            ::= { vdsl2ProfileAlarmConf 1 }
        
        vdsl2LineAlarmConfTemplateEntry  OBJECT-TYPE
            SYNTAX      Vdsl2LineAlarmConfTemplateEntry
            MAX-ACCESS  not-accessible
            STATUS      current
            DESCRIPTION
                "The table vdsl2LineAlarmConfTemplateTable contains VDSL2 line
                 alarm configuration template. 
                 The index of this entry is vdsl2LAlarmConfTempTemplateName.
                 A default template with an index of 'DEFVAL' will
                 always exist and its parameters will be set to vendor
                 specific values, unless otherwise specified in this
                 document.
                "
            INDEX  { IMPLIED vdsl2LAlarmConfTempTemplateName }
            ::= { vdsl2LineAlarmConfTemplateTable 1 }
        
        Vdsl2LineAlarmConfTemplateEntry  ::=
            SEQUENCE {
              vdsl2LAlarmConfTempTemplateName      OCTET STRING,
              vdsl2LAlarmConfTempLineProfile       OCTET STRING,
              vdsl2LAlarmConfTempChan1ConfProfile  OCTET STRING,
              vdsl2LAlarmConfTempChan2ConfProfile  OCTET STRING,
              vdsl2LAlarmConfTempChan3ConfProfile  OCTET STRING,
              vdsl2LAlarmConfTempChan4ConfProfile  OCTET STRING,
              vdsl2LAlarmConfTempRowStatus         RowStatus
            }
        
        vdsl2LAlarmConfTempTemplateName  OBJECT-TYPE
            SYNTAX      OCTET STRING (SIZE(1..32))
            MAX-ACCESS  not-accessible
            STATUS      current
            DESCRIPTION
                "This object identifies a row in this table."
            ::= { vdsl2LineAlarmConfTemplateEntry 1 }
        
        vdsl2LAlarmConfTempLineProfile  OBJECT-TYPE
            SYNTAX      OCTET STRING (SIZE(1..32))
            MAX-ACCESS  read-create
            STATUS      current
            DESCRIPTION
                "The value of this object identifies the row in the VDSL2 Line
                 Thresholds Configuration Profile Table
                 (vdsl2LineAlarmConfProfileTable) that applies to this VDSL2
                 line.
                "
            REFERENCE    "DSL Forum TR-90, paragraph 5.4.1"
            DEFVAL       { "DEFVAL" }
            ::= { vdsl2LineAlarmConfTemplateEntry 2 }
        
        vdsl2LAlarmConfTempChan1ConfProfile  OBJECT-TYPE
            SYNTAX      OCTET STRING (SIZE(1..32))
            MAX-ACCESS  read-create
            STATUS      current
            DESCRIPTION
                "The value of this object identifies the row in the VDSL2
                 Channel Thresholds Configuration Profile Table
                 (vdsl2ChAlarmConfProfileTable) that applies for VDSL2
                 bearer channel #1.  The channel profile name specified here
                 must match the name of an existing row in the
                 vdsl2ChAlarmConfProfileTable table.
                "
            REFERENCE    "DSL Forum TR-90, paragraph 5.4.1"
            DEFVAL       { "DEFVAL" }
            ::= { vdsl2LineAlarmConfTemplateEntry 3 }
            
        vdsl2LAlarmConfTempChan2ConfProfile  OBJECT-TYPE
            SYNTAX      OCTET STRING (SIZE(0..32))
            MAX-ACCESS  read-create
            STATUS      current
            DESCRIPTION
                "The value of this object identifies the row in the VDSL2
                 Channel Thresholds Configuration Profile Table
                 (vdsl2ChAlarmConfProfileTable) that applies for VDSL2
                 bearer channel #2.  The channel profile name specified here
                 must match the name of an existing row in the
                 vdsl2ChAlarmConfProfileTable table.  If the channel is unused,
                 then the object is set to a zero length string.
                "
            REFERENCE    "DSL Forum TR-90, paragraph 5.4.1"
            ::= { vdsl2LineAlarmConfTemplateEntry 4 }
        
        vdsl2LAlarmConfTempChan3ConfProfile  OBJECT-TYPE
            SYNTAX      OCTET STRING (SIZE(0..32))
            MAX-ACCESS  read-create
            STATUS      current
            DESCRIPTION
                "The value of this object identifies the row in the VDSL2
                 Channel Thresholds Configuration Profile Table
                 (vdsl2ChAlarmConfProfileTable) that applies for VDSL2
                 bearer channel #3.  The channel profile name specified here
                 must match the name of an existing row in the
                 vdsl2ChAlarmConfProfileTable table.
                 This object may be set to a non-zero length string only if
                 vdsl2LAlarmConfTempChan2ConfProfile contains a non-zero
                 length string.
                "
            REFERENCE    "DSL Forum TR-90, paragraph 5.4.1"
            ::= { vdsl2LineAlarmConfTemplateEntry 5 }
        
        vdsl2LAlarmConfTempChan4ConfProfile  OBJECT-TYPE
            SYNTAX      OCTET STRING (SIZE(0..32))
            MAX-ACCESS  read-create
            STATUS      current
            DESCRIPTION
                "The value of this object identifies the row in the VDSL2
                 Channel Thresholds Configuration Profile Table
                 (vdsl2ChAlarmConfProfileTable) that applies for VDSL2
                 bearer channel #4.  The channel profile name specified here
                 must match the name of an existing row in the
                 vdsl2ChAlarmConfProfileTable table.
                 This object may be set to a non-zero length string only if
                 vdsl2LAlarmConfTempChan3ConfProfile contains a non-zero
                 length string.
                "
            REFERENCE    "DSL Forum TR-90, paragraph 5.4.1"
            ::= { vdsl2LineAlarmConfTemplateEntry 6 }
        
        vdsl2LAlarmConfTempRowStatus  OBJECT-TYPE
            SYNTAX      RowStatus
            MAX-ACCESS  read-create
            STATUS      current
            DESCRIPTION
                "This object is used to create a new row or to modify or
                delete an existing row in this table.
                
                A profile is activated by setting this object to 'active'.
                When 'active' is set, the system will validate the profile.
                
                Before a profile can be deleted or taken out of service
                (by setting this object to 'destroy' or 'outOfService'),
                it must be not referenced from all associated
                lines.
               "
            ::= { vdsl2LineAlarmConfTemplateEntry 7 }
        
          --      vdsl2LineAlarmConfProfileTable        
        
        vdsl2LineAlarmConfProfileTable  OBJECT-TYPE
            SYNTAX      SEQUENCE  OF  Vdsl2LineAlarmConfProfileEntry
            MAX-ACCESS  not-accessible
            STATUS      current
            DESCRIPTION
                "The table vdsl2LineAlarmConfProfileTable contains VDSL2
                 line PM thresholds profiles. The index of this table is
                 vdsl2LineAlarmConfProfileName.   
                 A default profile with an index of 'DEFVAL' will
                 always exist and its parameters will be set to vendor
                 specific values, unless otherwise specified in this
                 document.
                "
            ::= { vdsl2ProfileAlarmConf 2 }
        
        vdsl2LineAlarmConfProfileEntry  OBJECT-TYPE
            SYNTAX      Vdsl2LineAlarmConfProfileEntry
            MAX-ACCESS  not-accessible
            STATUS      current
            DESCRIPTION
                "The table vdsl2LineAlarmConfProfileTable contains VDSL2
                 line PM thresholds profiles.
                 The index of this entry is vdsl2LineAlarmConfProfileName.
                 A default profile with an index of 'DEFVAL' will
                 always exist and its parameters will be set to vendor
                 specific values, unless otherwise specified in this
                 document.
                "
            INDEX  { IMPLIED vdsl2LineAlarmConfProfileName }
            ::= { vdsl2LineAlarmConfProfileTable 1 }
        
        Vdsl2LineAlarmConfProfileEntry ::=
             SEQUENCE {
             vdsl2LineAlarmConfProfileName                      OCTET STRING,
             vdsl2LineAlarmConfProfileXtucThresh15MinFecs
                                                  HCPerfIntervalThreshold,
             vdsl2LineAlarmConfProfileXtucThresh15MinEs
                                                  HCPerfIntervalThreshold,
             vdsl2LineAlarmConfProfileXtucThresh15MinSes
                                                   HCPerfIntervalThreshold,
             vdsl2LineAlarmConfProfileXtucThresh15MinLoss
                                                   HCPerfIntervalThreshold,
             vdsl2LineAlarmConfProfileXtucThresh15MinUas
                                                   HCPerfIntervalThreshold,
             vdsl2LineAlarmConfProfileXturThresh15MinFecs
                                                   HCPerfIntervalThreshold,
             vdsl2LineAlarmConfProfileXturThresh15MinEs
                                                   HCPerfIntervalThreshold,
             vdsl2LineAlarmConfProfileXturThresh15MinSes
                                                   HCPerfIntervalThreshold,
             vdsl2LineAlarmConfProfileXturThresh15MinLoss
                                                   HCPerfIntervalThreshold,
             vdsl2LineAlarmConfProfileXturThresh15MinUas
                                                   HCPerfIntervalThreshold,
             vdsl2LineAlarmConfProfileThresh15MinFailedFullInt   Unsigned32,
             vdsl2LineAlarmConfProfileThresh15MinFailedShrtInt   Unsigned32,
             vdsl2LineAlarmConfProfileRowStatus                  RowStatus,
             vdsl2LineAlarmConfProfileThresh15MinFullInt         Unsigned32,
             vdsl2LineAlarmConfProfileXtucThresh15MinLeftrs      HCPerfIntervalThreshold,
             vdsl2LineAlarmConfProfileXturThresh15MinLeftrs      HCPerfIntervalThreshold,
             hwVdsl2LineAlarmConfProfileDyingGaspAlarmSwitch     INTEGER,
             hwVdsl2LineAlarmConfProfileActiveFailAlarmSwitch    INTEGER,
             hwVdsl2LineAlarmConfProfileRateChangeAlarmSwitch    INTEGER,
             hwVdsl2LineAlarmConfProfileLegacyCpeAlarmSwitch     INTEGER, 
             hwVdsl2LineAlarmConfProfileVictAbnormalVariationAlarmSwitch INTEGER,
             hwVdsl2LineAlarmConfProfileDistAbnormalVariationAlarmSwitch INTEGER,
             hwVdsl2LineAlarmConfProfileReceivedESAbnormalAlarmSwitch    INTEGER,
             hwVdsl2LineAlarmConfProfileNonVectoringCPEActivatedAlarmSwitch INTEGER,
             hwVdsl2LineAlarmConfProfileFreqRetrainReachThresholdAlarmSwitch INTEGER,
             hwvdsl2LineAlarmConfProfilePSConfigAbnormalAlarmSwitch INTEGER
             }
        
        vdsl2LineAlarmConfProfileName  OBJECT-TYPE
            SYNTAX      OCTET STRING (SIZE(1..32))
            MAX-ACCESS  not-accessible
            STATUS      current
            DESCRIPTION
                "This object identifies a row in this table."
            ::= { vdsl2LineAlarmConfProfileEntry 1 }
        
        vdsl2LineAlarmConfProfileXtucThresh15MinFecs  OBJECT-TYPE
            SYNTAX      HCPerfIntervalThreshold
            UNITS       "seconds"
            MAX-ACCESS  read-create
            STATUS      current
            DESCRIPTION
                "A threshold for the vdsl2PMLCurr15MFecs counter,
                 when vdsl2PMLCurrUnit is XTUC {1}.
                 The value 0 means that no threshold is specified for the
                 associated counter.
                 Unit: seconds
                "
            REFERENCE    "ITU-T G.997.1, paragraph 7.3.1"
            DEFVAL       { 0 }
              ::= { vdsl2LineAlarmConfProfileEntry 2 }
        
        vdsl2LineAlarmConfProfileXtucThresh15MinEs  OBJECT-TYPE
            SYNTAX      HCPerfIntervalThreshold
            UNITS       "seconds"
            MAX-ACCESS  read-create
            STATUS      current
            DESCRIPTION
                "A threshold for the vdsl2PMLCurr15MEs counter,
                 when vdsl2PMLCurrUnit is XTUC {1}.
                 The value 0 means that no threshold is specified for the
                 associated counter.
                 Unit: seconds
                "
            REFERENCE    "ITU-T G.997.1, paragraph 7.3.1"
            DEFVAL       { 0 }
              ::= { vdsl2LineAlarmConfProfileEntry 3 }
        
        vdsl2LineAlarmConfProfileXtucThresh15MinSes  OBJECT-TYPE
            SYNTAX      HCPerfIntervalThreshold
            UNITS       "seconds"
            MAX-ACCESS  read-create
            STATUS      current
            DESCRIPTION
                "A threshold for the vdsl2PMLCurr15MSes counter,
                 when vdsl2PMLCurrUnit is XTUC {1}.
                 The value 0 means that no threshold is specified for the
                 associated counter.
                 Unit: seconds
                "
            REFERENCE    "ITU-T G.997.1, paragraph 7.3.1"
            DEFVAL       { 0 }
              ::= { vdsl2LineAlarmConfProfileEntry 4 }
            
        vdsl2LineAlarmConfProfileXtucThresh15MinLoss  OBJECT-TYPE
            SYNTAX      HCPerfIntervalThreshold
            UNITS       "seconds"
            MAX-ACCESS  read-create
            STATUS      current
            DESCRIPTION
                "A threshold for the vdsl2PMLCurr15MLoss counter,
                 when vdsl2PMLCurrUnit is XTUC {1}.
                 The value 0 means that no threshold is specified for the
                 associated counter.
                 Unit: seconds
                "
            REFERENCE    "ITU-T G.997.1, paragraph 7.3.1"
            DEFVAL       { 0 }
              ::= { vdsl2LineAlarmConfProfileEntry 5 }
        
        vdsl2LineAlarmConfProfileXtucThresh15MinUas  OBJECT-TYPE
            SYNTAX      HCPerfIntervalThreshold
            UNITS       "seconds"
            MAX-ACCESS  read-create
            STATUS      current
            DESCRIPTION
                "A threshold for the vdsl2PMLCurr15MUas counter,
                 when vdsl2PMLCurrUnit is XTUC {1}.
                 The value 0 means that no threshold is specified for the
                 associated counter.
                 Unit: seconds
                "
            REFERENCE    "ITU-T G.997.1, paragraph 7.3.1"
            DEFVAL       { 0 }
             ::= { vdsl2LineAlarmConfProfileEntry 6 }
        
        vdsl2LineAlarmConfProfileXturThresh15MinFecs  OBJECT-TYPE
            SYNTAX      HCPerfIntervalThreshold
            UNITS       "seconds"
            MAX-ACCESS  read-create
            STATUS      current
            DESCRIPTION
                "A threshold for the vdsl2PMLCurr15MFecs counter,
                 when vdsl2PMLCurrUnit is XTUR {2}.
                 The value 0 means that no threshold is specified for the
                 associated counter.
                 Unit: seconds
                "
            REFERENCE    "ITU-T G.997.1, paragraph 7.3.1"
            DEFVAL       { 0 }
              ::= { vdsl2LineAlarmConfProfileEntry 7 }
        
        vdsl2LineAlarmConfProfileXturThresh15MinEs  OBJECT-TYPE
            SYNTAX      HCPerfIntervalThreshold
            UNITS       "seconds"
            MAX-ACCESS  read-create
            STATUS      current
            DESCRIPTION
                "A threshold for the vdsl2PMLCurr15MEs counter,
                 when vdsl2PMLCurrUnit is XTUR {2}.
                 The value 0 means that no threshold is specified for the
                 associated counter.
                 Unit: seconds
                "
            REFERENCE    "ITU-T G.997.1, paragraph 7.3.1"
            DEFVAL       { 0 }
            ::= { vdsl2LineAlarmConfProfileEntry 8 }
        
        vdsl2LineAlarmConfProfileXturThresh15MinSes  OBJECT-TYPE
            SYNTAX      HCPerfIntervalThreshold
            UNITS       "seconds"
            MAX-ACCESS  read-create
            STATUS      current
            DESCRIPTION
                "A threshold for the vdsl2PMLCurr15MSes counter,
                 when vdsl2PMLCurrUnit is XTUR {2}.
                 The value 0 means that no threshold is specified for the
                 associated counter.
                 Unit: seconds
                "
            REFERENCE    "ITU-T G.997.1, paragraph 7.3.1"
            DEFVAL       { 0 }
            ::= { vdsl2LineAlarmConfProfileEntry 9 }
        
        vdsl2LineAlarmConfProfileXturThresh15MinLoss  OBJECT-TYPE
            SYNTAX      HCPerfIntervalThreshold
            UNITS       "seconds"
            MAX-ACCESS  read-create
            STATUS      current
            DESCRIPTION
               "A threshold for the vdsl2PMLCurr15MLoss counter,
                when vdsl2PMLCurrUnit is XTUR {2}.
                The value 0 means that no threshold is specified for the
                associated counter.
                Unit: seconds
               "
            REFERENCE    "ITU-T G.997.1, paragraph 7.3.1"
            DEFVAL       { 0 }
            ::= { vdsl2LineAlarmConfProfileEntry 10 }
        
        vdsl2LineAlarmConfProfileXturThresh15MinUas  OBJECT-TYPE
            SYNTAX      HCPerfIntervalThreshold
            UNITS       "seconds"
            MAX-ACCESS  read-create
            STATUS      current
            DESCRIPTION
               "A threshold for the vdsl2PMLCurr15MUas counter,
                when vdsl2PMLCurrUnit is XTUR {2}.
                The value 0 means that no threshold is specified for the
                associated counter.
                Unit: seconds
               "
            REFERENCE    "ITU-T G.997.1, paragraph 7.3.1"
            DEFVAL       { 0 }
            ::= { vdsl2LineAlarmConfProfileEntry 11 }
        
        vdsl2LineAlarmConfProfileThresh15MinFailedFullInt  OBJECT-TYPE
            SYNTAX      Unsigned32
            MAX-ACCESS  read-create
            STATUS      current
            DESCRIPTION
               "A threshold for the vdsl2PMLCurrInit15MfailedFullInits
                counter.
                The value 0 means that no threshold is specified for the
                associated counter.
               "
            REFERENCE    "ITU-T G.997.1, paragraph 7.3.1"
            DEFVAL       { 0 }
            ::= { vdsl2LineAlarmConfProfileEntry 12 }
        
        vdsl2LineAlarmConfProfileThresh15MinFailedShrtInt  OBJECT-TYPE
            SYNTAX      Unsigned32
            MAX-ACCESS  read-create
            STATUS      current
            DESCRIPTION
               "A threshold for the vdsl2PMLCurrInit15MFailedShortInits
                counter.
                The value 0 means that no threshold is specified for the
                associated counter.
               "
            REFERENCE    "ITU-T G.997.1, paragraph 7.3.1"
            DEFVAL       { 0 }
            ::= { vdsl2LineAlarmConfProfileEntry 13 }
             
        vdsl2LineAlarmConfProfileRowStatus  OBJECT-TYPE
            SYNTAX      RowStatus
            MAX-ACCESS  read-create
            STATUS      current
            DESCRIPTION
               "This object is used to create a new row or to modify or
                delete an existing row in this table.
                
                A profile is activated by setting this object to 'active'.
                When 'active' is set, the system will validate the profile.
                
                Before a profile can be deleted or taken out of service
                (by setting this object to 'destroy' or 'outOfService'),
                it must be not referenced from all associated
                templates.
               "
            ::= { vdsl2LineAlarmConfProfileEntry 14 }
        
        vdsl2LineAlarmConfProfileThresh15MinFullInt  OBJECT-TYPE
            SYNTAX      Unsigned32
            MAX-ACCESS  read-create
            STATUS      current
            DESCRIPTION
               "A threshold for the vdsl2PMLCurrInit15MFullInits
                counter.
                The value 0 means that no threshold is specified for the
                associated counter.
               "
            REFERENCE    "ITU-T G.997.1, paragraph 7.3.1"
            DEFVAL       { 0 }
              ::= { vdsl2LineAlarmConfProfileEntry 15 }
        
        vdsl2LineAlarmConfProfileXtucThresh15MinLeftrs  OBJECT-TYPE
            SYNTAX      HCPerfIntervalThreshold
            UNITS       "seconds"
            MAX-ACCESS  read-create
            STATUS      current
            DESCRIPTION
               "A threshold for the vdsl2PMLCurr15MLeftrs counter,
                when vdsl2PMLCurrUnit is XTUC {1}.
                The value 0 means that no threshold is specified for the
                associated counter.
                Unit: seconds
               "
            REFERENCE    "ITU-T G.997.1, paragraph 7.3.1"
            DEFVAL       { 0 }
            ::= { vdsl2LineAlarmConfProfileEntry 16 }              

        vdsl2LineAlarmConfProfileXturThresh15MinLeftrs  OBJECT-TYPE
            SYNTAX      HCPerfIntervalThreshold
            UNITS       "seconds"
            MAX-ACCESS  read-create
            STATUS      current
            DESCRIPTION
               "A threshold for the vdsl2PMLCurr15MLeftrs counter,
                when vdsl2PMLCurrUnit is XTUR {2}.
                The value 0 means that no threshold is specified for the
                associated counter.
                Unit: seconds
               "
            REFERENCE    "ITU-T G.997.1, paragraph 7.3.1"
            DEFVAL       { 0 }
            ::= { vdsl2LineAlarmConfProfileEntry 17 } 
            
         hwVdsl2LineAlarmConfProfileDyingGaspAlarmSwitch OBJECT-TYPE
            SYNTAX INTEGER {
                               enable (1),
                               disable (2)
                           }
            MAX-ACCESS  read-create
            STATUS      current
            DESCRIPTION
                       "This object enable/disable the report of LOSS-OF-POWER
                        alarm in a VDSL line.
                        Options:
                        1. enable(1)  - The report of LOSS-OF-POWER alarm in a VDSL line is enabled
                        2. disable(2) - The report of LOSS-OF-POWER alarm in a VDSL line is disabled
                       "
            DEFVAL       { enable }
            ::= { vdsl2LineAlarmConfProfileEntry 18 }
    
        hwVdsl2LineAlarmConfProfileActiveFailAlarmSwitch OBJECT-TYPE
            SYNTAX INTEGER {
                               enable (1),
                               disable (2)
                           }
            MAX-ACCESS  read-create
            STATUS      current
            DESCRIPTION
                       "This object enable/disable the active fail alarm switch. 
                        Options:
                        1. enable(1)  - The active fail alarm switch is enabled
                        2. disable(2) - The active fail alarm switch is disabled
                       "         
            DEFVAL       { enable }
            ::= { vdsl2LineAlarmConfProfileEntry 19 }  
                      
        hwVdsl2LineAlarmConfProfileRateChangeAlarmSwitch OBJECT-TYPE
            SYNTAX INTEGER {
                               enable (1),
                               disable (2)
                           }
            MAX-ACCESS  read-create
            STATUS      current
            DESCRIPTION
                       "This object enable/disable the active rate change alarm switch. 
                        Options:
                        1. enable(1)  - The active rate change alarm switch is enabled
                        2. disable(2) - The active rate change alarm switch is disabled
                       "         
            DEFVAL       { enable }
            ::= { vdsl2LineAlarmConfProfileEntry 20 } 
            
        hwVdsl2LineAlarmConfProfileLegacyCpeAlarmSwitch OBJECT-TYPE
            SYNTAX INTEGER {
                               enable (1),
                               disable (2)
                           }
            MAX-ACCESS  read-create
            STATUS      current
            DESCRIPTION
                       "This object enable/disable the legacy cpe alarm switch. 
                        Options:
                        1. enable(1)  - The legacy cpe alarm switch is enabled
                        2. disable(2) - The legacy cpe alarm switch is disabled
                       "         
            DEFVAL       { enable }
            ::= { vdsl2LineAlarmConfProfileEntry 21 } 
            
        hwVdsl2LineAlarmConfProfileVictAbnormalVariationAlarmSwitch OBJECT-TYPE
            SYNTAX INTEGER {
                               enable (1),
                               disable (2)
                           }
            MAX-ACCESS  read-create
            STATUS      current
            DESCRIPTION
                       "This object enable/disable alarm switch that the port 
                        receives abnormal crosstalk. 
                        Options:
                        1. enable(1)  - The alarm switch that the port receives
                                        abnormal crosstalk is enabled
                        2. disable(2) - The alarm switch that the port receives
                                        abnormal crosstalk is disabled
                       "         
            DEFVAL       { enable }
            ::= { vdsl2LineAlarmConfProfileEntry 22 } 
            
        hwVdsl2LineAlarmConfProfileDistAbnormalVariationAlarmSwitch OBJECT-TYPE
            SYNTAX INTEGER {
                               enable (1),
                               disable (2)
                           }
            MAX-ACCESS  read-create
            STATUS      current
            DESCRIPTION
                       "This object enable/disable the alarm switch that the port
                        causes abnormal crosstalk. 
                        Options:
                        1. enable(1)  - The alarm switch that the port causes
                                        abnormal crosstalk is enabled
                        2. disable(2) - The alarm switch that the port causes
                                        abnormal crosstalk is disabled
                       "         
            DEFVAL       { enable }
            ::= { vdsl2LineAlarmConfProfileEntry 23 }             

        hwVdsl2LineAlarmConfProfileReceivedESAbnormalAlarmSwitch OBJECT-TYPE
            SYNTAX INTEGER {
                               enable (1),
                               disable (2)
                           }
            MAX-ACCESS  read-create
            STATUS      current
            DESCRIPTION
                       "This object enable/disable the alarm switch that The port
                        receives abnormal error sample messages. 
                        Options:
                        1. enable(1)  - The alarm switch that the port receives
                                        abnormal error sample messages is enabled
                        2. disable(2) - The alarm switch that the port receives
                                        abnormal error sample messages is disabled
                       "         
            DEFVAL       { enable }
            ::= { vdsl2LineAlarmConfProfileEntry 24 } 

        hwVdsl2LineAlarmConfProfileNonVectoringCPEActivatedAlarmSwitch OBJECT-TYPE
            SYNTAX INTEGER {
                               enable (1),
                               disable (2)
                           }
            MAX-ACCESS  read-create
            STATUS      current
            DESCRIPTION
                       "This object enable/disable the alarm switch that the port is
                        activated in none-vectoring mode. 
                        Options:
                        1. enable(1)  - The alarm switch that the port is activated
                                        in none-vectoring mode is enabled
                        2. disable(2) - The alarm switch that the port is activated
                                        in none-vectoring mode is disabled
                       "         
            DEFVAL       { enable }
            ::= { vdsl2LineAlarmConfProfileEntry 25 } 

        hwVdsl2LineAlarmConfProfileFreqRetrainReachThresholdAlarmSwitch OBJECT-TYPE
            SYNTAX INTEGER {
                               enable (1),
                               disable (2)
                           }
            MAX-ACCESS  read-create
            STATUS      current
            DESCRIPTION
                       "This object enable/disable the alarm switch that the port
                        frequently retrain times in 15 minutes reach the threshold. 
                        Options:
                        1. enable(1)  - The alarm switch that the port frequently retrain
                                        times in 15 minutes reach the threshold is enabled
                        2. disable(2) - The alarm switch that the port frequently retrain
                                        times in 15 minutes reach the threshold is disabled
                       "         
            DEFVAL       { enable }
            ::= { vdsl2LineAlarmConfProfileEntry 26 } 
            
        hwvdsl2LineAlarmConfProfilePSConfigAbnormalAlarmSwitch OBJECT-TYPE
            SYNTAX INTEGER {
                               enable (1),
                               disable (2)
                           }
            MAX-ACCESS  read-create
            STATUS      current
            DESCRIPTION
                       "This object enable/disable the pilot sequence configuration abnormal alarm switch. 
                        Options:
                        1. enable(1)  - The pilot sequence configuration abnormal alarm switch is enabled
                        2. disable(2) - The pilot sequence configuration abnormal alarm switch is disabled
                       "        
            DEFVAL       { enable }
            ::= { vdsl2LineAlarmConfProfileEntry 27 } 
                                    
          --      vdsl2ChAlarmConfProfileTable        
        
        vdsl2ChAlarmConfProfileTable  OBJECT-TYPE
            SYNTAX      SEQUENCE  OF  Vdsl2ChAlarmConfProfileEntry
            MAX-ACCESS  not-accessible
            STATUS      current
            DESCRIPTION
                "The table vdsl2ChAlarmConfProfileTable contains VDSL2
                  channel PM thresholds profiles. 
                  The index of this table is vdsl2ChAlarmConfProfileName. 
                  A default profile with an index of 'DEFVAL' will
                  always exist and its parameters will be set to vendor-specific
                  values, unless otherwise specified in this document.
                 "
            ::= { vdsl2ProfileAlarmConf 3 }
        
        vdsl2ChAlarmConfProfileEntry  OBJECT-TYPE
            SYNTAX      Vdsl2ChAlarmConfProfileEntry
            MAX-ACCESS  not-accessible
            STATUS      current
            DESCRIPTION
                "The table vdsl2ChAlarmConfProfileTable contains VDSL2
                 channel PM thresholds profiles.
                 The index of this entry is vdsl2ChAlarmConfProfileName.
                 A default profile with an index of 'DEFVAL' will
                 always exist and its parameters will be set to vendor-specific
                 values, unless otherwise specified in this document.
                "
            INDEX  { IMPLIED vdsl2ChAlarmConfProfileName }
            ::= { vdsl2ChAlarmConfProfileTable 1 }
        
        Vdsl2ChAlarmConfProfileEntry ::=
             SEQUENCE {
             vdsl2ChAlarmConfProfileName                             OCTET STRING,
             vdsl2ChAlarmConfProfileXtucThresh15MinCodingViolations  Unsigned32,
             vdsl2ChAlarmConfProfileXtucThresh15MinCorrected         Unsigned32,
             vdsl2ChAlarmConfProfileXturThresh15MinCodingViolations  Unsigned32,
             vdsl2ChAlarmConfProfileXturThresh15MinCorrected         Unsigned32,
             vdsl2ChAlarmConfProfileMonitoringRateDs	             Unsigned32,
             vdsl2ChAlarmConfProfileMonitoringRateUs		     Unsigned32,
             vdsl2ChAlarmConfProfileRowStatus                        RowStatus
             }
        
        vdsl2ChAlarmConfProfileName  OBJECT-TYPE
            SYNTAX      OCTET STRING (SIZE(1..32))
            MAX-ACCESS  not-accessible
            STATUS      current
            DESCRIPTION
               "This object identifies a row in this table."
            ::= { vdsl2ChAlarmConfProfileEntry 1 }
        
        vdsl2ChAlarmConfProfileXtucThresh15MinCodingViolations OBJECT-TYPE
            SYNTAX      Unsigned32
            MAX-ACCESS  read-create
            STATUS      current
            DESCRIPTION   
               "A threshold for the vdsl2PMChCurr15MCodingViolations
                counter, when vdsl2PMChCurrUnit is XTUC {1}.
                The value 0 means that no threshold is specified for the
                associated counter.
               "
            REFERENCE    "ITU-T G.997.1, paragraph 7.3.2"
            DEFVAL       { 0 }
            ::= { vdsl2ChAlarmConfProfileEntry 2 }
        
        vdsl2ChAlarmConfProfileXtucThresh15MinCorrected  OBJECT-TYPE
            SYNTAX      Unsigned32
            MAX-ACCESS  read-create
            STATUS      current
            DESCRIPTION
               "A threshold for the vdsl2PMChCurr15MCorrectedBlocks
                counter, when vdsl2PMChCurrUnit is XTUC {1}.
                The value 0 means that no threshold is specified for the
                associated counter.
               "
            REFERENCE    "ITU-T G.997.1, paragraph 7.3.2"
            DEFVAL       { 0 }
              ::= { vdsl2ChAlarmConfProfileEntry 3 }
        
        vdsl2ChAlarmConfProfileXturThresh15MinCodingViolations  OBJECT-TYPE
            SYNTAX      Unsigned32
            MAX-ACCESS  read-create
            STATUS      current
            DESCRIPTION
                "A threshold for the vdsl2PMChCurr15MCodingViolations
                 counter, when vdsl2PMChCurrUnit is XTUR {2}.
                 The value 0 means that no threshold is specified for the
                 associated counter.
                "
            REFERENCE    "ITU-T G.997.1, paragraph 7.3.2"
            DEFVAL       { 0 }
              ::= { vdsl2ChAlarmConfProfileEntry 4 }
        
        vdsl2ChAlarmConfProfileXturThresh15MinCorrected  OBJECT-TYPE
            SYNTAX      Unsigned32
            MAX-ACCESS  read-create
            STATUS      current
            DESCRIPTION
                "A threshold for the vdsl2PMChCurr15MCorrectedBlocks
                 counter, when vdsl2PMChCurrUnit is XTUR {2}.
                 The value 0 means that no threshold is specified for the
                 associated counter.
                "
            REFERENCE    "ITU-T G.997.1, paragraph 7.3.2"
            DEFVAL       { 0 }
              ::= { vdsl2ChAlarmConfProfileEntry 5 }
        
        vdsl2ChAlarmConfProfileMonitoringRateDs  OBJECT-TYPE
            SYNTAX      Unsigned32(0..200000000)
            UNITS       "bits/second"
            MAX-ACCESS  read-create
            STATUS      current
            DESCRIPTION
                "The channel monitoring rate downstream. 
                 Huawei defined. When the value you set is larger than
                 the value of the rate downstream defined in the channel 
                 profile, it will not be successful. The value 0 means 
                 that no threshold is specified for the associated 
                 counter.
                 Unit: bits/second
                "
            DEFVAL       { 0 }
              ::= { vdsl2ChAlarmConfProfileEntry 6 }
        
        vdsl2ChAlarmConfProfileMonitoringRateUs  OBJECT-TYPE
            SYNTAX      Unsigned32(0..200000000)
            UNITS       "bits/second"
            MAX-ACCESS  read-create
            STATUS      current
            DESCRIPTION
                "The channel monitoring rate upstream.
                 Huawei defined. When the value you set is larger than
                 the value of the rate upstream defined in the channel 
                 profile, it will not be successful. The value 0 means 
                 that no threshold is specified for the associated 
                 counter.
                 Unit: bits/second
                "
            DEFVAL       { 0 }
              ::= { vdsl2ChAlarmConfProfileEntry 7 }
        
        vdsl2ChAlarmConfProfileRowStatus  OBJECT-TYPE
            SYNTAX      RowStatus
            MAX-ACCESS  read-create
            STATUS      current
            DESCRIPTION
                "This object is used to create a new row or to modify or
                 delete an existing row in this table.
                 
                 A profile is activated by setting this object to 'active'.
                 When 'active' is set, the system will validate the profile.
                 
                 Before a profile can be deleted or taken out of service
                 (by setting this object to 'destroy' or 'outOfService'),
                 it must be not referenced from all associated
                 templates.
                "
            ::= { vdsl2ChAlarmConfProfileEntry 8 }
       
          --          PM line current counters          
        vdsl2PMLineCurrTable  OBJECT-TYPE
            SYNTAX      SEQUENCE  OF  Vdsl2PMLineCurrEntry
            MAX-ACCESS  not-accessible
            STATUS      current
            DESCRIPTION
                "The table vdsl2PMLineCurrTable contains current Performance
                 Monitoring results of VDSL2 line.  
                 The indexes of this table are an interface index where the
                 interface has an ifType of vdsl2(251) and the termination
                 unit.
                "
            ::= { vdsl2PMLine 1 }
        
        vdsl2PMLineCurrEntry  OBJECT-TYPE
            SYNTAX      Vdsl2PMLineCurrEntry
            MAX-ACCESS  not-accessible
            STATUS      current
            DESCRIPTION
                "The table vdsl2PMLineCurrTable contains current Performance
                 Monitoring results of VDSL2 line.
                 The indexes of this entry are an interface index where the
                 interface has an ifType of vdsl2(251) and the termination
                 unit.
                "
            INDEX  { ifIndex, vdsl2PMLCurrUnit }
            ::= { vdsl2PMLineCurrTable 1 }
        
        Vdsl2PMLineCurrEntry  ::=
            SEQUENCE {
              vdsl2PMLCurrUnit                    Vdsl2Unit,
              vdsl2PMLCurrValidIntervals          Unsigned32,
              vdsl2PMLCurrInvalidIntervals        Unsigned32,
              vdsl2PMLCurr15MTimeElapsed          HCPerfTimeElapsed,
              vdsl2PMLCurr15MFecs                 Counter32,
              vdsl2PMLCurr15MEs                   Counter32,
              vdsl2PMLCurr15MSes                  Counter32,
              vdsl2PMLCurr15MLoss                 Counter32,
              vdsl2PMLCurr15MUas                  Counter32,
              vdsl2PMLCurr1DayValidIntervals      Unsigned32,
              vdsl2PMLCurr1DayInvalidIntervals    Unsigned32,
              vdsl2PMLCurr1DayTimeElapsed         HCPerfTimeElapsed,
              vdsl2PMLCurr1DayFecs                Counter32,
              vdsl2PMLCurr1DayEs                  Counter32,
              vdsl2PMLCurr1DaySes                 Counter32,
              vdsl2PMLCurr1DayLoss                Counter32,
              vdsl2PMLCurr1DayUas                 Counter32,
              vdsl2PMLEverBeforeFecs              Counter32,
              vdsl2PMLEverBeforeEs                Counter32,
              vdsl2PMLEverBeforeSes               Counter32,
              vdsl2PMLEverBeforeLoss              Counter32,
              vdsl2PMLEverBeforeUas               Counter32,
              vdsl2PMLCurr15MLofs                 Counter32,
              vdsl2PMLCurr15MLols                 Counter32,
              vdsl2PMLCurr15MLops                 Counter32,
              vdsl2PMLCurr1DayLofs                Counter32,
              vdsl2PMLCurr1DayLols                Counter32,
              vdsl2PMLCurr1DayLops                Counter32,
              vdsl2PMLEverBeforeLofs              Counter32,
              vdsl2PMLEverBeforeLols              Counter32,
              vdsl2PMLEverBeforeLops              Counter32,
              vdsl2PMLCurr15MSosSuccess           Counter32,
              vdsl2PMLCurr1DaySosSuccess          Counter32,
              vdsl2PMLEverBeforeSosSuccess        Counter32,
              vdsl2PMLCurr15MInmainpeq            OCTET STRING,
              vdsl2PMLCurr15MInmame               Counter32,
              vdsl2PMLCurr15MInmaiat              OCTET STRING,
              vdsl2PMLCurr1DayInmainpeq           OCTET STRING,  
              vdsl2PMLCurr1DayInmame              Counter32,
              vdsl2PMLCurr1DayInmaiat             OCTET STRING,
              vdsl2PMLEverBeforeInmainpeq         OCTET STRING,
              vdsl2PMLEverBeforeInmame            Counter32,
              vdsl2PMLEverBeforeInmaiat           OCTET STRING,
              vdsl2PMLineCurr15MStartTime         DateAndTime,
              vdsl2PMLineCurr1DayStartTime        DateAndTime,
              vdsl2PMLCurr15MLeftrs               Counter32,
              vdsl2PMLCurr15MEfb                  Counter32, 
              vdsl2PMLCurr15MMinEftr              Counter32,
              vdsl2PMLCurr1DayLeftrs              Counter32,
              vdsl2PMLCurr1DayEfb                 Counter32, 
              vdsl2PMLCurr1DayMinEftr             Counter32,
              vdsl2PMLEverBeforeLeftrs            Counter32,
              vdsl2PMLEverBeforeEfb               Counter32, 
              vdsl2PMLEverBeforeMinEftr           Counter32,
              hwvdsl2PMLEverBeforeSraDownShiftEvent    Counter32, 
              hwvdsl2PMLEverBeforeSraUpShiftEvent      Counter32,
              hwvdsl2PMLCurr15MSraDownShiftEvent       Counter32,
              hwvdsl2PMLCurr15MSraUpShiftEvent         Counter32,
              hwvdsl2PMLCurr1DaySraDownShiftEvent      Counter32,
              hwvdsl2PMLCurr1DaySraUpShiftEvent        Counter32,
              hwvdsl2PMLEverBeforeDisorderLeavingEvent Counter32,
              hwvdsl2PMLEverBeforeLof                  Counter32,
              hwvdsl2PMLEverBeforeLos                  Counter32,
              hwvdsl2PMLEverBeforeLop                  Counter32,
              hwvdsl2PMLEverBeforeLom                  Counter32,              
              hwvdsl2PMLCurr15MDisorderLeavingEvent    Counter32,
              hwvdsl2PMLCurr1DayDisorderLeavingEvent   Counter32,
              hwvdsl2PMLCurr15MLof                Counter32,  
              hwvdsl2PMLCurr15MLos                Counter32,
              hwvdsl2PMLCurr15MLop                Counter32,
              hwvdsl2PMLCurr15MLom                Counter32,
              hwvdsl2PMLCurr1DayLof               Counter32,
              hwvdsl2PMLCurr1DayLos               Counter32,
              hwvdsl2PMLCurr1DayLop               Counter32,
              hwvdsl2PMLCurr1DayLom               Counter32
            }
        
        vdsl2PMLCurrUnit  OBJECT-TYPE
            SYNTAX      Vdsl2Unit
            MAX-ACCESS  not-accessible
            STATUS      current
            DESCRIPTION
                "The termination unit XTUC{1} or XTUR{2}."
            ::= { vdsl2PMLineCurrEntry 1 }
        
        vdsl2PMLCurrValidIntervals  OBJECT-TYPE
            SYNTAX      Unsigned32
            MAX-ACCESS  read-only
            STATUS      current
            DESCRIPTION
                "Valid intervals."
            ::= { vdsl2PMLineCurrEntry 2 }
        
        vdsl2PMLCurrInvalidIntervals  OBJECT-TYPE
            SYNTAX      Unsigned32
            MAX-ACCESS  read-only
            STATUS      current
            DESCRIPTION
                "Invalid intervals."
            ::= { vdsl2PMLineCurrEntry 3 }
        
        vdsl2PMLCurr15MTimeElapsed  OBJECT-TYPE
            SYNTAX      HCPerfTimeElapsed
            UNITS       "seconds"
            MAX-ACCESS  read-only
            STATUS      current
            DESCRIPTION
                "Total elapsed seconds in this interval.
                 Unit: seconds
                "
            ::= { vdsl2PMLineCurrEntry 4 }
        
        vdsl2PMLCurr15MFecs  OBJECT-TYPE
            SYNTAX      Counter32
            UNITS       "seconds"
            MAX-ACCESS  read-only
            STATUS      current
            DESCRIPTION
                "Count of seconds during this interval that there was at least
                 one FEC correction event for one or more bearer channels in
                 this line.  This parameter is inhibited during UAS or SES.
                 Unit: seconds
                "
            REFERENCE    "ITU-T G.997.1, paragraph 7.2.1"
            ::= { vdsl2PMLineCurrEntry 5 }
           
        vdsl2PMLCurr15MEs  OBJECT-TYPE
            SYNTAX      Counter32
            UNITS       "seconds"
            MAX-ACCESS  read-only
            STATUS      current
            DESCRIPTION
                "Count of seconds during this interval that there was:
                 xTU-C: CRC-8 &gt;= 1 for one or more bearer channels OR
                        LOS &gt;= 1 OR SEF &gt;=1 OR LPR &gt;= 1
                 xTU-R: FEBE &gt;= 1 for one or more bearer channels OR
                        LOS-FE &gt;=1 OR RDI &gt;=1 OR LPR-FE &gt;=1 .
                 This parameter is inhibited during UAS.
                 Unit: seconds
                "
            REFERENCE    "ITU-T G.997.1, paragraph 7.2.1"
            ::= { vdsl2PMLineCurrEntry 6 }
        
        vdsl2PMLCurr15MSes  OBJECT-TYPE
            SYNTAX      Counter32
            UNITS       "seconds"
            MAX-ACCESS  read-only
            STATUS      current
            DESCRIPTION
                "Count of seconds during this interval that there was:
                 xTU-C:  If G.998.4 is supported and retransmission is enabled 
                         in the near-end received direction, a SES is declared 
                         if during a 1-second interval, there is one or more 
                         severe loss of error-free throughput (seftr) defect 
                         in the near-end received direction.
                         Or else, an SES is declared if, during a 1 second interval, 
                         there are 18 or more CRC 8 anomalies in one or more of the 
                         received bearer channels, or one or more LOS defects, or 
                         one or more SEF defects, or one or more LPR defects.
                        
                 xTU-R: If G.998.4 is supported and retransmission is enabled in the 
                        far-end received direction, a SES-LFE is declared if during 
                        a 1-second interval, there is one or more severe loss of 
                        error-free throughput (seftr) defect in the far-end received 
                        direction.
                        Or else, an SES is declared if, during a 1 second interval, 
                        there are 18 or more FEBE anomalies in one or more of the 
                        transmitted bearer channels, or one or more far end LOS 
                        defects, or one or more RDI defects, or one or more LPR FE 
                        defects.
                 This parameter is inhibited during UAS.
                 Unit: seconds
                "
            REFERENCE    "ITU-T G.997.1, paragraph 7.2.1"
            ::= { vdsl2PMLineCurrEntry 7 }
        
        vdsl2PMLCurr15MLoss  OBJECT-TYPE
            SYNTAX      Counter32
            UNITS       "seconds"
            MAX-ACCESS  read-only
            STATUS      current
            DESCRIPTION
                "Count of seconds during this interval that there was LOS (or
                 LOS-FE for xTU-R).
                 Unit: seconds
                "
            REFERENCE    "ITU-T G.997.1, paragraph 7.2.1"
            ::= { vdsl2PMLineCurrEntry 8 }
          
        vdsl2PMLCurr15MUas  OBJECT-TYPE
            SYNTAX      Counter32
            UNITS       "seconds"
            MAX-ACCESS  read-only
            STATUS      current
            DESCRIPTION
                "Count of seconds in Unavailability State during this
                 interval.  Unavailability begins at the onset of 10
                 contiguous severely-errored seconds, and ends at the
                 onset of 10 contiguous seconds with no severely-errored
                 seconds.
                 Unit: seconds
                "
            REFERENCE    "ITU-T G.997.1, paragraph 7.2.1"
            ::= { vdsl2PMLineCurrEntry 9 }
        
        vdsl2PMLCurr1DayValidIntervals  OBJECT-TYPE
            SYNTAX      Unsigned32
            MAX-ACCESS  read-only
            STATUS      current
            DESCRIPTION
                "Valid intervals."
            ::= { vdsl2PMLineCurrEntry 10 }
        
        vdsl2PMLCurr1DayInvalidIntervals  OBJECT-TYPE
            SYNTAX      Unsigned32
            MAX-ACCESS  read-only
            STATUS      current
            DESCRIPTION
                "Invalid intervals."
            ::= { vdsl2PMLineCurrEntry 11 }
        
        vdsl2PMLCurr1DayTimeElapsed  OBJECT-TYPE
            SYNTAX      HCPerfTimeElapsed
            UNITS       "seconds"
            MAX-ACCESS  read-only
            STATUS      current
            DESCRIPTION
                "Total elapsed seconds in this interval.
                 Unit: seconds
                "
            ::= { vdsl2PMLineCurrEntry 12 }
        
        vdsl2PMLCurr1DayFecs  OBJECT-TYPE
            SYNTAX      Counter32
            UNITS       "seconds"
            MAX-ACCESS  read-only
            STATUS      current
            DESCRIPTION
                "Count of seconds during this interval that there was at least
                 one FEC correction event for one or more bearer channels in
                 this line.  This parameter is inhibited during UAS or SES.
                 Unit: seconds
                "
            REFERENCE    "ITU-T G.997.1, paragraph 7.2.1"
            ::= { vdsl2PMLineCurrEntry 13 }
        
        vdsl2PMLCurr1DayEs  OBJECT-TYPE
            SYNTAX      Counter32
            UNITS       "seconds"
            MAX-ACCESS  read-only
            STATUS      current
            DESCRIPTION
                "Count of seconds during this interval that there was:
                 xTU-C: CRC-8 &gt;= 1 for one or more bearer channels OR
                        LOS &gt;= 1 OR SEF &gt;= 1 OR LPR &gt;= 1
                 xTU-R: FEBE &gt;= 1 for one or more bearer channels OR
                        LOS-FE &gt;= 1 OR RDI &gt;= 1 OR LPR-FE &gt;= 1.
                 This parameter is inhibited during UAS.
                 Unit: seconds
                "
            REFERENCE    "ITU-T G.997.1, paragraph 7.2.1"
            ::= { vdsl2PMLineCurrEntry 14 }
        
        vdsl2PMLCurr1DaySes  OBJECT-TYPE
            SYNTAX      Counter32
            UNITS       "seconds"
            MAX-ACCESS  read-only
            STATUS      current
            DESCRIPTION
                "Count of seconds during this interval that there was:
                 xTU-C: (CRC-8 summed over all bearer channels) &gt;= 18 OR
                        LOS &gt;= 1 OR SEF &gt;= 1 OR LPR &gt;= 1
                 xTU-R: (FEBE summed over all bearer channels) &gt;= 18 OR
                        LOS-FE &gt;= 1 OR RDI &gt;= 1 OR LPR-FE &gt;= 1
                 This parameter is inhibited during UAS.
                 Unit: seconds
                "
            REFERENCE    "ITU-T G.997.1, paragraph 7.2.1"
            ::= { vdsl2PMLineCurrEntry 15 }
        
        vdsl2PMLCurr1DayLoss  OBJECT-TYPE
            SYNTAX      Counter32
            UNITS       "seconds"
            MAX-ACCESS  read-only
            STATUS      current
            DESCRIPTION
                "Count of seconds during this interval that there was LOS (or
                 LOS-FE for xTU-R).
                 Unit: seconds
                "
            REFERENCE    "ITU-T G.997.1, paragraph 7.2.1"
            ::= { vdsl2PMLineCurrEntry 16 }
        
        vdsl2PMLCurr1DayUas  OBJECT-TYPE
            SYNTAX      Counter32
            UNITS       "seconds"
            MAX-ACCESS  read-only
            STATUS      current
            DESCRIPTION
                "Count of seconds in Unavailability State during this interval.
                 Unavailability begins at the onset of 10 contiguous severely
                 -errored seconds, and ends at the onset of 10 contiguous
                 seconds with no severely-errored seconds.
                 Unit: seconds
                "
            REFERENCE    "ITU-T G.997.1, paragraph 7.2.1"
            ::= { vdsl2PMLineCurrEntry 17 }
        
        vdsl2PMLEverBeforeFecs  OBJECT-TYPE
            SYNTAX      Counter32
            UNITS       "seconds"
            MAX-ACCESS  read-only
            STATUS      current
            DESCRIPTION
                "Count of seconds since agent reset that there was at least
                 one FEC correction event for one or more bearer channels in
                 this line. This parameter is inhibited during UAS or SES.
                 Huawei defined.
                 Unit: seconds
                "
            ::= { vdsl2PMLineCurrEntry 18 }
            
        vdsl2PMLEverBeforeEs  OBJECT-TYPE
            SYNTAX      Counter32
            UNITS       "seconds"
            MAX-ACCESS  read-only
            STATUS      current
            DESCRIPTION
                "Count of seconds since agent reset that there was:
                 xTU-C: CRC-8 &gt;= 1 for one or more bearer channels OR
                        LOS &gt;= 1 OR SEF &gt;= 1 OR LPR &gt;= 1
                 xTU-R: FEBE &gt;= 1 for one or more bearer channels OR
                        LOS-FE &gt;= 1 OR RDI &gt;= 1 OR LPR-FE &gt;= 1.
                 This parameter is inhibited during UAS.
                 Huawei defined.
                 Unit: seconds
                "
            ::= { vdsl2PMLineCurrEntry 19 }
        
        vdsl2PMLEverBeforeSes  OBJECT-TYPE
            SYNTAX      Counter32
            UNITS       "seconds"
            MAX-ACCESS  read-only
            STATUS      current
            DESCRIPTION
                "Count of seconds since agent reset that there was:
                 xTU-C: (CRC-8 summed over all bearer channels) &gt;= 18 OR
                        LOS &gt;= 1 OR SEF &gt;= 1 OR LPR &gt;= 1
                 xTU-R: (FEBE summed over all bearer channels) &gt;= 18 OR
                        LOS-FE &gt;= 1 OR RDI &gt;= 1 OR LPR-FE &gt;= 1
                 This parameter is inhibited during UAS.
                 Huawei defined.
                 Unit: seconds
                "
            ::= { vdsl2PMLineCurrEntry 20 }
        
        vdsl2PMLEverBeforeLoss  OBJECT-TYPE
            SYNTAX      Counter32
            UNITS       "seconds"
            MAX-ACCESS  read-only
            STATUS      current
            DESCRIPTION
                "Count of seconds since agent reset that there was LOS (or
                 LOS-FE for xTU-R).
                 Huawei defined.
                 Unit: seconds
                "
            ::= { vdsl2PMLineCurrEntry 21 }
        
        vdsl2PMLEverBeforeUas  OBJECT-TYPE
            SYNTAX      Counter32
            UNITS       "seconds"
            MAX-ACCESS  read-only
            STATUS      current
            DESCRIPTION
                "Count of seconds in Unavailability State since agent reset.
                 Unavailability begins at the onset of 10 contiguous severely
                 -errored seconds, and ends at the onset of 10 contiguous
                 seconds with no severely-errored seconds.
                 Huawei defined.
                 Unit: seconds
                "
            ::= { vdsl2PMLineCurrEntry 22 }
           
        vdsl2PMLCurr15MLofs  OBJECT-TYPE
            SYNTAX      Counter32
            UNITS       "seconds"
            MAX-ACCESS  read-only
            STATUS      current
            DESCRIPTION
                "Count of seconds in the current 15 minute interval when there was Loss of Framing.
                 Unit: seconds
                "
            ::= { vdsl2PMLineCurrEntry 23 }
            
        vdsl2PMLCurr15MLols  OBJECT-TYPE
            SYNTAX      Counter32
            UNITS       "seconds"
            MAX-ACCESS  read-only
            STATUS      current
            DESCRIPTION
                "Count of seconds in the current 15 minute interval when there was Loss of Link.
                 Unit: seconds
                "
            ::= { vdsl2PMLineCurrEntry 24 }
        
        vdsl2PMLCurr15MLops  OBJECT-TYPE
            SYNTAX      Counter32
            UNITS       "seconds"
            MAX-ACCESS  read-only
            STATUS      current
            DESCRIPTION
                "Count of seconds in the current 15 minute interval when there was Loss of Power.
                 Unit: seconds
                "
            ::= { vdsl2PMLineCurrEntry 25 }
                   
        vdsl2PMLCurr1DayLofs  OBJECT-TYPE
            SYNTAX      Counter32
            UNITS       "seconds"
            MAX-ACCESS  read-only
            STATUS      current
            DESCRIPTION
                "Count of the number of seconds when there was Loss of Framing during the current day.
                 Unit: seconds
                "
            ::= { vdsl2PMLineCurrEntry 26 }
        
        vdsl2PMLCurr1DayLols  OBJECT-TYPE
            SYNTAX      Counter32
            UNITS       "seconds"
            MAX-ACCESS  read-only
            STATUS      current
            DESCRIPTION
                "Count of the number of seconds when there was Loss of Link during the current day.
                 Unit: seconds
                "
            ::= { vdsl2PMLineCurrEntry 27 }
        
        vdsl2PMLCurr1DayLops  OBJECT-TYPE
            SYNTAX      Counter32
            UNITS       "seconds"
            MAX-ACCESS  read-only
            STATUS      current
            DESCRIPTION
                "Count of the number of seconds when there was Loss of Power during the current day.
                 Unit: seconds
                "
            ::= { vdsl2PMLineCurrEntry 28 }
        
        vdsl2PMLEverBeforeLofs  OBJECT-TYPE
            SYNTAX      Counter32
            UNITS       "seconds"
            MAX-ACCESS  read-only
            STATUS      current
            DESCRIPTION
                "Count of the number of seconds when there was Loss of Framing since agent reset.
                 Unit: seconds
                "
            ::= { vdsl2PMLineCurrEntry 29 }
        
        vdsl2PMLEverBeforeLols  OBJECT-TYPE
            SYNTAX      Counter32
            UNITS       "seconds"
            MAX-ACCESS  read-only
            STATUS      current
            DESCRIPTION
                "Count of the number of seconds when there was Loss of Link since agent reset.
                 Unit: seconds
                "
            ::= { vdsl2PMLineCurrEntry 30 }
        
        vdsl2PMLEverBeforeLops  OBJECT-TYPE
            SYNTAX      Counter32
            UNITS       "seconds"
            MAX-ACCESS  read-only
            STATUS      current
            DESCRIPTION
                "Count of the number of seconds when there was Loss of Power since agent reset.
                 Unit: seconds
                "
            ::= { vdsl2PMLineCurrEntry 31 }
        
        vdsl2PMLCurr15MSosSuccess  OBJECT-TYPE
            SYNTAX      Counter32
            UNITS       "times"
            MAX-ACCESS  read-only
            STATUS      current
            DESCRIPTION
                "Count of the total number of successful SOS procedures initiated in the current 15 minute.
                 Unit: times
                "
            REFERENCE    "ITU-T G.997.1, paragraph 7.2.1"
            ::= { vdsl2PMLineCurrEntry 32 }
            
        vdsl2PMLCurr1DaySosSuccess  OBJECT-TYPE
            SYNTAX      Counter32
            UNITS       "times"
            MAX-ACCESS  read-only
            STATUS      current
            DESCRIPTION
                "Count of the total number of successful SOS procedures initiated during the current day.
                 Unit: times
                "
            REFERENCE    "ITU-T G.997.1, paragraph 7.2.1"
            ::= { vdsl2PMLineCurrEntry 33 } 
        
        vdsl2PMLEverBeforeSosSuccess  OBJECT-TYPE
            SYNTAX      Counter32
            UNITS       "times"
            MAX-ACCESS  read-only
            STATUS      current
            DESCRIPTION
                "Count of the total number of successful SOS procedures initiated since agent reset.
                 Unit: times
                "
            REFERENCE    "ITU-T G.997.1, paragraph 7.2.1"
            ::= { vdsl2PMLineCurrEntry 34 }  
           
        vdsl2PMLCurr15MInmainpeq  OBJECT-TYPE
            SYNTAX      OCTET STRING  (SIZE(0..68))
            MAX-ACCESS  read-only
            STATUS      current
            DESCRIPTION
                "This parameter is a count of the INMAINPEQi anomalies 
                 occurring on the line during current 15 minutes.
                "
            REFERENCE    "ITU-T G.997.1, paragraph 7.2.1"
            ::= { vdsl2PMLineCurrEntry 35 }        
            
        vdsl2PMLCurr15MInmame  OBJECT-TYPE
            SYNTAX      Counter32
            MAX-ACCESS  read-only
            STATUS      current
            DESCRIPTION
                "This parameter is a count of the INMAME anomalies 
                 occurring on the line during current 15 minutes.
                "
            REFERENCE    "ITU-T G.997.1, paragraph 7.2.1"
            ::= { vdsl2PMLineCurrEntry 36 }    
            
        vdsl2PMLCurr15MInmaiat  OBJECT-TYPE
            SYNTAX      OCTET STRING  (SIZE(0..32))
            MAX-ACCESS  read-only
            STATUS      current
            DESCRIPTION
                "This parameter is a count of the INMAIATi anomalies 
                 occurring on the line during current 15 minutes.
                "
            REFERENCE    "ITU-T G.997.1, paragraph 7.2.1"
            ::= { vdsl2PMLineCurrEntry 37 }    
             
        vdsl2PMLCurr1DayInmainpeq  OBJECT-TYPE
            SYNTAX      OCTET STRING  (SIZE(0..68))
            MAX-ACCESS  read-only
            STATUS      current
            DESCRIPTION
                "This parameter is a count of the INMAINPEQi anomalies 
                 occurring on the line during current 1 day.
                "
            REFERENCE    "ITU-T G.997.1, paragraph 7.2.1"
            ::= { vdsl2PMLineCurrEntry 38 }    
            
        vdsl2PMLCurr1DayInmame  OBJECT-TYPE
            SYNTAX      Counter32
            MAX-ACCESS  read-only
            STATUS      current
            DESCRIPTION
                "This parameter is a count of the INMAME anomalies 
                 occurring on the line during current 1 day.
                "
            REFERENCE    "ITU-T G.997.1, paragraph 7.2.1"
            ::= { vdsl2PMLineCurrEntry 39 }    
             
        vdsl2PMLCurr1DayInmaiat  OBJECT-TYPE
            SYNTAX      OCTET STRING  (SIZE(0..32))
            MAX-ACCESS  read-only
            STATUS      current
            DESCRIPTION
                "This parameter is a count of the INMAIATi anomalies 
                 occurring on the line during current 1 day.
                "
            REFERENCE    "ITU-T G.997.1, paragraph 7.2.1"
            ::= { vdsl2PMLineCurrEntry 40 }    
            
        vdsl2PMLEverBeforeInmainpeq  OBJECT-TYPE
            SYNTAX      OCTET STRING  (SIZE(0..68))
            MAX-ACCESS  read-only
            STATUS      current
            DESCRIPTION
                "This parameter is a count of the INMAINPEQi anomalies 
                 occurring on the line ever before.
                "
            REFERENCE    "ITU-T G.997.1, paragraph 7.2.1"
            ::= { vdsl2PMLineCurrEntry 41 }    
            
        vdsl2PMLEverBeforeInmame  OBJECT-TYPE
            SYNTAX      Counter32
            MAX-ACCESS  read-only
            STATUS      current
            DESCRIPTION
                "This parameter is a count of the INMAME anomalies 
                 occurring on the line ever before.
                "
            REFERENCE    "ITU-T G.997.1, paragraph 7.2.1"
            ::= { vdsl2PMLineCurrEntry 42 }    
            
        vdsl2PMLEverBeforeInmaiat  OBJECT-TYPE
            SYNTAX      OCTET STRING  (SIZE(0..32))
            MAX-ACCESS  read-only
            STATUS      current
            DESCRIPTION
                "This parameter is a count of the INMAIATi anomalies 
                 occurring on the line ever before.
                "
            REFERENCE    "ITU-T G.997.1, paragraph 7.2.1"
            ::= { vdsl2PMLineCurrEntry 43 }
           
        vdsl2PMLineCurr15MStartTime  OBJECT-TYPE
            SYNTAX      DateAndTime
            MAX-ACCESS  read-only
            STATUS      current
            DESCRIPTION
                "Start time of the current 15-minute performance statistics."
            ::= { vdsl2PMLineCurrEntry 44 } 
           
        vdsl2PMLineCurr1DayStartTime  OBJECT-TYPE
            SYNTAX      DateAndTime
            MAX-ACCESS  read-only
            STATUS      current
            DESCRIPTION
                "Start time of the current 1-day performance statistics."
            ::= { vdsl2PMLineCurrEntry 45 }              
            
        vdsl2PMLCurr15MLeftrs     OBJECT-TYPE
            SYNTAX      Counter32
            MAX-ACCESS  read-only
            STATUS      current
            DESCRIPTION
                "If retransmission is used in a given transmit direction, this parameter 
                 is a count of the seconds with a near-end leftr defect present observed 
                 over the 15 minutes accumulation period.
                "
            REFERENCE    "ITU-T G.997.1, paragraph 7.2.1.1.6 7.2.1.2.6"    
            ::= { vdsl2PMLineCurrEntry 46 }
                          
        vdsl2PMLCurr15MEfb        OBJECT-TYPE
            SYNTAX      Counter32
            MAX-ACCESS  read-only
            STATUS      current
            DESCRIPTION
                "If retransmission is used in a given transmit direction, this parameter 
                 is a count of the number of error-free bits observed over the 15 minutes
                 accumulation period.
                "
            REFERENCE    "ITU-T G.997.1, paragraph 7.2.1.1.7 7.2.1.2.7"     
            ::= { vdsl2PMLineCurrEntry 47 } 
            
        vdsl2PMLCurr15MMinEftr    OBJECT-TYPE
            SYNTAX      Counter32
            MAX-ACCESS  read-only
            STATUS      current
            DESCRIPTION
                "If retransmission is used in a given transmit direction, this parameter 
                 reports the minimum of the EFTR(Error-free throughput rate) observed 
                 over the 15 minutes accumulation period.
                "
            REFERENCE    "ITU-T G.997.1, paragraph 7.2.1.1.8 7.2.1.2.8"     
            ::= { vdsl2PMLineCurrEntry 48 } 
        vdsl2PMLCurr1DayLeftrs    OBJECT-TYPE
            SYNTAX      Counter32
            MAX-ACCESS  read-only
            STATUS      current
            DESCRIPTION
                "If retransmission is used in a given transmit direction, this parameter 
                 is a count of the seconds with a near-end leftr defect present observed 
                 over the 24 hours accumulation period.
                "
            REFERENCE    "ITU-T G.997.1, paragraph 7.2.1.1.6 7.2.1.2.6"     
            ::= { vdsl2PMLineCurrEntry 49 } 
            
        vdsl2PMLCurr1DayEfb       OBJECT-TYPE
            SYNTAX      Counter32
            MAX-ACCESS  read-only
            STATUS      current
            DESCRIPTION
                "If retransmission is used in a given transmit direction, this parameter 
                 is a count of the number of error-free bits observed over the 24 hours 
                 accumulation period.
                "
            REFERENCE    "ITU-T G.997.1, paragraph 7.2.1.1.7 7.2.1.2.7"     
            ::= { vdsl2PMLineCurrEntry 50 } 
            
        vdsl2PMLCurr1DayMinEftr   OBJECT-TYPE
            SYNTAX      Counter32
            MAX-ACCESS  read-only
            STATUS      current
            DESCRIPTION
                "If retransmission is used in a given transmit direction, this parameter 
                 reports the minimum of the EFTR(Error-free throughput rate) observed 
                 over the 24 hours accumulation period.
                "
            REFERENCE    "ITU-T G.997.1, paragraph 7.2.1.1.8 7.2.1.2.8"     
            ::= { vdsl2PMLineCurrEntry 51} 
            
        vdsl2PMLEverBeforeLeftrs  OBJECT-TYPE
            SYNTAX      Counter32
            MAX-ACCESS  read-only
            STATUS      current
            DESCRIPTION
                "If retransmission is used in a given transmit direction, this parameter 
                 is a count of the seconds with a near-end leftr defect present observed 
                 ever before.
                "
            REFERENCE    "ITU-T G.997.1, paragraph 7.2.1.1.6 7.2.1.2.6"     
            ::= { vdsl2PMLineCurrEntry 52 } 
            
        vdsl2PMLEverBeforeEfb     OBJECT-TYPE
            SYNTAX      Counter32
            MAX-ACCESS  read-only
            STATUS      current
            DESCRIPTION
                "If retransmission is used in a given transmit direction, this parameter 
                 is a count of the number of error-free bits observed ever before.
                "
            REFERENCE    "ITU-T G.997.1, paragraph 7.2.1.1.7 7.2.1.2.7"     
            ::= { vdsl2PMLineCurrEntry 53 } 
            
        vdsl2PMLEverBeforeMinEftr OBJECT-TYPE
            SYNTAX      Counter32
            MAX-ACCESS  read-only
            STATUS      current
            DESCRIPTION
                "If retransmission is used in a given transmit direction, this parameter 
                 reports the minimum of the EFTR(Error-free throughput rate) observed 
                 ever before.
                "
            REFERENCE    "ITU-T G.997.1, paragraph 7.2.1.1.8 7.2.1.2.8"     
            ::= { vdsl2PMLineCurrEntry 54 } 
            
        hwvdsl2PMLEverBeforeSraDownShiftEvent OBJECT-TYPE
            SYNTAX      Counter32
            MAX-ACCESS  read-only
            STATUS      current
            DESCRIPTION
                "This parameter is a count of sra downshift event occurring on the line ever before."
            ::= { vdsl2PMLineCurrEntry 55 } 
            
        hwvdsl2PMLEverBeforeSraUpShiftEvent OBJECT-TYPE
            SYNTAX      Counter32
            MAX-ACCESS  read-only
            STATUS      current
            DESCRIPTION
                "This parameter is a count of sra upshift event occurring on the line ever before."
            ::= { vdsl2PMLineCurrEntry 56 } 
        
        hwvdsl2PMLCurr15MSraDownShiftEvent OBJECT-TYPE
            SYNTAX      Counter32
            MAX-ACCESS  read-only
            STATUS      current
            DESCRIPTION
                "This parameter is a count of sra downshift event occurring on the line over the 15 minutes accumulation period."
            ::= { vdsl2PMLineCurrEntry 57 } 
            
        hwvdsl2PMLCurr15MSraUpShiftEvent OBJECT-TYPE
            SYNTAX      Counter32
            MAX-ACCESS  read-only
            STATUS      current
            DESCRIPTION
                "This parameter is a count of sra upshift event occurring on the line over the 15 minutes accumulation period."
            ::= { vdsl2PMLineCurrEntry 58 } 
            
        hwvdsl2PMLCurr1DaySraDownShiftEvent OBJECT-TYPE
            SYNTAX      Counter32
            MAX-ACCESS  read-only
            STATUS      current
            DESCRIPTION
                "This parameter is a count of sra downshift event occurring on the line during current 1 day."
            ::= { vdsl2PMLineCurrEntry 59 } 
            
        hwvdsl2PMLCurr1DaySraUpShiftEvent OBJECT-TYPE
            SYNTAX      Counter32
            MAX-ACCESS  read-only
            STATUS      current
            DESCRIPTION
                "This parameter is a count of sra upshift event occurring on the line during current 1 day."
            ::= { vdsl2PMLineCurrEntry 60 }
            
        hwvdsl2PMLEverBeforeDisorderLeavingEvent OBJECT-TYPE
            SYNTAX      Counter32
            MAX-ACCESS  read-only
            STATUS      current
            DESCRIPTION
                "This parameter is a count of disorder leaving event occurring on the line ever before."
            ::= { vdsl2PMLineCurrEntry 61 }

        hwvdsl2PMLEverBeforeLof OBJECT-TYPE
            SYNTAX      Counter32
            MAX-ACCESS  read-only
            STATUS      current
            DESCRIPTION
                "This parameter is a count of loss of frame failure occurring on the line ever before."
            ::= { vdsl2PMLineCurrEntry 62 }

        hwvdsl2PMLEverBeforeLos OBJECT-TYPE
            SYNTAX      Counter32
            MAX-ACCESS  read-only
            STATUS      current
            DESCRIPTION
                "This parameter is a count of loss of signal failure occurring on the line ever before."
            ::= { vdsl2PMLineCurrEntry 63 }

        hwvdsl2PMLEverBeforeLop OBJECT-TYPE
            SYNTAX      Counter32
            MAX-ACCESS  read-only
            STATUS      current
            DESCRIPTION
                "This parameter is a count of loss of power failure occurring on the line ever before."
            ::= { vdsl2PMLineCurrEntry 64 }
            
        hwvdsl2PMLEverBeforeLom OBJECT-TYPE
            SYNTAX      Counter32
            MAX-ACCESS  read-only
            STATUS      current
            DESCRIPTION
                "This parameter is a count of loss of margin failure occurring on the line ever before."
            ::= { vdsl2PMLineCurrEntry 65 }

        hwvdsl2PMLCurr15MDisorderLeavingEvent OBJECT-TYPE
            SYNTAX      Counter32
            MAX-ACCESS  read-only
            STATUS      current
            DESCRIPTION
                "This parameter is a count of disorder leaving event occurring on the line during current 15 minutes."
            ::= { vdsl2PMLineCurrEntry 66 }

        hwvdsl2PMLCurr1DayDisorderLeavingEvent OBJECT-TYPE
            SYNTAX      Counter32
            MAX-ACCESS  read-only
            STATUS      current
            DESCRIPTION
                "This parameter is a count of disorder leaving event occurring on the line during current 1 day."
            ::= { vdsl2PMLineCurrEntry 67 }

        hwvdsl2PMLCurr15MLof OBJECT-TYPE
            SYNTAX      Counter32
            MAX-ACCESS  read-only
            STATUS      current
            DESCRIPTION
                "This parameter is a count of loss of frame failure occurring on the line during current 15 minutes."
            ::= { vdsl2PMLineCurrEntry 68 }

        hwvdsl2PMLCurr15MLos OBJECT-TYPE
            SYNTAX      Counter32
            MAX-ACCESS  read-only
            STATUS      current
            DESCRIPTION
                "This parameter is a count of loss of signal failure occurring on the line during current 15 minutes."
            ::= { vdsl2PMLineCurrEntry 69 }

        hwvdsl2PMLCurr15MLop OBJECT-TYPE
            SYNTAX      Counter32
            MAX-ACCESS  read-only
            STATUS      current
            DESCRIPTION
                "This parameter is a count of loss of power failure occurring on the line during current 15 minutes."
            ::= { vdsl2PMLineCurrEntry 70 }
            
        hwvdsl2PMLCurr15MLom OBJECT-TYPE
            SYNTAX      Counter32
            MAX-ACCESS  read-only
            STATUS      current
            DESCRIPTION
                "This parameter is a count of loss of margin failure occurring on the line during current 15 minutes."
            ::= { vdsl2PMLineCurrEntry 71 }

        hwvdsl2PMLCurr1DayLof OBJECT-TYPE
            SYNTAX      Counter32
            MAX-ACCESS  read-only
            STATUS      current
            DESCRIPTION
                "This parameter is a count of loss of frame failure occurring on the line during current 1 day."
            ::= { vdsl2PMLineCurrEntry 72 }

        hwvdsl2PMLCurr1DayLos OBJECT-TYPE
            SYNTAX      Counter32
            MAX-ACCESS  read-only
            STATUS      current
            DESCRIPTION
                "This parameter is a count of loss of signal failure occurring on the line during current 1 day."
            ::= { vdsl2PMLineCurrEntry 73 }

        hwvdsl2PMLCurr1DayLop OBJECT-TYPE
            SYNTAX      Counter32
            MAX-ACCESS  read-only
            STATUS      current
            DESCRIPTION
                "This parameter is a count of loss of power failure occurring on the line during current 1 day."
            ::= { vdsl2PMLineCurrEntry 74 }
            
        hwvdsl2PMLCurr1DayLom OBJECT-TYPE
            SYNTAX      Counter32
            MAX-ACCESS  read-only
            STATUS      current
            DESCRIPTION
                "This parameter is a count of loss of margin failure occurring on the line during current 1 day."
            ::= { vdsl2PMLineCurrEntry 75 }              

          --          PM line init current counters     
        
        vdsl2PMLineCurrInitTable   OBJECT-TYPE
            SYNTAX      SEQUENCE  OF  Vdsl2PMLineCurrInitEntry
            MAX-ACCESS  not-accessible
            STATUS      current
            DESCRIPTION
                "The table vdsl2PMLineCurrInitTable contains current
                 initialization counters of VDSL2 line. 
                 The indexes of this table are an interface index where the
                 interface has an ifType of vdsl2(251) and the termination
                 unit.
                "
            ::= { vdsl2PMLine 2 }
        
        vdsl2PMLineCurrInitEntry  OBJECT-TYPE
            SYNTAX      Vdsl2PMLineCurrInitEntry
            MAX-ACCESS  not-accessible
            STATUS      current
            DESCRIPTION
                "The table vdsl2PMLineCurrInitTable contains current
                 initialization counters of VDSL2 line.
                 The indexes of this entry are an interface index where the
                 interface has an ifType of vdsl2(251) and the termination
                 unit.
                "
            INDEX  { ifIndex }
            ::= { vdsl2PMLineCurrInitTable 1 }
        
        Vdsl2PMLineCurrInitEntry  ::=
            SEQUENCE {
              vdsl2PMLCurrInit15MTimeElapsed          Unsigned32,
              vdsl2PMLCurrInit15MFullInits            Unsigned32,
              vdsl2PMLCurrInit15MFailedFullInits      Unsigned32,
              vdsl2PMLCurrInit15MShortInits           Unsigned32,
              vdsl2PMLCurrInit15MFailedShortInits     Unsigned32,
              vdsl2PMLCurrInit1DayTimeElapsed         Unsigned32,
              vdsl2PMLCurrInit1DayFullInits           Unsigned32,
              vdsl2PMLCurrInit1DayFailedFullInits     Unsigned32,
              vdsl2PMLCurrInit1DayShortInits          Unsigned32,
              vdsl2PMLCurrInit1DayFailedShortInits    Unsigned32,
              vdsl2PMLInitEverBeforeFullInits         Unsigned32,
              vdsl2PMLInitEverBeforeFailedFullInits   Unsigned32,
              vdsl2PMLInitEverBeforeShortInits        Unsigned32,
              vdsl2PMLInitEverBeforeFailedShortInits  Unsigned32,
              vdsl2PMLineCurrInit15MStartTime         DateAndTime,
              vdsl2PMLineCurrInit1DayStartTime        DateAndTime 
            }
        
        vdsl2PMLCurrInit15MTimeElapsed  OBJECT-TYPE
            SYNTAX      Unsigned32
            UNITS       "seconds"
            MAX-ACCESS  read-only
            STATUS      current
            DESCRIPTION
                "Total elapsed seconds in this interval.
                 Unit: seconds
                "
            ::= { vdsl2PMLineCurrInitEntry 1 }
           
        vdsl2PMLCurrInit15MFullInits  OBJECT-TYPE
            SYNTAX      Unsigned32
            MAX-ACCESS  read-only
            STATUS      current
            DESCRIPTION
                "Count of full initializations attempted on the line
                 (successful and failed) during this interval.
                "
            REFERENCE    "ITU-T G.997.1, paragraph 7.2.1"
            ::= { vdsl2PMLineCurrInitEntry 2 }
        
        vdsl2PMLCurrInit15MFailedFullInits  OBJECT-TYPE
            SYNTAX      Unsigned32
            MAX-ACCESS  read-only
            STATUS      current
            DESCRIPTION
                "Count of failed full initializations on the line during this
                 interval.
                "
            REFERENCE    "ITU-T G.997.1, paragraph 7.2.1"
            ::= { vdsl2PMLineCurrInitEntry 3 }
        
        vdsl2PMLCurrInit15MShortInits  OBJECT-TYPE
            SYNTAX      Unsigned32
            MAX-ACCESS  read-only
            STATUS      current
            DESCRIPTION
                "Count of short initializations attempted on the line
                 (successful and failed) during this interval.
                "
            REFERENCE    "ITU-T G.997.1, paragraph 7.2.1"
            ::= { vdsl2PMLineCurrInitEntry 4 }
        
        vdsl2PMLCurrInit15MFailedShortInits  OBJECT-TYPE
            SYNTAX      Unsigned32
            MAX-ACCESS  read-only
            STATUS      current
            DESCRIPTION
                "Count of failed short initializations on the line during this
                 interval.
                "
            REFERENCE    "ITU-T G.997.1, paragraph 7.2.1"
            ::= { vdsl2PMLineCurrInitEntry 5 }
        
        vdsl2PMLCurrInit1DayTimeElapsed  OBJECT-TYPE
            SYNTAX      Unsigned32
            UNITS       "seconds"
            MAX-ACCESS  read-only
            STATUS      current
            DESCRIPTION
                "Total elapsed seconds in this interval.
                 Unit: seconds
                "
            ::= { vdsl2PMLineCurrInitEntry 6 }
        
        vdsl2PMLCurrInit1DayFullInits  OBJECT-TYPE
            SYNTAX      Unsigned32
            MAX-ACCESS  read-only
            STATUS      current
            DESCRIPTION
                "Count of full initializations attempted on the line
                 (successful and failed) during this interval.
                "
            REFERENCE    "ITU-T G.997.1, paragraph 7.2.1"
            ::= { vdsl2PMLineCurrInitEntry 7 }
        
        vdsl2PMLCurrInit1DayFailedFullInits  OBJECT-TYPE
            SYNTAX      Unsigned32
            MAX-ACCESS  read-only
            STATUS      current
            DESCRIPTION
                "Count of failed full initializations on the line during this
                 interval.
                "
            REFERENCE    "ITU-T G.997.1, paragraph 7.2.1"
            ::= { vdsl2PMLineCurrInitEntry 8 }
        
        vdsl2PMLCurrInit1DayShortInits  OBJECT-TYPE
            SYNTAX      Unsigned32
            MAX-ACCESS  read-only
            STATUS      current
            DESCRIPTION
                "Count of short initializations attempted on the line
                 (successful and failed) during this interval.
                "
            REFERENCE    "ITU-T G.997.1, paragraph 7.2.1"
            ::= { vdsl2PMLineCurrInitEntry 9 }
        
        vdsl2PMLCurrInit1DayFailedShortInits  OBJECT-TYPE
            SYNTAX      Unsigned32
            MAX-ACCESS  read-only
            STATUS      current
            DESCRIPTION
                "Count of failed short initializations on the line during this
                 interval.
                "
            REFERENCE    "ITU-T G.997.1, paragraph 7.2.1"
            ::= { vdsl2PMLineCurrInitEntry 10 }
        
        vdsl2PMLInitEverBeforeFullInits  OBJECT-TYPE
            SYNTAX      Unsigned32
            MAX-ACCESS  read-only
            STATUS      current
            DESCRIPTION
                "Count of full initializations attempted on the line
                 (successful and failed) since agent reset.
                 Huawei defined.
                "
            ::= { vdsl2PMLineCurrInitEntry 11 }
        
        vdsl2PMLInitEverBeforeFailedFullInits  OBJECT-TYPE
            SYNTAX      Unsigned32
            MAX-ACCESS  read-only
            STATUS      current
            DESCRIPTION
                "Count of failed full initializations on the line since agent 
                 reset.
                 Huawei defined.
                "
            ::= { vdsl2PMLineCurrInitEntry 12 }
            
        vdsl2PMLInitEverBeforeShortInits  OBJECT-TYPE
            SYNTAX      Unsigned32
            MAX-ACCESS  read-only
            STATUS      current
            DESCRIPTION
                "Count of short initializations attempted on the line
                 (successful and failed) since agent reset.
                 Huawei defined.
                "
            ::= { vdsl2PMLineCurrInitEntry 13 }
        
        vdsl2PMLInitEverBeforeFailedShortInits  OBJECT-TYPE
            SYNTAX      Unsigned32
            MAX-ACCESS  read-only
            STATUS      current
            DESCRIPTION
                "Count of failed short initializations on the line since agent 
                 reset.
                 Huawei defined.
                "
            ::= { vdsl2PMLineCurrInitEntry 14 }   
            
        vdsl2PMLineCurrInit15MStartTime  OBJECT-TYPE
            SYNTAX      DateAndTime
            MAX-ACCESS  read-only
            STATUS      current
            DESCRIPTION
                "Start time of the current initializations 15-minute performance statistics."
            ::= { vdsl2PMLineCurrInitEntry 15 } 
            
        vdsl2PMLineCurrInit1DayStartTime  OBJECT-TYPE
            SYNTAX      DateAndTime
            MAX-ACCESS  read-only
            STATUS      current
            DESCRIPTION
                "Start time of the current initializations 1-day performance statistics."
            ::= { vdsl2PMLineCurrInitEntry 16 } 
          --       PM line history 15 Minutes      
        vdsl2PMLineHist15MinTable    OBJECT-TYPE
            SYNTAX      SEQUENCE  OF  Vdsl2PMLineHist15MinEntry
            MAX-ACCESS  not-accessible
            STATUS      current
            DESCRIPTION
                "The table vdsl2PMLineHist15MinTable contains PM line history
                 for 15min intervals of VDSL2 line.   
                 The indexes of this table are an interface index where the
                 interface has an ifType of vdsl2(251), the termination unit,
                 and an interval number.
                "
            ::= { vdsl2PMLine 3 }
        
        vdsl2PMLineHist15MinEntry  OBJECT-TYPE
            SYNTAX      Vdsl2PMLineHist15MinEntry
            MAX-ACCESS  not-accessible
            STATUS      current
            DESCRIPTION
                "The table vdsl2PMLineHist15MinTable contains PM line history
                 for 15min intervals of VDSL2 line.
                 The indexes of this entry are an interface index where the
                 interface has an ifType of vdsl2(251), the termination unit,
                 and an interval number.
                "
            INDEX  { ifIndex,
                     vdsl2PMLHist15MUnit,
                     vdsl2PMLHist15MInterval }
            ::= { vdsl2PMLineHist15MinTable 1 }
        
        Vdsl2PMLineHist15MinEntry  ::=
            SEQUENCE {
              vdsl2PMLHist15MUnit                 Vdsl2Unit,
              vdsl2PMLHist15MInterval             Unsigned32,
              vdsl2PMLHist15MMonitoredTime        Unsigned32,
              vdsl2PMLHist15MFecs                 Counter32,
              vdsl2PMLHist15MEs                   Counter32,
              vdsl2PMLHist15MSes                  Counter32,
              vdsl2PMLHist15MLoss                 Counter32,
              vdsl2PMLHist15MUas                  Counter32,
              vdsl2PMLHist15MValidInterval        TruthValue,
              vdsl2PMLHist15MLofs                 Counter32,
              vdsl2PMLHist15MLols                 Counter32,
              vdsl2PMLHist15MLops                 Counter32,
              vdsl2PMLHist15MSosSuccess           Counter32,
              vdsl2PMLHist15MInmainpeq            OCTET STRING,
              vdsl2PMLHist15MInmame               Counter32,
              vdsl2PMLHist15MInmaiat              OCTET STRING,
              vdsl2PMLHist15MStartTime            DateAndTime,
              vdsl2PMLHist15MLeftrs               Counter32,
              vdsl2PMLHist15MEfb                  Counter32, 
              vdsl2PMLHist15MMinEftr              Counter32,
              hwvdsl2PMLHist15MSraDownShiftEvent  Counter32,
              hwvdsl2PMLHist15MSraUpShiftEvent    Counter32,
              hwvdsl2PMLHist15MDisorderLeavingEvent Counter32,
              hwvdsl2PMLHist15MLof                Counter32,
              hwvdsl2PMLHist15MLos                Counter32,
              hwvdsl2PMLHist15MLop                Counter32,
              hwvdsl2PMLHist15MLom                Counter32
            }
        
        vdsl2PMLHist15MUnit  OBJECT-TYPE
            SYNTAX      Vdsl2Unit
            MAX-ACCESS  not-accessible
            STATUS      current
            DESCRIPTION
                "The termination unit XTUC{1} or XTUR{2}."
            ::= { vdsl2PMLineHist15MinEntry 1 }
        
        vdsl2PMLHist15MInterval  OBJECT-TYPE
            SYNTAX      Unsigned32
            MAX-ACCESS  not-accessible
            STATUS      current
            DESCRIPTION
                "The interval number."
            ::= { vdsl2PMLineHist15MinEntry 2 }
        
        vdsl2PMLHist15MMonitoredTime  OBJECT-TYPE
            SYNTAX      Unsigned32
            UNITS       "seconds"
            MAX-ACCESS  read-only
            STATUS      current
            DESCRIPTION
                "Total seconds monitored in this interval.
                 Unit: seconds
                "
            ::= { vdsl2PMLineHist15MinEntry 3 }
        
        vdsl2PMLHist15MFecs  OBJECT-TYPE
            SYNTAX      Counter32
            UNITS       "seconds"
            MAX-ACCESS  read-only
            STATUS      current
            DESCRIPTION
                "Count of seconds during this interval that there was at least
                 one FEC correction event for one or more bearer channels in
                 this line.  This parameter is inhibited during UAS or SES.
                 Unit: seconds
                "
            REFERENCE    "ITU-T G.997.1, paragraph 7.2.1"
            ::= { vdsl2PMLineHist15MinEntry 4 }
        
        vdsl2PMLHist15MEs  OBJECT-TYPE
            SYNTAX      Counter32
            UNITS       "seconds"
            MAX-ACCESS  read-only
            STATUS      current
            DESCRIPTION
                "Count of seconds during this interval that there was:
                 xTU-C: CRC-8 &gt;= 1 for one or more bearer channels OR
                        LOS &gt;= 1 OR SEF &gt;= 1 OR LPR &gt;= 1
                 xTU-R: FEBE &gt;= 1 for one or more bearer channels OR
                        LOS-FE &gt;= 1 OR RDI &gt;= 1 OR LPR-FE &gt;= 1.
                 This parameter is inhibited during UAS.
                 Unit: seconds
                "
            REFERENCE    "ITU-T G.997.1, paragraph 7.2.1"
            ::= { vdsl2PMLineHist15MinEntry 5 }
        
        vdsl2PMLHist15MSes  OBJECT-TYPE
            SYNTAX      Counter32
            UNITS       "seconds"
            MAX-ACCESS  read-only
            STATUS      current
            DESCRIPTION
                "Count of seconds during this interval that there was:
                 xTU-C: (CRC-8 summed over all bearer channels) &gt;= 18 OR
                        LOS &gt;= 1 OR SEF &gt;= 1 OR LPR &gt;= 1
                 xTU-R: (FEBE summed over all bearer channels) &gt;= 18 OR
                        LOS-FE &gt;= 1 OR RDI &gt;= 1 OR LPR-FE &gt;= 1.
                 This parameter is inhibited during UAS.
                 Unit: seconds
                "
            REFERENCE    "ITU-T G.997.1, paragraph 7.2.1"
            ::= { vdsl2PMLineHist15MinEntry 6 }
        
        vdsl2PMLHist15MLoss  OBJECT-TYPE
            SYNTAX      Counter32
            UNITS       "seconds"
            MAX-ACCESS  read-only
            STATUS      current
            DESCRIPTION
                "Count of seconds during this interval that there was LOS (or
                 LOS-FE for xTU-R).
                 Unit: seconds
                "
            REFERENCE    "ITU-T G.997.1, paragraph 7.2.1"
            ::= { vdsl2PMLineHist15MinEntry 7 }
        
        vdsl2PMLHist15MUas  OBJECT-TYPE
            SYNTAX      Counter32
            UNITS       "seconds"
            MAX-ACCESS  read-only
            STATUS      current
            DESCRIPTION
                "Count of seconds in Unavailability State during this interval.
                 Unavailability begins at the onset of 10 contiguous severely
                 -errored seconds, and ends at the onset of 10 contiguous
                 seconds with no severely-errored seconds.
                 Unit: seconds
                "
            REFERENCE    "ITU-T G.997.1, paragraph 7.2.1"
            ::= { vdsl2PMLineHist15MinEntry 8 }
        
        vdsl2PMLHist15MValidInterval  OBJECT-TYPE
            SYNTAX      TruthValue
            MAX-ACCESS  read-only
            STATUS      current
            DESCRIPTION
                "This variable indicates if the data for this interval is
                 valid.
                "
            ::= { vdsl2PMLineHist15MinEntry 9 }
              
        vdsl2PMLHist15MLofs  OBJECT-TYPE
            SYNTAX      Counter32
            UNITS       "seconds"
            MAX-ACCESS  read-only
            STATUS      current
            DESCRIPTION
                "Count of seconds in the interval when there was Loss of Framing.
                 Unit: seconds
                "
            ::= { vdsl2PMLineHist15MinEntry 10 }
           
        vdsl2PMLHist15MLols  OBJECT-TYPE
            SYNTAX      Counter32
            UNITS       "seconds"
            MAX-ACCESS  read-only
            STATUS      current
            DESCRIPTION
                "Count of seconds in the interval when there was Loss of Link.
                 Unit: seconds
                "
            ::= { vdsl2PMLineHist15MinEntry 11 }
           
        vdsl2PMLHist15MLops  OBJECT-TYPE
            SYNTAX      Counter32
            UNITS       "seconds"
            MAX-ACCESS  read-only
            STATUS      current
            DESCRIPTION
                "Count of seconds in the interval when there was Loss of Power.
                 Unit: seconds
                "
            ::= { vdsl2PMLineHist15MinEntry 12 }
            
        vdsl2PMLHist15MSosSuccess  OBJECT-TYPE
            SYNTAX      Counter32
            UNITS       "times"
            MAX-ACCESS  read-only
            STATUS      current
            DESCRIPTION
                "Count of the total number of successful SOS procedures initiated in the interval.
                 Unit: times
                "
            REFERENCE    "ITU-T G.997.1, paragraph 7.2.1"
            ::= { vdsl2PMLineHist15MinEntry 13 }
           
        vdsl2PMLHist15MInmainpeq  OBJECT-TYPE
            SYNTAX      OCTET STRING  (SIZE(0..68))
            MAX-ACCESS  read-only
            STATUS      current
            DESCRIPTION
                "This parameter is a count of the INMAINPEQi anomalies 
                 occurring on the line over the 15 minutes accumulation period.
                "
            REFERENCE    "ITU-T G.997.1, paragraph 7.2.1"
            ::= { vdsl2PMLineHist15MinEntry 14 }        
            
        vdsl2PMLHist15MInmame  OBJECT-TYPE
            SYNTAX      Counter32
            MAX-ACCESS  read-only
            STATUS      current
            DESCRIPTION
                "This parameter is a count of the INMAME anomalies 
                 occurring on the line over the 15 minutes accumulation period.
                "
            REFERENCE    "ITU-T G.997.1, paragraph 7.2.1"
            ::= { vdsl2PMLineHist15MinEntry 15}    
            
        vdsl2PMLHist15MInmaiat  OBJECT-TYPE
            SYNTAX      OCTET STRING  (SIZE(0..32))
            MAX-ACCESS  read-only
            STATUS      current
            DESCRIPTION
                "This parameter is a count of the INMAIATi anomalies 
                 occurring on the line over the 15 minutes accumulation period.
                "
            REFERENCE    "ITU-T G.997.1, paragraph 7.2.1"
            ::= { vdsl2PMLineHist15MinEntry 16}
           
        vdsl2PMLHist15MStartTime  OBJECT-TYPE
            SYNTAX      DateAndTime
            MAX-ACCESS  read-only
            STATUS      current
            DESCRIPTION
                "Start time of the historical 15-minute performance statistics."
            ::= { vdsl2PMLineHist15MinEntry 17 }       
              
        vdsl2PMLHist15MLeftrs     OBJECT-TYPE
            SYNTAX      Counter32
            MAX-ACCESS  read-only
            STATUS      current
            DESCRIPTION
                "If retransmission is used in a given transmit direction, this parameter 
                 is a count of the seconds with a near-end leftr defect present observed 
                 over the 15 minutes accumulation period.
                "
            REFERENCE    "ITU-T G.997.1, paragraph 7.2.1.1.6 7.2.1.2.6"    
            ::= { vdsl2PMLineHist15MinEntry 18 }
                          
        vdsl2PMLHist15MEfb        OBJECT-TYPE
            SYNTAX      Counter32
            MAX-ACCESS  read-only
            STATUS      current
            DESCRIPTION
                "If retransmission is used in a given transmit direction, this parameter 
                 is a count of the number of error-free bits observed over the 15 minutes
                 accumulation period.
                "
            REFERENCE    "ITU-T G.997.1, paragraph 7.2.1.1.7 7.2.1.2.7"     
            ::= { vdsl2PMLineHist15MinEntry 19 } 
            
        vdsl2PMLHist15MMinEftr    OBJECT-TYPE
            SYNTAX      Counter32
            MAX-ACCESS  read-only
            STATUS      current
            DESCRIPTION
                "If retransmission is used in a given transmit direction, this parameter 
                 reports the minimum of the EFTR(Error-free throughput rate) observed 
                 over the 15 minutes accumulation period.
                "
            REFERENCE    "ITU-T G.997.1, paragraph 7.2.1.1.8 7.2.1.2.8"     
            ::= { vdsl2PMLineHist15MinEntry 20 } 
        
        hwvdsl2PMLHist15MSraDownShiftEvent OBJECT-TYPE
            SYNTAX      Counter32
            MAX-ACCESS  read-only
            STATUS      current
            DESCRIPTION
                "This parameter is a count of sra downshift event occurring on the line over the 15 minutes accumulation period."
            ::= { vdsl2PMLineHist15MinEntry 21 } 
            
        hwvdsl2PMLHist15MSraUpShiftEvent OBJECT-TYPE
            SYNTAX      Counter32
            MAX-ACCESS  read-only
            STATUS      current
            DESCRIPTION
                "This parameter is a count of sra upshift event occurring on the line over the 15 minutes accumulation period."
            ::= { vdsl2PMLineHist15MinEntry 22 }
            
        hwvdsl2PMLHist15MDisorderLeavingEvent OBJECT-TYPE
            SYNTAX      Counter32
            MAX-ACCESS  read-only
            STATUS      current
            DESCRIPTION
                "This parameter is a count of disorder leaving event occurring on the line over the 15 minutes accumulation period."
            ::= { vdsl2PMLineHist15MinEntry 23 } 
            
        hwvdsl2PMLHist15MLof OBJECT-TYPE
            SYNTAX      Counter32
            MAX-ACCESS  read-only
            STATUS      current
            DESCRIPTION
                "This parameter is a count of loss of frame failure occurring on the line over the 15 minutes accumulation period."
            ::= { vdsl2PMLineHist15MinEntry 24 } 
            
        hwvdsl2PMLHist15MLos OBJECT-TYPE
            SYNTAX      Counter32
            MAX-ACCESS  read-only
            STATUS      current
            DESCRIPTION
                "This parameter is a count of loss of signal failure occurring on the line over the 15 minutes accumulation period."
            ::= { vdsl2PMLineHist15MinEntry 25 } 
            
        hwvdsl2PMLHist15MLop OBJECT-TYPE
            SYNTAX      Counter32
            MAX-ACCESS  read-only
            STATUS      current
            DESCRIPTION
                "This parameter is a count of loss of power failure occurring on the line over the 15 minutes accumulation period."
            ::= { vdsl2PMLineHist15MinEntry 26 }
            
        hwvdsl2PMLHist15MLom OBJECT-TYPE
            SYNTAX      Counter32
            MAX-ACCESS  read-only
            STATUS      current
            DESCRIPTION
                "This parameter is a count of loss of margin failure occurring on the line over the 15 minutes accumulation period."
            ::= { vdsl2PMLineHist15MinEntry 27 }     
                       
          --       PM line history 1 Day       
        vdsl2PMLineHist1DayTable     OBJECT-TYPE
            SYNTAX      SEQUENCE  OF  Vdsl2PMLineHist1DayEntry
            MAX-ACCESS  not-accessible
            STATUS      current
            DESCRIPTION
                "The table vdsl2PMLineHist1DayTable contains PM line history
                 for 24 hours intervals of VDSL2 line.
                 The indexes of this table are an interface index where the
                 interface has an ifType of vdsl2(251), the termination unit
                 and an interval number.
                "
            ::= { vdsl2PMLine 4 }
        
        vdsl2PMLineHist1DayEntry  OBJECT-TYPE
            SYNTAX      Vdsl2PMLineHist1DayEntry
            MAX-ACCESS  not-accessible
            STATUS      current
            DESCRIPTION
                "The table vdsl2PMLineHist1DayTable contains PM line history
                 for 24 hours intervals of VDSL2 line.
                 The indexes of this entry are an interface index where the
                 interface has an ifType of vdsl2(251), the termination unit
                 and an interval number.
                "            
            INDEX  { ifIndex,
                     vdsl2PMLHist1DUnit,
                     vdsl2PMLHist1DInterval }
            ::= { vdsl2PMLineHist1DayTable 1 }
        
        Vdsl2PMLineHist1DayEntry  ::=
            SEQUENCE {
              vdsl2PMLHist1DUnit              Vdsl2Unit,
              vdsl2PMLHist1DInterval          Unsigned32,
              vdsl2PMLHist1DMonitoredTime     Unsigned32,
              vdsl2PMLHist1DFecs              Counter32,
              vdsl2PMLHist1DEs                Counter32,
              vdsl2PMLHist1DSes               Counter32,
              vdsl2PMLHist1DLoss              Counter32,
              vdsl2PMLHist1DUas               Counter32,
              vdsl2PMLHist1DValidInterval     TruthValue,
              vdsl2PMLHist1DLofs              Counter32,
              vdsl2PMLHist1DLols              Counter32,
              vdsl2PMLHist1DLops              Counter32,
              vdsl2PMLHist1DSosSuccess        Counter32,
              vdsl2PMLHist1DInmainpeq         OCTET STRING,
              vdsl2PMLHist1DInmame            Counter32,
              vdsl2PMLHist1DInmaiat           OCTET STRING,
              vdsl2PMLHist1DStartTime         DateAndTime,
              vdsl2PMLHist1DLeftrs            Counter32,
              vdsl2PMLHist1DEfb               Counter32, 
              vdsl2PMLHist1DMinEftr           Counter32,
              hwvdsl2PMLHist1DSraDownShiftEvent  Counter32,
              hwvdsl2PMLHist1DSraUpShiftEvent    Counter32,
              hwvdsl2PMLHist1DDisorderLeavingEvent Counter32,
              hwvdsl2PMLHist1DLof             Counter32,
              hwvdsl2PMLHist1DLos             Counter32,
              hwvdsl2PMLHist1DLop             Counter32,
              hwvdsl2PMLHist1DLom             Counter32
            }
        
        vdsl2PMLHist1DUnit  OBJECT-TYPE
            SYNTAX      Vdsl2Unit
            MAX-ACCESS  not-accessible
            STATUS      current
            DESCRIPTION
                "The termination unit."
            ::= { vdsl2PMLineHist1DayEntry 1 }
        
        vdsl2PMLHist1DInterval  OBJECT-TYPE
            SYNTAX      Unsigned32
            MAX-ACCESS  not-accessible
            STATUS      current
            DESCRIPTION
                "The interval number."
            ::= { vdsl2PMLineHist1DayEntry 2 }
            
        vdsl2PMLHist1DMonitoredTime  OBJECT-TYPE
            SYNTAX      Unsigned32
            UNITS       "seconds"
            MAX-ACCESS  read-only
            STATUS      current
            DESCRIPTION
                "Total seconds monitored in this interval.
                 Unit: seconds
                "
            ::= { vdsl2PMLineHist1DayEntry 3 }
        
        vdsl2PMLHist1DFecs  OBJECT-TYPE
            SYNTAX      Counter32
            UNITS       "seconds"
            MAX-ACCESS  read-only
            STATUS      current
            DESCRIPTION
                "Count of seconds during this interval that there was at least
                 one FEC correction event for one or more bearer channels in
                 this line.  This parameter is inhibited during UAS or SES.
                 Unit: seconds
                "
            REFERENCE    "ITU-T G.997.1, paragraph 7.2.1"
            ::= { vdsl2PMLineHist1DayEntry 4 }
        
        vdsl2PMLHist1DEs  OBJECT-TYPE
            SYNTAX      Counter32
            UNITS       "seconds"
            MAX-ACCESS  read-only
            STATUS      current
            DESCRIPTION
                "Count of seconds during this interval that there was:
                 xTU-C: CRC-8 &gt;= 1 for one or more bearer channels OR
                        LOS &gt;= 1 OR SEF &gt;= 1 OR LPR &gt;= 1
                 xTU-R: FEBE &gt;= 1 for one or more bearer channels OR
                        LOS-FE &gt;= 1 OR RDI &gt;= 1 OR LPR-FE &gt;= 1.
                 This parameter is inhibited during UAS.
                 Unit: seconds
                "
            REFERENCE    "ITU-T G.997.1, paragraph 7.2.1"
            ::= { vdsl2PMLineHist1DayEntry 5 }
        
        vdsl2PMLHist1DSes  OBJECT-TYPE
            SYNTAX      Counter32
            UNITS       "seconds"
            MAX-ACCESS  read-only
            STATUS      current
            DESCRIPTION
                "Count of seconds during this interval that there was:
                 xTU-C: (CRC-8 summed over all bearer channels) &gt;= 18 OR
                        LOS &gt;= 1 OR SEF &gt;&gt; 1 OR LPR &gt;= 1
                 xTU-R: (FEBE summed over all bearer channels) &gt;= 18 OR
                        LOS-FE &gt;= 1 OR RDI &gt;= 1 OR LPR-FE &gt;= 1.
                 This parameter is inhibited during UAS.
                 Unit: seconds
                "
            REFERENCE    "ITU-T G.997.1, paragraph 7.2.1"
            ::= { vdsl2PMLineHist1DayEntry 6 }
        
        vdsl2PMLHist1DLoss  OBJECT-TYPE
            SYNTAX      Counter32
            UNITS       "seconds"
            MAX-ACCESS  read-only
            STATUS      current
            DESCRIPTION
                "Count of seconds during this interval that there was LOS (or
                 LOS-FE for xTU-R).
                 Unit: seconds
                "
            REFERENCE    "ITU-T G.997.1, paragraph 7.2.1"
            ::= { vdsl2PMLineHist1DayEntry 7 }
        
        vdsl2PMLHist1DUas  OBJECT-TYPE
            SYNTAX      Counter32
            UNITS       "seconds"
            MAX-ACCESS  read-only
            STATUS      current
            DESCRIPTION
                "Count of seconds in Unavailability State during this interval.
                 Unavailability begins at the onset of 10 contiguous severely
                 -errored seconds, and ends at the onset of 10 contiguous
                 seconds with no severely-errored seconds.
                 Unit: seconds
                "
            REFERENCE    "ITU-T G.997.1, paragraph 7.2.1"
            ::= { vdsl2PMLineHist1DayEntry 8 }
        
        vdsl2PMLHist1DValidInterval  OBJECT-TYPE
            SYNTAX      TruthValue
            MAX-ACCESS  read-only
            STATUS      current
            DESCRIPTION
                "This variable indicates if the data for this interval is
                 valid.
                "
            ::= { vdsl2PMLineHist1DayEntry 9 }
        
        vdsl2PMLHist1DLofs  OBJECT-TYPE
            SYNTAX      Counter32
            UNITS       "seconds"
            MAX-ACCESS  read-only
            STATUS      current
            DESCRIPTION
                "Count of seconds during this interval that there was Loss of Framing.
                 Unit: seconds
                "
            ::= { vdsl2PMLineHist1DayEntry 10 }
        
        vdsl2PMLHist1DLols  OBJECT-TYPE
            SYNTAX      Counter32
            UNITS       "seconds"
            MAX-ACCESS  read-only
            STATUS      current
            DESCRIPTION
                "Count of seconds during this interval that there was Loss of Link.
                 Unit: seconds
                "
            ::= { vdsl2PMLineHist1DayEntry 11 }
        
        vdsl2PMLHist1DLops  OBJECT-TYPE
            SYNTAX      Counter32
            UNITS       "seconds"
            MAX-ACCESS  read-only
            STATUS      current
            DESCRIPTION
                "Count of seconds during this interval that there was Loss of Power.
                 Unit: seconds
                "
            ::= { vdsl2PMLineHist1DayEntry 12 }
        
        vdsl2PMLHist1DSosSuccess  OBJECT-TYPE
            SYNTAX      Counter32
            UNITS       "times"
            MAX-ACCESS  read-only
            STATUS      current
            DESCRIPTION
                "Count of the total number of successful SOS procedures initiated during this interval.
                 Unit: times
                "
            REFERENCE    "ITU-T G.997.1, paragraph 7.2.1"
            ::= { vdsl2PMLineHist1DayEntry 13 }
           
        vdsl2PMLHist1DInmainpeq  OBJECT-TYPE
            SYNTAX      OCTET STRING  (SIZE(0..68))
            MAX-ACCESS  read-only
            STATUS      current
            DESCRIPTION
                "This parameter is a count of the INMAINPEQi anomalies 
                 occurring on the line over the 24 hours accumulation period.
                "
            REFERENCE    "ITU-T G.997.1, paragraph 7.2.1"
            ::= { vdsl2PMLineHist1DayEntry 14 }        
            
        vdsl2PMLHist1DInmame  OBJECT-TYPE
            SYNTAX      Counter32
            MAX-ACCESS  read-only
            STATUS      current
            DESCRIPTION
                "This parameter is a count of the INMAME anomalies 
                 occurring on the line over the 24 hours accumulation period.
                "
            REFERENCE    "ITU-T G.997.1, paragraph 7.2.1"
            ::= { vdsl2PMLineHist1DayEntry 15 }    
            
        vdsl2PMLHist1DInmaiat  OBJECT-TYPE
            SYNTAX      OCTET STRING  (SIZE(0..32))
            MAX-ACCESS  read-only
            STATUS      current
            DESCRIPTION
                "This parameter is a count of the INMAIATi anomalies 
                 occurring on the line over the 24 hours accumulation period.
                "
            REFERENCE    "ITU-T G.997.1, paragraph 7.2.1"
            ::= { vdsl2PMLineHist1DayEntry 16 }
           
        vdsl2PMLHist1DStartTime  OBJECT-TYPE
            SYNTAX      DateAndTime
            MAX-ACCESS  read-only
            STATUS      current
            DESCRIPTION
                "Start time of the historical 1-day performance statistics."
            ::= { vdsl2PMLineHist1DayEntry 17 }  

       vdsl2PMLHist1DLeftrs     OBJECT-TYPE
            SYNTAX      Counter32
            MAX-ACCESS  read-only
            STATUS      current
            DESCRIPTION
                "If retransmission is used in a given transmit direction, this parameter 
                 is a count of the seconds with a near-end leftr defect present observed 
                 over the 24 hours accumulation period.
                "
            REFERENCE    "ITU-T G.997.1, paragraph 7.2.1.1.6 7.2.1.2.6"     
            ::= { vdsl2PMLineHist1DayEntry 18 }
                          
        vdsl2PMLHist1DEfb        OBJECT-TYPE
            SYNTAX      Counter32
            MAX-ACCESS  read-only
            STATUS      current
            DESCRIPTION
                "If retransmission is used in a given transmit direction, this parameter 
                 is a count of the number of error-free bits observed over the 24 hours 
                 accumulation period.
                "
            REFERENCE    "ITU-T G.997.1, paragraph 7.2.1.1.7 7.2.1.2.7" 
            ::= { vdsl2PMLineHist1DayEntry 19 } 
            
        vdsl2PMLHist1DMinEftr    OBJECT-TYPE
            SYNTAX      Counter32
            MAX-ACCESS  read-only
            STATUS      current
            DESCRIPTION
                "If retransmission is used in a given transmit direction, this parameter 
                 reports the minimum of the EFTR(Error-free throughput rate) observed 
                 over the 24 hours accumulation period.
                "
            REFERENCE    "ITU-T G.997.1, paragraph 7.2.1.1.8 7.2.1.2.8"     
            ::= { vdsl2PMLineHist1DayEntry 20 }             
            
        hwvdsl2PMLHist1DSraDownShiftEvent OBJECT-TYPE
            SYNTAX      Counter32
            MAX-ACCESS  read-only
            STATUS      current
            DESCRIPTION
                "This parameter is a count of sra downshift event occurring on the line over the 24 hours accumulation period."
            ::= { vdsl2PMLineHist1DayEntry 21 } 
            
        hwvdsl2PMLHist1DSraUpShiftEvent OBJECT-TYPE
            SYNTAX      Counter32
            MAX-ACCESS  read-only
            STATUS      current
            DESCRIPTION
                "This parameter is a count of sra upshift event occurring on the line over the 24 hours accumulation period."
            ::= { vdsl2PMLineHist1DayEntry 22 }
            
        hwvdsl2PMLHist1DDisorderLeavingEvent OBJECT-TYPE
            SYNTAX      Counter32
            MAX-ACCESS  read-only
            STATUS      current
            DESCRIPTION
                "This parameter is a count of disorder leaving event occurring on the line over the 24 hours accumulation period."
            ::= { vdsl2PMLineHist1DayEntry 23 } 
            
        hwvdsl2PMLHist1DLof OBJECT-TYPE
            SYNTAX      Counter32
            MAX-ACCESS  read-only
            STATUS      current
            DESCRIPTION
                "This parameter is a count of loss of frame failure occurring on the line over the 24 hours accumulation period."
            ::= { vdsl2PMLineHist1DayEntry 24 } 
            
        hwvdsl2PMLHist1DLos OBJECT-TYPE
            SYNTAX      Counter32
            MAX-ACCESS  read-only
            STATUS      current
            DESCRIPTION
                "This parameter is a count of loss of signal failure occurring on the line over the 24 hours accumulation period."
            ::= { vdsl2PMLineHist1DayEntry 25 } 
            
        hwvdsl2PMLHist1DLop OBJECT-TYPE
            SYNTAX      Counter32
            MAX-ACCESS  read-only
            STATUS      current
            DESCRIPTION
                "This parameter is a count of loss of power failure occurring on the line over the 24 hours accumulation period."
            ::= { vdsl2PMLineHist1DayEntry 26 }
            
        hwvdsl2PMLHist1DLom OBJECT-TYPE
            SYNTAX      Counter32
            MAX-ACCESS  read-only
            STATUS      current
            DESCRIPTION
                "This parameter is a count of loss of margin failure occurring on the line over the 24 hours accumulation period."
            ::= { vdsl2PMLineHist1DayEntry 27 }    
                
          --     PM line init history 15 Minutes   
        
        vdsl2PMLineInitHist15MinTable      OBJECT-TYPE
            SYNTAX      SEQUENCE  OF  Vdsl2PMLineInitHist15MinEntry
            MAX-ACCESS  not-accessible
            STATUS      current
            DESCRIPTION
                "The table vdsl2PMLineInitHist15MinTable contains PM line
                 initialization history for 15 minutes intervals of VDSL2 line.  
                 The indexes of this table are an interface index where the
                 interface has an ifType of vdsl2(251) and an interval number.
                "
            ::= { vdsl2PMLine 5 }
        
        vdsl2PMLineInitHist15MinEntry  OBJECT-TYPE
            SYNTAX      Vdsl2PMLineInitHist15MinEntry
            MAX-ACCESS  not-accessible
            STATUS      current
            DESCRIPTION
                "The table vdsl2PMLineInitHist15MinTable contains PM line
                 initialization history for 15 minutes intervals of VDSL2 line.
                 The indexes of this entry are an interface index where the
                 interface has an ifType of vdsl2(251) and an interval number.
                "           
            INDEX  { ifIndex,
                     vdsl2PMLHistInit15MInterval }
            ::= { vdsl2PMLineInitHist15MinTable 1 }
        
        Vdsl2PMLineInitHist15MinEntry  ::=
            SEQUENCE {
              vdsl2PMLHistInit15MInterval              Unsigned32,
              vdsl2PMLHistInit15MMonitoredTime         Unsigned32,
              vdsl2PMLHistInit15MFullInits             Unsigned32,
              vdsl2PMLHistInit15MFailedFullInits       Unsigned32,
              vdsl2PMLHistInit15MShortInits            Unsigned32,
              vdsl2PMLHistInit15MFailedShortInits      Unsigned32,
              vdsl2PMLHistInit15MValidInterval         TruthValue,
              vdsl2PMLHistInit15MStartTime             DateAndTime
            }
        
        vdsl2PMLHistInit15MInterval  OBJECT-TYPE
            SYNTAX      Unsigned32
            MAX-ACCESS  not-accessible
            STATUS      current
            DESCRIPTION
                "The interval number."
            ::= { vdsl2PMLineInitHist15MinEntry 1 }
        
        vdsl2PMLHistInit15MMonitoredTime  OBJECT-TYPE
            SYNTAX      Unsigned32
            UNITS       "seconds"
            MAX-ACCESS  read-only
            STATUS      current
            DESCRIPTION
                "Total seconds monitored in this interval.
                 Unit: seconds
                "
            ::= { vdsl2PMLineInitHist15MinEntry 2 }
        
        vdsl2PMLHistInit15MFullInits  OBJECT-TYPE
            SYNTAX      Unsigned32
            MAX-ACCESS  read-only
            STATUS      current
            DESCRIPTION
                "Count of full initializations attempted on the line
                 (successful and failed) during this interval.
                "
            REFERENCE    "ITU-T G.997.1, paragraph 7.2.1"
            ::= { vdsl2PMLineInitHist15MinEntry 3 }
        
        vdsl2PMLHistInit15MFailedFullInits  OBJECT-TYPE
            SYNTAX      Unsigned32
            MAX-ACCESS  read-only
            STATUS      current
            DESCRIPTION
                "Count of failed full initializations on the line during this
                 interval.
                "
            REFERENCE    "ITU-T G.997.1, paragraph 7.2.1"
            ::= { vdsl2PMLineInitHist15MinEntry 4 }
        
        vdsl2PMLHistInit15MShortInits  OBJECT-TYPE
            SYNTAX      Unsigned32
            MAX-ACCESS  read-only
            STATUS      current
            DESCRIPTION
                "Count of short initializations attempted on the line
                 (successful and failed) during this interval.
                "
            REFERENCE    "ITU-T G.997.1, paragraph 7.2.1"
            ::= { vdsl2PMLineInitHist15MinEntry 5 }
        
        vdsl2PMLHistInit15MFailedShortInits  OBJECT-TYPE
            SYNTAX      Unsigned32
            MAX-ACCESS  read-only
            STATUS      current
            DESCRIPTION
                "Count of failed short initializations on the line during this
                 interval.
                "
            REFERENCE    "ITU-T G.997.1, paragraph 7.2.1"
            ::= { vdsl2PMLineInitHist15MinEntry 6 }
        
        vdsl2PMLHistInit15MValidInterval  OBJECT-TYPE
            SYNTAX      TruthValue
            MAX-ACCESS  read-only
            STATUS      current
            DESCRIPTION
                "This variable indicates if the data for this interval is
                 valid.
                "
            ::= { vdsl2PMLineInitHist15MinEntry 7 }
           
        vdsl2PMLHistInit15MStartTime  OBJECT-TYPE
            SYNTAX      DateAndTime
            MAX-ACCESS  read-only
            STATUS      current
            DESCRIPTION
                "Start time of the historical initializations 15-minute performance statistics."
            ::= { vdsl2PMLineInitHist15MinEntry 8 }  
           
        
          --       PM line init history 1 Day      
        vdsl2PMLineInitHist1DayTable       OBJECT-TYPE
            SYNTAX      SEQUENCE  OF  Vdsl2PMLineInitHist1DayEntry
            MAX-ACCESS  not-accessible
            STATUS      current
            DESCRIPTION
                "The table vdsl2PMLineInitHist1DayTable contains PM line
                 initialization history for 24 hours intervals of VDSL2 line. 
                 The indexes of this table are an interface index where the
                 interface has an ifType of vdsl2(251) and an interval number.
                "
            ::= { vdsl2PMLine 6 }
        
        vdsl2PMLineInitHist1DayEntry  OBJECT-TYPE
            SYNTAX      Vdsl2PMLineInitHist1DayEntry
            MAX-ACCESS  not-accessible
            STATUS      current
            DESCRIPTION
                "The table vdsl2PMLineInitHist1DayTable contains PM line
                 initialization history for 24 hours intervals of VDSL2 line.
                 The indexes of this entry are an interface index where the
                 interface has an ifType of vdsl2(251) and an interval number.
                "
            INDEX  { ifIndex,
                     vdsl2PMLHistinit1DInterval }
            ::= { vdsl2PMLineInitHist1DayTable 1 }
        
        Vdsl2PMLineInitHist1DayEntry  ::=
            SEQUENCE {
              vdsl2PMLHistinit1DInterval              Unsigned32,
              vdsl2PMLHistinit1DMonitoredTime         Unsigned32,
              vdsl2PMLHistinit1DFullInits             Unsigned32,
              vdsl2PMLHistinit1DFailedFullInits       Unsigned32,
              vdsl2PMLHistinit1DShortInits            Unsigned32,
              vdsl2PMLHistinit1DFailedShortInits      Unsigned32,
              vdsl2PMLHistinit1DValidInterval         TruthValue,
              vdsl2PMLHistinit1DStartTime             DateAndTime
            }
        
        vdsl2PMLHistinit1DInterval  OBJECT-TYPE
            SYNTAX      Unsigned32
            MAX-ACCESS  not-accessible
            STATUS      current
            DESCRIPTION
                "The interval number."
            ::= { vdsl2PMLineInitHist1DayEntry 1 }
        
        vdsl2PMLHistinit1DMonitoredTime  OBJECT-TYPE
            SYNTAX      Unsigned32
            UNITS       "seconds"
            MAX-ACCESS  read-only
            STATUS      current
            DESCRIPTION
                "Total seconds monitored in this interval."
            ::= { vdsl2PMLineInitHist1DayEntry 2 }
        
        vdsl2PMLHistinit1DFullInits  OBJECT-TYPE
            SYNTAX      Unsigned32
            MAX-ACCESS  read-only
            STATUS      current
            DESCRIPTION
                "Count of full initializations attempted on the line
                 (successful and failed) during this interval.
                "
            REFERENCE    "ITU-T G.997.1, paragraph 7.2.1"
             ::= { vdsl2PMLineInitHist1DayEntry 3 }
        
        vdsl2PMLHistinit1DFailedFullInits  OBJECT-TYPE
            SYNTAX      Unsigned32
            MAX-ACCESS  read-only
            STATUS      current
            DESCRIPTION
                "Count of failed full initializations on the line during this
                 interval.
                "
            REFERENCE    "ITU-T G.997.1, paragraph 7.2.1"
            ::= { vdsl2PMLineInitHist1DayEntry 4 }
        
        vdsl2PMLHistinit1DShortInits  OBJECT-TYPE
            SYNTAX      Unsigned32
            MAX-ACCESS  read-only
            STATUS      current
            DESCRIPTION
                "Count of short initializations attempted on the line
                 (successful and failed) during this interval.
                "
            REFERENCE    "ITU-T G.997.1, paragraph 7.2.1"
            ::= { vdsl2PMLineInitHist1DayEntry 5 }
        
        vdsl2PMLHistinit1DFailedShortInits  OBJECT-TYPE
            SYNTAX      Unsigned32
            MAX-ACCESS  read-only
            STATUS      current
            DESCRIPTION
                "Count of failed short initializations on the line during this
                 interval.
                "
            REFERENCE    "ITU-T G.997.1, paragraph 7.2.1"
            ::= { vdsl2PMLineInitHist1DayEntry 6 }
        
        vdsl2PMLHistinit1DValidInterval  OBJECT-TYPE
            SYNTAX      TruthValue
            MAX-ACCESS  read-only
            STATUS      current
            DESCRIPTION
                "This variable indicates if the data for this interval is
                 valid.
                "
            ::= { vdsl2PMLineInitHist1DayEntry 7 }
           
        vdsl2PMLHistinit1DStartTime  OBJECT-TYPE
            SYNTAX      DateAndTime
            MAX-ACCESS  read-only
            STATUS      current
            DESCRIPTION
                "Start time of the historical initializations 1-day performance statistics."
            ::= { vdsl2PMLineInitHist1DayEntry 8 } 

        
          --          PM channel current counters          
        vdsl2PMChCurrTable        OBJECT-TYPE
            SYNTAX      SEQUENCE  OF  Vdsl2PMChCurrEntry
            MAX-ACCESS  not-accessible
            STATUS      current
            DESCRIPTION
                "The table vdsl2PMChCurrTable contains current Performance
                 Monitoring results of VDSL2 channel. 
                 The indexes of this table are an interface index where
                 the interface has an ifType value which is applicable
                 for a DSL channel and the termination unit.
                "
            ::= { vdsl2PMChannel 1 }
        
        vdsl2PMChCurrEntry  OBJECT-TYPE
            SYNTAX      Vdsl2PMChCurrEntry
            MAX-ACCESS  not-accessible
            STATUS      current
            DESCRIPTION
                "The table vdsl2PMChCurrTable contains current Performance
                 Monitoring results of VDSL2 channel.
                 The indexes of this entry are an interface index where
                 the interface has an ifType value which is applicable
                 for a DSL channel and the termination unit.
                "
            INDEX  { ifIndex, vdsl2PMChCurrUnit }
            ::= { vdsl2PMChCurrTable 1 }
        
        Vdsl2PMChCurrEntry  ::=
            SEQUENCE {
              vdsl2PMChCurrUnit                     Vdsl2Unit,
              vdsl2PMChCurrValidIntervals           Unsigned32,
              vdsl2PMChCurrInvalidIntervals         Unsigned32,
              vdsl2PMChCurr15MTimeElapsed           HCPerfTimeElapsed,
              vdsl2PMChCurr15MCodingViolations      Unsigned32,
              vdsl2PMChCurr15MCorrectedBlocks       Unsigned32,
              vdsl2PMChCurr1DayValidIntervals       Unsigned32,
              vdsl2PMChCurr1DayInvalidIntervals     Unsigned32,
              vdsl2PMChCurr1DayTimeElapsed          HCPerfTimeElapsed,
              vdsl2PMChCurr1DayCodingViolations     Unsigned32,
              vdsl2PMChCurr1DayCorrectedBlocks      Unsigned32,
              vdsl2PMChEverBeforeCodingViolations   Unsigned32,
              vdsl2PMChEverBeforeCorrectedBlocks    Unsigned32,
              vdsl2PMChCurr15MEncodedBlocks         Unsigned32,
              vdsl2PMChCurr15MUncorrectableBlocks   Unsigned32,
              vdsl2PMChCurr1DayEncodedBlocks        Unsigned32,
              vdsl2PMChCurr1DayUncorrectableBlocks  Unsigned32, 
              vdsl2PMChEverBeforeEncodedBlocks      Unsigned32,
              vdsl2PMChEverBeforeUncorrectableBlocks Unsigned32,
              vdsl2PMChCurr15MAtmCells              Counter32,
              vdsl2PMChCurr15MPtmPackets            Counter32,
              vdsl2PMChCurr1DayAtmCells             Counter32,
              vdsl2PMChCurr1DayPtmPackets           Counter32,
              vdsl2PMChEverBeforeAtmCells           Counter64,
              vdsl2PMChEverBeforePtmPackets         Counter64,
             vdsl2PMChCurr15MRtxCW		            Counter32,
              vdsl2PMChCurr15MRtxCorrectedCW	    Counter32,
              vdsl2PMChCurr15MRtxUncorrectedCW      Counter32,
              vdsl2PMChCurr1DayRtxCW		        Counter32,
              vdsl2PMChCurr1DayRtxCorrectedCW       Counter32,
              vdsl2PMChCurr1DayRtxUncorrectedCW     Counter32,
              vdsl2PMChEverBeforeRtxCW	            Counter32,
              vdsl2PMChEverBeforeRtxCorrectedCW     Counter32,
              vdsl2PMChEverBeforeRtxUncorrectedCW   Counter32,
              vdsl2PMChCurr15MStartTime             DateAndTime,
              vdsl2PMChCurr1DayStartTime            DateAndTime
            }
        
        vdsl2PMChCurrUnit  OBJECT-TYPE
            SYNTAX      Vdsl2Unit
            MAX-ACCESS  not-accessible
            STATUS      current
            DESCRIPTION
                "The termination unit."
            ::= { vdsl2PMChCurrEntry 1 }
           
        vdsl2PMChCurrValidIntervals  OBJECT-TYPE
            SYNTAX      Unsigned32
            MAX-ACCESS  read-only
            STATUS      current
            DESCRIPTION
                "Valid intervals."
            ::= { vdsl2PMChCurrEntry 2 }
        
        vdsl2PMChCurrInvalidIntervals  OBJECT-TYPE
            SYNTAX      Unsigned32
            MAX-ACCESS  read-only
            STATUS      current
            DESCRIPTION
                "Invalid intervals."
             ::= { vdsl2PMChCurrEntry 3 }
        
        vdsl2PMChCurr15MTimeElapsed  OBJECT-TYPE
            SYNTAX      HCPerfTimeElapsed
            UNITS       "seconds"
            MAX-ACCESS  read-only
            STATUS      current
            DESCRIPTION
                "Total elapsed seconds in this interval.
                 Unit: seconds
                "
            ::= { vdsl2PMChCurrEntry 4 }
        
        vdsl2PMChCurr15MCodingViolations  OBJECT-TYPE
            SYNTAX      Unsigned32
            MAX-ACCESS  read-only
            STATUS      current
            DESCRIPTION
                "Count of CRC-8 (FEBE for xTU-R) anomalies occurring in the
                 channel during the interval.  This parameter is inhibited
                 during UAS or SES.  If the CRC is applied over multiple
                 channels, then each related CRC-8 (or FEBE) anomaly should
                 increment each of the counters related to the individual
                 channels.
                "
            REFERENCE    "ITU-T G.997.1, paragraph 7.2.2"
           ::= { vdsl2PMChCurrEntry 5 }
        
        vdsl2PMChCurr15MCorrectedBlocks  OBJECT-TYPE
            SYNTAX      Unsigned32
            MAX-ACCESS  read-only
            STATUS      current
            DESCRIPTION
                "Count of FEC (FFEC for xTU-R) anomalies (corrected code words)
                 occurring in the channel during the interval.  This parameter
                 is inhibited during UAS or SES.  If the FEC is applied over
                 multiple channels, then each related FEC (or FFEC) anomaly
                 should increment each of the counters related to the
                 individual channels.
                "
            REFERENCE    "ITU-T G.997.1, paragraph 7.2.2"
            ::= { vdsl2PMChCurrEntry 6 }
        
        vdsl2PMChCurr1DayValidIntervals  OBJECT-TYPE
            SYNTAX      Unsigned32
            MAX-ACCESS  read-only
            STATUS      current
            DESCRIPTION
                "Valid intervals."
            ::= { vdsl2PMChCurrEntry 7 }
        
        vdsl2PMChCurr1DayInvalidIntervals  OBJECT-TYPE
            SYNTAX      Unsigned32
            MAX-ACCESS  read-only
            STATUS      current
            DESCRIPTION
                "Invalid intervals."
            ::= { vdsl2PMChCurrEntry 8 }
           
        vdsl2PMChCurr1DayTimeElapsed  OBJECT-TYPE
            SYNTAX      HCPerfTimeElapsed
            UNITS       "seconds"
            MAX-ACCESS  read-only
            STATUS      current
            DESCRIPTION
                "Total elapsed seconds in this interval.
                 Unit: seconds
                "
            ::= { vdsl2PMChCurrEntry 9 }
        
        vdsl2PMChCurr1DayCodingViolations  OBJECT-TYPE
            SYNTAX      Unsigned32
            MAX-ACCESS  read-only
            STATUS      current
            DESCRIPTION
                "Count of CRC-8 (FEBE for xTU-R) anomalies occurring in the
                 channel during the interval.  This parameter is inhibited
                 during UAS or SES.  If the CRC is applied over multiple
                 channels, then each related CRC-8 (or FEBE) anomaly should
                 increment each of the counters related to the individual
                 channels.
                "
            REFERENCE    "ITU-T G.997.1, paragraph 7.2.2"
            ::= { vdsl2PMChCurrEntry 10 }
        
        vdsl2PMChCurr1DayCorrectedBlocks  OBJECT-TYPE
            SYNTAX      Unsigned32
            MAX-ACCESS  read-only
            STATUS      current
            DESCRIPTION
                "Count of FEC (FFEC for xTU-R) anomalies (corrected code words)
                 occurring in the channel during the interval.  This parameter
                 is inhibited during UAS or SES.  If the FEC is applied over
                 multiple channels, then each related FEC (or FFEC) anomaly
                 should increment each of the counters related to the
                 individual channels.
                "
            REFERENCE    "ITU-T G.997.1, paragraph 7.2.2"
            ::= { vdsl2PMChCurrEntry 11 }
        
        
        vdsl2PMChEverBeforeCodingViolations  OBJECT-TYPE
            SYNTAX      Unsigned32
            MAX-ACCESS  read-only
            STATUS      current
            DESCRIPTION
                "Count of CRC-8 (FEBE for xTU-R) anomalies occurring in the
                 channel since agent reset.  This parameter is inhibited
                 during UAS or SES.  If the CRC is applied over multiple
                 channels, then each related CRC-8 (or FEBE) anomaly should
                 increment each of the counters related to the individual
                 channels.
                 Huawei defined.
                "                 
            ::= { vdsl2PMChCurrEntry 12 }  
                                          
        vdsl2PMChEverBeforeCorrectedBlocks  OBJECT-TYPE
            SYNTAX      Unsigned32         
            MAX-ACCESS  read-only          
            STATUS      current            
            DESCRIPTION                    
                "Count of FEC (FFEC for xTU-R) anomalies (corrected code words)
                 occurring in the channel since agent reset.  This parameter
                 is inhibited during UAS or SES.  If the FEC is applied over
                 multiple channels, then each related FEC (or FFEC) anomaly
                 should increment each of the counters related to the
                 individual channels.
                 Huawei defined.
                "      
            ::= { vdsl2PMChCurrEntry 13 }  
        
        vdsl2PMChCurr15MEncodedBlocks  OBJECT-TYPE
            SYNTAX      Unsigned32         
            MAX-ACCESS  read-only          
            STATUS      current            
            DESCRIPTION                    
                "Count of all encoded blocks received 
                 on this channel within the current 15 minute interval.
                "      
            ::= { vdsl2PMChCurrEntry 14 }
            
        vdsl2PMChCurr15MUncorrectableBlocks  OBJECT-TYPE
            SYNTAX      Unsigned32         
            MAX-ACCESS  read-only          
            STATUS      current            
            DESCRIPTION                    
                "Count of all blocks received with 
                 uncorrectable errors on this channel within the current 15 minute interval.
                "      
            ::= { vdsl2PMChCurrEntry 15 }
        
        vdsl2PMChCurr1DayEncodedBlocks  OBJECT-TYPE
            SYNTAX      Unsigned32         
            MAX-ACCESS  read-only          
            STATUS      current            
            DESCRIPTION                    
                "Count of all encoded blocks received on this channel during the current day."      
            ::= { vdsl2PMChCurrEntry 16 }
        
        vdsl2PMChCurr1DayUncorrectableBlocks  OBJECT-TYPE
            SYNTAX      Unsigned32         
            MAX-ACCESS  read-only          
            STATUS      current            
            DESCRIPTION                    
                "Count of all blocks received with uncorrectable errors on this channel during the current day."      
            ::= { vdsl2PMChCurrEntry 17 }
        
        vdsl2PMChEverBeforeEncodedBlocks  OBJECT-TYPE
            SYNTAX      Unsigned32         
            MAX-ACCESS  read-only          
            STATUS      current            
            DESCRIPTION                    
                "Count of all encoded blocks received on this
                 channel since agent reset.
                "      
            ::= { vdsl2PMChCurrEntry 18 }
           
        vdsl2PMChEverBeforeUncorrectableBlocks  OBJECT-TYPE
            SYNTAX      Unsigned32         
            MAX-ACCESS  read-only          
            STATUS      current            
            DESCRIPTION                    
                "Count of all blocks received with uncorrectable
                 errors since agent reset.
                "      
            ::= { vdsl2PMChCurrEntry 19 }
        
        vdsl2PMChCurr15MAtmCells  OBJECT-TYPE
            SYNTAX      Counter32         
            MAX-ACCESS  read-only          
            STATUS      current            
            DESCRIPTION                    
                "Count of Atm Cells received
                 within the current 15 minute interval.
                "      
            ::= { vdsl2PMChCurrEntry 20 }
        
        vdsl2PMChCurr15MPtmPackets  OBJECT-TYPE
            SYNTAX      Counter32         
            MAX-ACCESS  read-only          
            STATUS      current            
            DESCRIPTION                    
                "Count of Ptm Packet received
                 within the current 15 minute interval.
                "      
            ::= { vdsl2PMChCurrEntry 21 }
           
        vdsl2PMChCurr1DayAtmCells  OBJECT-TYPE
            SYNTAX      Counter32         
            MAX-ACCESS  read-only          
            STATUS      current            
            DESCRIPTION                    
                "Count of Atm Cells received
                 during the current day.
                "      
            ::= { vdsl2PMChCurrEntry 22 }   
        
        vdsl2PMChCurr1DayPtmPackets  OBJECT-TYPE
            SYNTAX      Counter32         
            MAX-ACCESS  read-only          
            STATUS      current            
            DESCRIPTION                    
                "Count of Ptm Packets received
                 during the current day.
                "      
            ::= { vdsl2PMChCurrEntry 23 }   
           
        vdsl2PMChEverBeforeAtmCells  OBJECT-TYPE
            SYNTAX      Counter64         
            MAX-ACCESS  read-only          
            STATUS      current            
            DESCRIPTION                    
                "Count of Atm Cells received 
                 since agent reset.
                "      
            ::= { vdsl2PMChCurrEntry 24 }  
           
        vdsl2PMChEverBeforePtmPackets  OBJECT-TYPE
            SYNTAX      Counter64         
            MAX-ACCESS  read-only          
            STATUS      current            
            DESCRIPTION                    
               "Count of Ptm Packets received
                since agent reset."      
            ::= { vdsl2PMChCurrEntry 25 }       
           
        vdsl2PMChCurr15MRtxCW  OBJECT-TYPE
            SYNTAX      Counter32
            MAX-ACCESS  read-only
            STATUS      current
            DESCRIPTION
               "Count of units request retransmission within the current 15 minute interval."
            ::= { vdsl2PMChCurrEntry 26 }
           
        vdsl2PMChCurr15MRtxCorrectedCW  OBJECT-TYPE
            SYNTAX      Counter32
            MAX-ACCESS  read-only
            STATUS      current
            DESCRIPTION
                "Count of units corrected by retransmission within the current 15 minute interval."
            ::= { vdsl2PMChCurrEntry 27 }
           
        vdsl2PMChCurr15MRtxUncorrectedCW  OBJECT-TYPE
            SYNTAX      Counter32
            MAX-ACCESS  read-only
            STATUS      current
            DESCRIPTION
                "Count of units uncorrected by retransmission within the current 15 minute interval."
            ::= { vdsl2PMChCurrEntry 28 }
        
        vdsl2PMChCurr1DayRtxCW  OBJECT-TYPE
            SYNTAX      Counter32
            MAX-ACCESS  read-only
            STATUS      current
            DESCRIPTION
                "Count of units request retransmission during the current day."
            ::= { vdsl2PMChCurrEntry 29 }
           
        vdsl2PMChCurr1DayRtxCorrectedCW  OBJECT-TYPE
            SYNTAX      Counter32
            MAX-ACCESS  read-only
            STATUS      current
            DESCRIPTION
                "Count of units corrected by retransmission during the current day."
            ::= { vdsl2PMChCurrEntry 30 }
        
        vdsl2PMChCurr1DayRtxUncorrectedCW  OBJECT-TYPE
            SYNTAX      Counter32
            MAX-ACCESS  read-only
            STATUS      current
            DESCRIPTION
                "Count of units uncorrected by retransmission during the current day."
            ::= { vdsl2PMChCurrEntry 31 }
           
        vdsl2PMChEverBeforeRtxCW  OBJECT-TYPE
            SYNTAX      Counter32
            MAX-ACCESS  read-only
            STATUS      current
            DESCRIPTION
                "Count of units request retransmission since agent reset."
            ::= { vdsl2PMChCurrEntry 32 }
           
        vdsl2PMChEverBeforeRtxCorrectedCW  OBJECT-TYPE
            SYNTAX      Counter32
            MAX-ACCESS  read-only
            STATUS      current
            DESCRIPTION
                "Count of units corrected by retransmission since agent reset."
            ::= { vdsl2PMChCurrEntry 33 }
        
        vdsl2PMChEverBeforeRtxUncorrectedCW  OBJECT-TYPE
            SYNTAX      Counter32
            MAX-ACCESS  read-only
            STATUS      current
            DESCRIPTION
                 "Count of units uncorrected by retransmission since agent reset."
            ::= { vdsl2PMChCurrEntry 34 }      
           
        vdsl2PMChCurr15MStartTime  OBJECT-TYPE
            SYNTAX      DateAndTime
            MAX-ACCESS  read-only
            STATUS      current
            DESCRIPTION
                "Start time of the channel current 15-minute performance statistics."
            ::= { vdsl2PMChCurrEntry 35 }    
           
        vdsl2PMChCurr1DayStartTime  OBJECT-TYPE
            SYNTAX      DateAndTime
            MAX-ACCESS  read-only
            STATUS      current
            DESCRIPTION
                "Start time of the channel current 1-day performance statistics."
            ::= { vdsl2PMChCurrEntry 36 } 
          --    PM channel history 15 Minutes      
        vdsl2PMChHist15MinTable         OBJECT-TYPE
            SYNTAX      SEQUENCE  OF  Vdsl2PMChHist15MinEntry
            MAX-ACCESS  not-accessible
            STATUS      current
            DESCRIPTION
                "The table vdsl2PMChHist15MinTable contains PM channel history 
                 for 15min intervals of VDSL2 channel. 
                 The indexes of this table are an interface index where
                 the interface has an ifType value which is applicable
                 for a DSL channel, the termination unit and the
                 interval number.
                "
            ::= { vdsl2PMChannel 2 }
        
        vdsl2PMChHist15MinEntry  OBJECT-TYPE
            SYNTAX      Vdsl2PMChHist15MinEntry
            MAX-ACCESS  not-accessible
            STATUS      current
            DESCRIPTION
                "The table vdsl2PMChHist15MinTable contains PM channel history 
                 for 15min intervals of VDSL2 channel.
                 The indexes of this entry are an interface index where
                 the interface has an ifType value which is applicable
                 for a DSL channel, the termination unit and the
                 interval number.
                "
            INDEX  { ifIndex,
                     vdsl2PMChHist15MUnit,
                     vdsl2PMChHist15MInterval }
            ::= { vdsl2PMChHist15MinTable 1 }
        
        Vdsl2PMChHist15MinEntry  ::=
            SEQUENCE {
              vdsl2PMChHist15MUnit                     Vdsl2Unit,
              vdsl2PMChHist15MInterval                 Unsigned32,
              vdsl2PMChHist15MMonitoredTime            Unsigned32,
              vdsl2PMChHist15MCodingViolations         Unsigned32,
              vdsl2PMChHist15MCorrectedBlocks          Unsigned32,
              vdsl2PMChHist15MValidInterval            TruthValue,
              vdsl2PMChHist15MEncodedBlocks            Unsigned32,
              vdsl2PMChHist15MUncorrectableBlocks      Unsigned32,
              vdsl2PMChHist15MAtmCells                 Counter32,
              vdsl2PMChHist15MPtmPackets               Counter32,
              vdsl2PMChHist15MRtxCW		       Counter32,
              vdsl2PMChHist15MRtxCorrectedCW	       Counter32,
              vdsl2PMChHist15MRtxUncorrectedCW         Counter32,
              vdsl2PMChHist15MStartTime                DateAndTime
            }
        
        vdsl2PMChHist15MUnit  OBJECT-TYPE
            SYNTAX      Vdsl2Unit
            MAX-ACCESS  not-accessible
            STATUS      current
            DESCRIPTION
                "The termination unit."
            ::= { vdsl2PMChHist15MinEntry 1 }
        
        vdsl2PMChHist15MInterval  OBJECT-TYPE
            SYNTAX      Unsigned32
            MAX-ACCESS  not-accessible
            STATUS      current
            DESCRIPTION
                "The interval number."
            ::= { vdsl2PMChHist15MinEntry 2 }
        
        vdsl2PMChHist15MMonitoredTime  OBJECT-TYPE
            SYNTAX      Unsigned32
            UNITS       "seconds"
            MAX-ACCESS  read-only
            STATUS      current
            DESCRIPTION
                "Total seconds monitored in this interval.
                 Unit: seconds
                "
            ::= { vdsl2PMChHist15MinEntry 3 }
        
        vdsl2PMChHist15MCodingViolations  OBJECT-TYPE
            SYNTAX      Unsigned32
            MAX-ACCESS  read-only
            STATUS      current
            DESCRIPTION
                "Count of CRC-8 (FEBE for xTU-R) anomalies occurring in the
                 channel during the interval.  This parameter is inhibited
                 during UAS or SES.  If the CRC is applied over multiple
                 channels, then each related CRC-8 (or FEBE) anomaly should
                 increment each of the counters related to the individual
                 channels.
                "
            REFERENCE    "ITU-T G.997.1, paragraph 7.2.2"
            ::= { vdsl2PMChHist15MinEntry 4 }
        
        vdsl2PMChHist15MCorrectedBlocks  OBJECT-TYPE
            SYNTAX      Unsigned32
            MAX-ACCESS  read-only
            STATUS      current
            DESCRIPTION
                "Count of FEC (FFEC for xTU-R) anomalies (corrected code words)
                 occurring in the channel during the interval.  This parameter
                 is inhibited during UAS or SES.  If the FEC is applied over
                 multiple channels, then each related FEC (or FFEC) anomaly
                 should increment each of the counters related to the
                 individual channels.
                "
            REFERENCE    "ITU-T G.997.1, paragraph 7.2.2"
            ::= { vdsl2PMChHist15MinEntry 5 }
        
        vdsl2PMChHist15MValidInterval  OBJECT-TYPE
            SYNTAX      TruthValue
            MAX-ACCESS  read-only
            STATUS      current
            DESCRIPTION
                "This variable indicates if the data for this interval is
                 valid.
                "
            ::= { vdsl2PMChHist15MinEntry 6 }
        
        vdsl2PMChHist15MEncodedBlocks  OBJECT-TYPE
            SYNTAX      Unsigned32
            MAX-ACCESS  read-only
            STATUS      current
            DESCRIPTION
                "Count of all encoded blocks received on this
                 channel during the interval.
                "
            ::= { vdsl2PMChHist15MinEntry 7 }
        
        vdsl2PMChHist15MUncorrectableBlocks  OBJECT-TYPE
            SYNTAX      Unsigned32
            MAX-ACCESS  read-only
            STATUS      current
            DESCRIPTION
                "Count of all blocks received with uncorrectable
                 errors on this channel during the interval.
                "
            ::= { vdsl2PMChHist15MinEntry 8 }
        
        vdsl2PMChHist15MAtmCells  OBJECT-TYPE
            SYNTAX      Counter32
            MAX-ACCESS  read-only
            STATUS      current
            DESCRIPTION
                "Count of Atm Cells received
                 on this channel during the interval.
                "
            ::= { vdsl2PMChHist15MinEntry 9 }
        
        vdsl2PMChHist15MPtmPackets  OBJECT-TYPE
            SYNTAX      Counter32
            MAX-ACCESS  read-only
            STATUS      current
            DESCRIPTION
                "Count of Ptm Packets received
                 on this channel during the interval.
                "
            ::= { vdsl2PMChHist15MinEntry 10 }
        
        vdsl2PMChHist15MRtxCW  OBJECT-TYPE
            SYNTAX      Counter32
            MAX-ACCESS  read-only
            STATUS      current
            DESCRIPTION
                "Count of units request retransmission during the 
                 serval 15 minute interval of history.
                "
            ::= { vdsl2PMChHist15MinEntry 11 }
           
        vdsl2PMChHist15MRtxCorrectedCW  OBJECT-TYPE
            SYNTAX      Counter32
            MAX-ACCESS  read-only
            STATUS      current
            DESCRIPTION
                "Count of units corrected by retransmission during the 
                 serval 15 minute interval of history.
                "
            ::= { vdsl2PMChHist15MinEntry 12 }
        
        vdsl2PMChHist15MRtxUncorrectedCW  OBJECT-TYPE
            SYNTAX      Counter32
            MAX-ACCESS  read-only
            STATUS      current
            DESCRIPTION
                "Count of units uncorrected by retransmission during 
                 the serval 15 minute interval of history.
                "
            ::= { vdsl2PMChHist15MinEntry 13 }       
           
        vdsl2PMChHist15MStartTime  OBJECT-TYPE
            SYNTAX      DateAndTime
            MAX-ACCESS  read-only
            STATUS      current
            DESCRIPTION
                "Start time of the channel historical 15-minute performance 
                 statistics.
                "
            ::= { vdsl2PMChHist15MinEntry 14 } 
        
          --        PM channel history 1 Day      
        vdsl2PMChHist1DTable         OBJECT-TYPE
            SYNTAX      SEQUENCE  OF  Vdsl2PMChHist1DEntry
            MAX-ACCESS  not-accessible
            STATUS      current
            DESCRIPTION
                "The table vdsl2PMChHist1DTable contains PM channel history
                 for 1 day intervals of VDSL2. The indexes of this table are
                 an interface index where
                 the interface has an ifType value which is applicable
                 for a DSL channel, the termination unit and the
                 interval number.
                "
            ::= { vdsl2PMChannel 3 }
        
        vdsl2PMChHist1DEntry  OBJECT-TYPE
            SYNTAX      Vdsl2PMChHist1DEntry
            MAX-ACCESS  not-accessible
            STATUS      current
            DESCRIPTION
                "The table vdsl2PMChHist1DTable contains PM channel history
                 for 1 day intervals of VDSL2.
                 The indexes of this entry are an interface index where
                 the interface has an ifType value which is applicable
                 for a DSL channel, the termination unit and the
                 interval number.
                "            
            INDEX  { ifIndex,
                     vdsl2PMChHist1DUnit,
                     vdsl2PMChHist1DInterval }
            ::= { vdsl2PMChHist1DTable 1 }
        
        Vdsl2PMChHist1DEntry  ::=
            SEQUENCE {
               vdsl2PMChHist1DUnit                      Vdsl2Unit,
               vdsl2PMChHist1DInterval                  Unsigned32,
               vdsl2PMChHist1DMonitoredTime             Unsigned32,
               vdsl2PMChHist1DCodingViolations          Unsigned32,
               vdsl2PMChHist1DCorrectedBlocks           Unsigned32,
               vdsl2PMChHist1DValidInterval             TruthValue,
               vdsl2PMChHist1DEncodedBlocks             Unsigned32,
               vdsl2PMChHist1DUncorrectableBlocks       Unsigned32,
               vdsl2PMChHist1DAtmCells                  Counter32,
               vdsl2PMChHist1DPtmPackets                Counter32,
               vdsl2PMChHist1DRtxCW		 	Counter32,
               vdsl2PMChHist1DRtxCorrectedCW  	        Counter32,
               vdsl2PMChHist1DRtxUncorrectedCW	        Counter32,
               vdsl2PMChHist1DStartTime                 DateAndTime
            }
        
        vdsl2PMChHist1DUnit  OBJECT-TYPE
            SYNTAX      Vdsl2Unit
            MAX-ACCESS  not-accessible
            STATUS      current
            DESCRIPTION
                "The termination unit."
             ::= { vdsl2PMChHist1DEntry 1 }
        
        vdsl2PMChHist1DInterval  OBJECT-TYPE
            SYNTAX      Unsigned32
            MAX-ACCESS  not-accessible
            STATUS      current
            DESCRIPTION
                "The interval number."
            ::= { vdsl2PMChHist1DEntry 2 }
        
        vdsl2PMChHist1DMonitoredTime  OBJECT-TYPE
            SYNTAX      Unsigned32
            UNITS       "seconds"
            MAX-ACCESS  read-only
            STATUS      current
            DESCRIPTION
                "Total seconds monitored in this interval.
                 Unit: seconds
                "
            ::= { vdsl2PMChHist1DEntry 3 }
        
        vdsl2PMChHist1DCodingViolations  OBJECT-TYPE
            SYNTAX      Unsigned32
            MAX-ACCESS  read-only
            STATUS      current
            DESCRIPTION
                "Count of CRC-8 (FEBE for xTU-R) anomalies occurring in the
                 channel during the interval.  This parameter is inhibited
                 during UAS or SES.  If the CRC is applied over multiple
                 channels, then each related CRC-8 (or FEBE) anomaly should
                 increment each of the counters related to the individual
                 channels.
                "
            REFERENCE    "ITU-T G.997.1, paragraph 7.2.2"
            ::= { vdsl2PMChHist1DEntry 4 }
        
        vdsl2PMChHist1DCorrectedBlocks  OBJECT-TYPE
            SYNTAX      Unsigned32
            MAX-ACCESS  read-only
            STATUS      current
            DESCRIPTION
                "Count of FEC (FFEC for xTU-R) anomalies (corrected code words)
                 occurring in the channel during the interval.  This parameter
                 is inhibited during UAS or SES.  If the FEC is applied over
                 multiple channels, then each related FEC (or FFEC) anomaly
                 should increment each of the counters related to the
                 individual channels.
                "
            REFERENCE    "ITU-T G.997.1, paragraph 7.2.2"
            ::= { vdsl2PMChHist1DEntry 5 }
        
        vdsl2PMChHist1DValidInterval  OBJECT-TYPE
            SYNTAX      TruthValue
            MAX-ACCESS  read-only
            STATUS      current
            DESCRIPTION
                "This variable indicates if the data for this interval is
                 valid.
                "
            ::= { vdsl2PMChHist1DEntry 6 }
        
        vdsl2PMChHist1DEncodedBlocks  OBJECT-TYPE
            SYNTAX      Unsigned32
            MAX-ACCESS  read-only
            STATUS      current
            DESCRIPTION
                "Count of all encoded blocks received on this
                 channel during the interval.
                "
            ::= { vdsl2PMChHist1DEntry 7 }
        
        vdsl2PMChHist1DUncorrectableBlocks  OBJECT-TYPE
            SYNTAX      Unsigned32
            MAX-ACCESS  read-only
            STATUS      current
            DESCRIPTION
                "Count of all blocks received with uncorrectable
                 errors on this channel during the interval."
            ::= { vdsl2PMChHist1DEntry 8 }
              
        vdsl2PMChHist1DAtmCells  OBJECT-TYPE
            SYNTAX      Counter32
            MAX-ACCESS  read-only
            STATUS      current
            DESCRIPTION
                "Count of Atm Cells received
                 on this channel during the interval.
                "
            ::= { vdsl2PMChHist1DEntry 9 }
           
        vdsl2PMChHist1DPtmPackets  OBJECT-TYPE
            SYNTAX      Counter32
            MAX-ACCESS  read-only
            STATUS      current
            DESCRIPTION
                "Count of Ptm Packets received
                 on this channel during the interval.
                "
            ::= { vdsl2PMChHist1DEntry 10 }
           
        vdsl2PMChHist1DRtxCW  OBJECT-TYPE
            SYNTAX      Counter32
            MAX-ACCESS  read-only
            STATUS      current
            DESCRIPTION
                "Count of units request retransmission within the 
                 serval one day interval of history.
                "
            ::= { vdsl2PMChHist1DEntry 11 }
           
        vdsl2PMChHist1DRtxCorrectedCW  OBJECT-TYPE
            SYNTAX      Counter32
            MAX-ACCESS  read-only
            STATUS      current
            DESCRIPTION
                "Count of units corrected by retransmission during the 
                 serval one day interval of history.
                "
            ::= { vdsl2PMChHist1DEntry 12 }
        
        vdsl2PMChHist1DRtxUncorrectedCW  OBJECT-TYPE
            SYNTAX      Counter32
            MAX-ACCESS  read-only
            STATUS      current
            DESCRIPTION
                "Count of units uncorrected by retransmission during 
                 the serval one day interval of history.
                "
            ::= { vdsl2PMChHist1DEntry 13 }       
           
        vdsl2PMChHist1DStartTime  OBJECT-TYPE
            SYNTAX      DateAndTime
            MAX-ACCESS  read-only
            STATUS      current
            DESCRIPTION
                "Start time of the channel historical 1-day performance statistics."
            ::= { vdsl2PMChHist1DEntry 14 }       
          --          PM channel chipset statistics        
        vdsl2PMChChipStatTable        OBJECT-TYPE
            SYNTAX      SEQUENCE  OF  Vdsl2PMChChipStatEntry
            MAX-ACCESS  not-accessible
            STATUS      current
            DESCRIPTION
                "The table vdsl2PMChChipStatTable contains packets and CRC errors on chipset of 
                 upstream and downstream of VDSL2 channel. 
                 The indexes of this table are an interface index where
                 the interface has an ifType value which is applicable
                 for a DSL channel and the termination unit.
                "
            ::= { vdsl2PMChannel 4 }
        
        vdsl2PMChChipStatEntry  OBJECT-TYPE
            SYNTAX      Vdsl2PMChChipStatEntry
            MAX-ACCESS  not-accessible
            STATUS      current
            DESCRIPTION
                "The table vdsl2PMChChipStatTable contains packets and CRC errors on chipset of 
                 upstream and downstream of VDSL2 channel. 
                 The indexes of this entry are an interface index where
                 the interface has an ifType value which is applicable
                 for a DSL channel and the termination unit.
                "
            INDEX  { ifIndex, vdsl2PMChChipstatUnit }
            ::= { vdsl2PMChChipStatTable 1 }
        
        Vdsl2PMChChipStatEntry  ::=
            SEQUENCE {
               vdsl2PMChChipstatUnit                 Vdsl2Unit,
               vdsl2PMChPktsDs                       Unsigned32,
               vdsl2PMChPktsUs                       Unsigned32,
               vdsl2PMChCrcErrsDs                    Unsigned32,
               vdsl2PMChCrcErrsUs                    Unsigned32, 
               vdsl2PMChStatAdminStatus              INTEGER
          
            }
                  
        vdsl2PMChChipstatUnit  OBJECT-TYPE
            SYNTAX      Vdsl2Unit
            MAX-ACCESS  not-accessible
            STATUS      current
            DESCRIPTION
                "The termination unit."
            ::= { vdsl2PMChChipStatEntry 1 }
           
        vdsl2PMChPktsDs  OBJECT-TYPE
            SYNTAX      Unsigned32         
            MAX-ACCESS  read-only          
            STATUS      current            
            DESCRIPTION                    
                "The number of downstream packets."      
             ::= { vdsl2PMChChipStatEntry 2 } 
            
        vdsl2PMChPktsUs  OBJECT-TYPE
            SYNTAX      Unsigned32
            MAX-ACCESS  read-only
            STATUS      current
            DESCRIPTION
                "The number of upstream packets."
            ::= { vdsl2PMChChipStatEntry 3 }
        
        vdsl2PMChCrcErrsDs  OBJECT-TYPE
            SYNTAX      Unsigned32
            MAX-ACCESS  read-only
            STATUS      current
            DESCRIPTION
                "The number of downstream CRC errors."
             ::= { vdsl2PMChChipStatEntry 4 }
        
        vdsl2PMChCrcErrsUs  OBJECT-TYPE
            SYNTAX      Unsigned32
            MAX-ACCESS  read-only
            STATUS      current
            DESCRIPTION
                "The number of upstream CRC errors."
            ::= { vdsl2PMChChipStatEntry 5 }
            
        vdsl2PMChStatAdminStatus OBJECT-TYPE
            SYNTAX  INTEGER {
                        reset(1)       
                     }
            MAX-ACCESS  read-write
            STATUS  current
            DESCRIPTION
                "Clear the number of packets transmitted and received,
                 CRC errors upstream and downstream.
                 Options: 
                 1. reset(1)       - reset statistic data
                "
            ::= { vdsl2PMChChipStatEntry 6 }
        
          --          Notifications Group          
        
        vdsl2LinePerfFECSThreshXtuc NOTIFICATION-TYPE
            OBJECTS
            {
            vdsl2PMLCurr15MFecs,
            vdsl2LineAlarmConfProfileXtucThresh15MinFecs
            }
            STATUS     current
            DESCRIPTION
                "This notification indicates that the FEC seconds threshold
                 has been reached/exceeded for the referred xTU-C.
                "
            ::= { vdsl2Notifications 1 }
        
        vdsl2LinePerfFECSThreshXtur NOTIFICATION-TYPE
            OBJECTS
            {
            vdsl2PMLCurr15MFecs,
            vdsl2LineAlarmConfProfileXturThresh15MinFecs
            }
            STATUS     current
            DESCRIPTION
                "This notification indicates that the FEC seconds threshold
                 has been reached/exceeded for the referred xTU-R.
                "
            ::= { vdsl2Notifications 2 }
        
        vdsl2LinePerfESThreshXtuc NOTIFICATION-TYPE
            OBJECTS
            {
            vdsl2PMLCurr15MEs,
            vdsl2LineAlarmConfProfileXtucThresh15MinEs
            }
            STATUS     current
            DESCRIPTION
                "This notification indicates that the errored seconds threshold
                 has been reached/exceeded for the referred xTU-C.
                "
            ::= { vdsl2Notifications 3 }
        
        vdsl2LinePerfESThreshXtur NOTIFICATION-TYPE
            OBJECTS
            {
            vdsl2PMLCurr15MEs,
            vdsl2LineAlarmConfProfileXturThresh15MinEs
            }
            STATUS     current
            DESCRIPTION
                "This notification indicates that the errored seconds threshold
                 has been reached/exceeded for the referred xTU-R.
                "
            ::= { vdsl2Notifications 4 }
        
        vdsl2LinePerfSESThreshXtuc NOTIFICATION-TYPE
            OBJECTS
            {
            vdsl2PMLCurr15MSes,
            vdsl2LineAlarmConfProfileXtucThresh15MinSes
            }
            STATUS     current
            DESCRIPTION
                "This notification indicates that the severely-errored seconds
                 threshold has been reached/exceeded for the referred xTU-C.
                "
            ::= { vdsl2Notifications 5 }
        
        vdsl2LinePerfSESThreshXtur NOTIFICATION-TYPE
            OBJECTS
            {
            vdsl2PMLCurr15MSes,
            vdsl2LineAlarmConfProfileXturThresh15MinSes
            }
            STATUS     current
            DESCRIPTION
                "This notification indicates that the severely-errored seconds
                 threshold has been reached/exceeded for the referred xTU-R.
                "
            ::= { vdsl2Notifications 6 }
        
        vdsl2LinePerfLOSSThreshXtuc NOTIFICATION-TYPE
            OBJECTS
            {
            vdsl2PMLCurr15MLoss,
            vdsl2LineAlarmConfProfileXtucThresh15MinLoss
            }
            STATUS     current
            DESCRIPTION
                "This notification indicates that the LOS seconds
                 threshold has been reached/exceeded for the referred xTU-C.
                "
            ::= { vdsl2Notifications 7 }
        
        vdsl2LinePerfLOSSThreshXtur NOTIFICATION-TYPE
            OBJECTS
            {
            vdsl2PMLCurr15MLoss,
            vdsl2LineAlarmConfProfileXturThresh15MinLoss
            }
            STATUS     current
            DESCRIPTION
                "This notification indicates that the LOS seconds
                 threshold has been reached/exceeded for the referred xTU-R.
                "
            ::= { vdsl2Notifications 8 }
        
        vdsl2LinePerfUASThreshXtuc NOTIFICATION-TYPE
            OBJECTS
            {
            vdsl2PMLCurr15MUas,
            vdsl2LineAlarmConfProfileXtucThresh15MinUas
            }
            STATUS     current
            DESCRIPTION
                "This notification indicates that the unavailable seconds
                 threshold has been reached/exceeded for the referred xTU-C.
                "
            ::= { vdsl2Notifications 9 }
        
        vdsl2LinePerfUASThreshXtur NOTIFICATION-TYPE
            OBJECTS
            {
            vdsl2PMLCurr15MUas,
            vdsl2LineAlarmConfProfileXturThresh15MinUas
            }
            STATUS     current
            DESCRIPTION
                "This notification indicates that the unavailable seconds
                 threshold has been reached/exceeded for the referred xTU-R.
                "
            ::= { vdsl2Notifications 10 }
        
        vdsl2LinePerfCodingViolationsThreshXtuc NOTIFICATION-TYPE
            OBJECTS
            {
            vdsl2PMChCurr15MCodingViolations,
            vdsl2ChAlarmConfProfileXtucThresh15MinCodingViolations
            }
            STATUS     current
            DESCRIPTION
                "This notification indicates that the coding violations
                 threshold has been reached/exceeded for the referred xTU-C.
                "
            ::= { vdsl2Notifications 11 }
        
        vdsl2LinePerfCodingViolationsThreshXtur NOTIFICATION-TYPE
            OBJECTS
            {
            vdsl2PMChCurr15MCodingViolations,
            vdsl2ChAlarmConfProfileXturThresh15MinCodingViolations
            }
            STATUS     current
            DESCRIPTION
                "This notification indicates that the coding violations
                 threshold has been reached/exceeded for the referred xTU-R.
                "
            ::= { vdsl2Notifications 12 }
        
        vdsl2LinePerfCorrectedThreshXtuc NOTIFICATION-TYPE
            OBJECTS
            {
            vdsl2PMChCurr15MCorrectedBlocks,
            vdsl2ChAlarmConfProfileXtucThresh15MinCorrected
            }
            STATUS     current
            DESCRIPTION
                "This notification indicates that the corrected blocks
                 (FEC events) threshold has been reached/exceeded for the
                 referred xTU-C.
                "
            ::= { vdsl2Notifications 13 }
        
        vdsl2LinePerfCorrectedThreshXtur NOTIFICATION-TYPE
            OBJECTS
            {
            vdsl2PMChCurr15MCorrectedBlocks,
            vdsl2ChAlarmConfProfileXturThresh15MinCorrected
            }
            STATUS     current
            DESCRIPTION
                "This notification indicates that the corrected blocks
                 (FEC events) threshold has been reached/exceeded for the
                 referred xTU-R.
                "
            ::= { vdsl2Notifications 14 }
        
        vdsl2LinePerfFailedFullInitThresh NOTIFICATION-TYPE
            OBJECTS
            {
            vdsl2PMLCurrInit15MFailedFullInits,
            vdsl2LineAlarmConfProfileThresh15MinFailedFullInt
            }
            STATUS     current
            DESCRIPTION
                "This notification indicates that the failed full
                 initializations threshold has been reached/exceeded for the
                 referred VDSL/VDSL2 or VDSL2 line.
                "
            ::= { vdsl2Notifications 15 }
        
        vdsl2LinePerfFailedShortInitThresh NOTIFICATION-TYPE
            OBJECTS
            {
            vdsl2PMLCurrInit15MFailedShortInits,
            vdsl2LineAlarmConfProfileThresh15MinFailedShrtInt
            }
            STATUS     current
            DESCRIPTION
                "This notification indicates that the failed short
                 initializations threshold has been reached/exceeded for the
                 referred VDSL or VDSL2 line.
                "
            ::= { vdsl2Notifications 16 }
        
        vdsl2LineStatusChangeXtuc NOTIFICATION-TYPE
            OBJECTS
            {
            vdsl2LineStatusXtuc
            }
            STATUS     current
            DESCRIPTION
                "This notification indicates that a status change is
                 detected for the referred xTU-C.
                "
            ::= { vdsl2Notifications 17 }
            
        vdsl2LineStatusChangeXtur NOTIFICATION-TYPE
            OBJECTS
            {
            vdsl2LineStatusXtur
            }
            STATUS     current
            DESCRIPTION
                "This notification indicates that a status change is
                 detected for the referred xTU-R.
                "
            ::= { vdsl2Notifications 18 }
            
              
        vdsl2LinePerfFullInitThresh NOTIFICATION-TYPE
            OBJECTS
            {
            vdsl2PMLCurrInit15MFullInits,
            vdsl2LineAlarmConfProfileThresh15MinFullInt
            }
            STATUS     current
            DESCRIPTION
                "This notification indicates that the full
                 initializations threshold has been reached/exceeded for the
                 referred VDSL/VDSL2 or VDSL2 line.
                "
            ::= { vdsl2Notifications 19 }
            
            -- conformance information
            
            vdsl2Groups OBJECT IDENTIFIER ::= { vdsl2Conformance 1 }
            vdsl2Compliances OBJECT IDENTIFIER ::= { vdsl2Conformance 2 }
        
        vdsl2LineMibCompliance MODULE-COMPLIANCE
            STATUS  current
            DESCRIPTION
                "The compliance statement for SNMP entities which
                 manage VDSL2 interfaces.
                "
            MODULE  -- this module
            MANDATORY-GROUPS
                {
                vdsl2LineGroup,
                vdsl2ChannelStatusGroup,
                vdsl2PrivSCStatusGroup, 
                vdsl2DeltGroup, 
                vdsl2LineInventoryGroup,
                vdsl2LineConfTemplateGroup,
                vdsl2LineConfProfGroup,
                vdsl2LineConfProfModeSpecGroup,
                vdsl2ChConfProfileGroup,
                vdsl2LineAlarmConfTemplateGroup,
                vdsl2PMLineCurrGroup,
                vdsl2PMLineCurrInitGroup,
                vdsl2PMLineHist15MinGroup,
                vdsl2PMLineHist1DayGroup,
                vdsl2PMLineInitHist15MinGroup,
                vdsl2PMLineInitHist1DayGroup,
                vdsl2PMChCurrGroup,
                vdsl2PMChHist15MinGroup,
                vdsl2PMChHist1DGroup
                }
        
        GROUP  vdsl2ChannelStatusAtmGroup
            DESCRIPTION
                "The group of status objects required when the data path
              is ATM."
         
        GROUP  vdsl2ChannelStatusPtmGroup
            DESCRIPTION
                "The group of status objects required when the data path
               is PTM."
         
        GROUP  vdsl2LineConfProfRaGroup
            DESCRIPTION
                "The group of objects required for controlling the rate
               adaptive behavior of the line."
         
        GROUP  vdsl2LineConfProfMsgMinGroup
            DESCRIPTION
                "The group of objects required for controlling the rate
               reserved for Overhead traffic."
         
        GROUP  vdsl2LineAlarmConfProfileGroup
            DESCRIPTION
                "The group of objects that define the alarm thresholds
               on line level PM counters."
         
        GROUP  vdsl2ChAlarmConfProfileGroup
            DESCRIPTION
                "The group of objects that define the alarm thresholds
               on channel level PM counters."
         
        GROUP  vdsl2ChConfProfileAtmGroup
            DESCRIPTION
                "The group of configuration objects required when the data
               path is ATM."
         
        GROUP  vdsl2ChConfProfileMinResGroup
            DESCRIPTION
                "The group of configuration objects required for the
               reserved data rate."
         
        GROUP  vdsl2PMLineCurrInitShortGroup
            DESCRIPTION
                "The group of PM counters for the current intervals
               short initializations."
         
        GROUP  vdsl2PMLineInitHist15MinShortGroup
            DESCRIPTION
                "The group of PM counters for the previous 15 minutes
               intervals short initializations."
         
        GROUP  vdsl2PMLineInitHist1DayShortGroup
            DESCRIPTION
                "The group of PM counters for the previous 24 hours
               intervals short initializations."
         
        GROUP  vdsl2ScalarDeltGroup
            DESCRIPTION
                "The group of objects that report the available memory
               resources for DELT processes."     
             
        GROUP  vdsl2ThreshNotificationGroup
            DESCRIPTION
                "The group of thresholds crossing notifications."
         
        GROUP  vdsl2StatusChangeNotificationGroup
            DESCRIPTION
               "The group of status change notifications."
            
            ::= { vdsl2Compliances 1 }            
    
        vdsl2LineGroup OBJECT-GROUP
            OBJECTS
                {
                vdsl2LineCnfgTemplate,
                vdsl2LineAlarmCnfgTemplate,
                vdsl2LineCmndConfPmsf,
                vdsl2LineCmndConfLdsf,
                vdsl2LineCmndConfLdsfFailReason,
                vdsl2LineCmndAutomodeColdStart,
                vdsl2LineStatusXtuTransSys,
                vdsl2LineStatusPwrMngState,
                vdsl2LineStatusInitResult,
                vdsl2LineStatusLastStateDs,
                vdsl2LineStatusLastStateUs,
                vdsl2LineStatusXtur,
                vdsl2LineStatusXtuc,
                vdsl2LineStatusLnAttenDs,
                vdsl2LineStatusLnAttenUs,
                vdsl2LineStatusSigAttenDs,
                vdsl2LineStatusSigAttenUs,
                vdsl2LineStatusSnrMarginDs,
                vdsl2LineStatusSnrMarginUs,
                vdsl2LineStatusAttainableRateDs,
                vdsl2LineStatusAttainableRateUs,
                vdsl2LineStatusActPsdDs,
                vdsl2LineStatusActPsdUs,
                vdsl2LineStatusActAtpDs,
                vdsl2LineStatusActAtpUs,
                vdsl2LineBandPlan,
                vdsl2LinePsdClassMaskSelection,
                vdsl2LineCnfgServiceProf,
                vdsl2LineCnfgSpectrumProf,
                vdsl2LineCnfgDpboProf,
                vdsl2LineCnfgUpboProf,
                vdsl2LineCnfgNoiseMarginProf,
                vdsl2LineCnfgDelayINPProf,
                vdsl2UpboProfKl0CpeVal,
                vdsl2LineStatusCodingGainUs,
                vdsl2LineStatusCodingGainDs,
                vdsl2LineStatusPcbDs,
                hwvdslDlmDsmprofile,
                hwvdsl2LineActmode,
                vdsl2UpboProfKl0CoVal,
                vdsl2UpboRxThreshDs,
                vdsl2UpboRxThreshUs,
                hwvdsl2LineStatusLineRateDs,
                hwvdsl2LineStatusLineRateUs,
                hwvdsl2LineSplitterMode,
                hwvdsl2LineBackup,
                hwvdsl2LineBackupPort
                }
            STATUS     current
            DESCRIPTION
                "The group of configuration, status, and commands objects
                 on the line level.
                "
            ::= { vdsl2Groups 1 }
        
        vdsl2ChannelStatusGroup OBJECT-GROUP
            OBJECTS
                {
                vdsl2ChStatusChannelNum,
                vdsl2ChStatusActDataRate,
                vdsl2ChStatusPrevDataRate,
                vdsl2ChStatusActDelay
                }
            STATUS     current
            DESCRIPTION
                "The group of status objects on the channel level."
            ::= { vdsl2Groups 2 }
        
        vdsl2ChannelStatusAtmGroup OBJECT-GROUP
            OBJECTS
                {
                vdsl2ChStatusAtmStatus
                }
            STATUS     current
            DESCRIPTION
                "The group of status objects on the data path level
                 when it is ATM."
            ::= { vdsl2Groups 3 }
        
        vdsl2ChannelStatusPtmGroup OBJECT-GROUP
            OBJECTS
                {
                vdsl2ChStatusPtmStatus
                }
            STATUS     current
            DESCRIPTION
                "The group of status objects on the data path level
                 when it is PTM."
            ::= { vdsl2Groups 4 }
        
        vdsl2PrivSCStatusGroup OBJECT-GROUP         
            OBJECTS
                {
                vdsl2PrivSCStatusMtime,
                vdsl2PrivSCStatusSnr,
                vdsl2PrivSCStatusBitsAlloc,
                vdsl2PrivSCStatusGainAlloc
                }
            STATUS     current
            DESCRIPTION
                "The group of status objects on the sub-carrier level.
                 They are updated as a result of a DELT process."
            ::= { vdsl2Groups 5 }  
           
        vdsl2DeltGroup OBJECT-GROUP
            OBJECTS
                {
                vdsl2SCStatusLinScale,
                vdsl2SCStatusLogMt,
                vdsl2SCStatusQlnMt,
                vdsl2SCStatusAttainableRate,
                vdsl2SCStatusActAtp,
                vdsl2SCStatusRowStatus
                }
            STATUS     current
            DESCRIPTION
                "The group of status objects on the sub-carrier level.
                 They are updated as a result of a DELT process."
            ::= { vdsl2Groups 6 }
        vdsl2LineInventoryGroup OBJECT-GROUP
            OBJECTS
                {
                vdsl2LInvG994VendorId,
                vdsl2LInvSystemVendorId,
                vdsl2LInvVersionNumber,
                vdsl2LInvSerialNumber,
                vdsl2LInvSelfTestResult,
                vdsl2LInvTransmissionCapabilities,
                vdsl2LInvModelId
                }
            STATUS     current
            DESCRIPTION
                "The group of inventory objects per xTU."
            ::= { vdsl2Groups 7 }
        
        vdsl2LineConfTemplateGroup OBJECT-GROUP
            OBJECTS
                {
                vdsl2LConfTempLineProfile,
                vdsl2LConfTempChan1ConfProfile,
                vdsl2LConfTempChan1RaRatioDs,
                vdsl2LConfTempChan1RaRatioUs,
                vdsl2LConfTempChan2ConfProfile,
                vdsl2LConfTempChan2RaRatioDs,
                vdsl2LConfTempChan2RaRatioUs,
                vdsl2LConfTempChan3ConfProfile,
                vdsl2LConfTempChan3RaRatioDs,
                vdsl2LConfTempChan3RaRatioUs,
                vdsl2LConfTempChan4ConfProfile,
                vdsl2LConfTempChan4RaRatioDs,
                vdsl2LConfTempChan4RaRatioUs,
                vdsl2LConfTempRowStatus
                }
            STATUS     current
            DESCRIPTION
                "The group of objects in a line configuration template."
            ::= { vdsl2Groups 8 }
        
        vdsl2LineConfProfGroup OBJECT-GROUP
            OBJECTS
                {
                vdsl2LConfProfScMaskDs,
                vdsl2LConfProfScMaskUs,
                vdsl2LConfProfRfiBands,
                vdsl2LConfProfVDSLtoneblackout,
                vdsl2LConfProfRaModeDs,
                vdsl2LConfProfRaModeUs,
                vdsl2LConfProfTargetSnrmDs,
                vdsl2LConfProfTargetSnrmUs,
                vdsl2LConfProfMaxSnrmDs,
                vdsl2LConfProfMaxSnrmUs,
                vdsl2LConfProfMinSnrmDs,
                vdsl2LConfProfMinSnrmUs,
                vdsl2LConfProfXtuTransSysEna,
                vdsl2LConfProfPmMode,
                vdsl2LConfProfL0Time,
                vdsl2LConfProfL2Time,
                vdsl2LConfProfL2Atpr,
                vdsl2LConfProfL2Atprt,
                vdsl2LConfProfDpboEpsd,         
                vdsl2LConfProfDpboEsel,         
                vdsl2LConfProfDpboEscm,         
                vdsl2LConfProfDpboMus,		
                vdsl2LConfProfDpboFmin,	        
                vdsl2LConfProfDpboFmax,		
                vdsl2LConfProfUpboPsdBand,      
                vdsl2LConfProfUpboKl,		
                vdsl2LConfProfUpboKlf,
                vdsl2LConfProfBitSwapDs,
                vdsl2LConfProfBitSwapUs,
                vdsl2LConfProfRowStatus
                }
            STATUS     current
            DESCRIPTION
                "The group of objects in a line configuration profile."
            ::= { vdsl2Groups 9 }
        
        vdsl2LineConfProfRaGroup OBJECT-GROUP
            OBJECTS
                {
                vdsl2LConfProfRaUsNrmDs,
                vdsl2LConfProfRaUsNrmUs,
                vdsl2LConfProfRaUsTimeDs,
                vdsl2LConfProfRaUsTimeUs,
                vdsl2LConfProfRaDsNrmsDs,
                vdsl2LConfProfRaDsNrmsUs,
                vdsl2LConfProfRaDsTimeDs,
                vdsl2LConfProfRaDsTimeUs
                }
            STATUS     current
            DESCRIPTION
              "The group of objects required for controlling the rate
               adaptive behavior of the line."
            ::= { vdsl2Groups 10 }
        
        vdsl2LineConfProfMsgMinGroup OBJECT-GROUP
            OBJECTS
                {
                vdsl2LConfProfMsgMinUs,
                vdsl2LConfProfMsgMinDs
                }
            STATUS     current
            DESCRIPTION
                "The group of objects required for controlling the rate
                 reserved for Overhead traffic.
                "
            ::= { vdsl2Groups 11 }
        
        vdsl2LineConfProfModeSpecGroup OBJECT-GROUP
            OBJECTS
                {
                vdsl2LConfProfMaxNomPsdDs,
                vdsl2LConfProfMaxNomPsdUs,
                vdsl2LConfProfMaxNomAtpDs,
                vdsl2LConfProfMaxNomAtpUs,
                vdsl2LConfProfMaxAggRxPwrUs,
                vdsl2LConfProfPsdMaskDs,
                vdsl2LConfProfPsdMaskUs,
                vdsl2LConfProfPsdMaskSelectUs,
                vdsl2LConfProfModeSpecRowStatus,
                hwVdsl2ConfProfVirtualNoiseModeDs,
                hwVdsl2ConfProfVirtualNoiseModeUs,
                hwVdsl2ConfProfVirtualNoiseDs,
                hwVdsl2ConfProfVirtualNoiseUs,
                hwVdsl2ConfProfAutoProfile
                }
            STATUS     current
            DESCRIPTION
                "The group of objects in a line configuration profile
                 that have an instance for each operation mode allowed.
                "
            ::= { vdsl2Groups 12 }
        
        vdsl2ChConfProfileGroup OBJECT-GROUP
            OBJECTS
                {
                vdsl2ChConfProfMinDataRateDs,
                vdsl2ChConfProfMinDataRateUs,
                vdsl2ChConfProfMaxDataRateDs,
                vdsl2ChConfProfMaxDataRateUs,
                vdsl2ChConfProfMinDataRateLowPwrDs,
                vdsl2ChConfProfMinDataRateLowPwrUs,
                vdsl2ChConfProfMaxDelayDs,
                vdsl2ChConfProfMaxDelayUs,
                vdsl2ChConfProfMinProtectionDs,
                vdsl2ChConfProfMinProtectionUs,
                vdsl2ChConfProfMaxBerDs,
                vdsl2ChConfProfMaxBerUs,
                vdsl2ChConfProfUsDataRateDs,
                vdsl2ChConfProfDsDataRateDs,
                vdsl2ChConfProfUsDataRateUs,
                vdsl2ChConfProfDsDataRateUs,
                vdsl2ChConfProfRowStatus,
                vdsl2ChConfProfPhyRcontrolDs,  
                vdsl2ChConfProfPhyRcontrolUs,  
                vdsl2ChConfProfInpMaxDs, 
                vdsl2ChConfProfInpMaxUs,       
                vdsl2ChConfProfMinRtxRatioDs,  
                vdsl2ChConfProfMinRtxRatioUs,  
                vdsl2ChConfProfMinRSoverheadDs,
                vdsl2ChConfProfMinRSoverheadUs,
                vdsl2ChConfProfErasureDecoding,
                vdsl2ChConfProfMinSosBrDs,
                vdsl2ChConfProfMinSosBrUs       ,
                vdsl2ChConfProfMinEtrRtxDs      , 
                vdsl2ChConfProfMinEtrRtxUs      , 
                vdsl2ChConfProfMaxEtrRtxDs      , 
                vdsl2ChConfProfMaxEtrRtxUs      , 
                vdsl2ChConfProfMaxNdrRtxDs      , 
                vdsl2ChConfProfMaxNdrRtxUs      , 
                vdsl2ChConfProfMaxDelayRtxDs    ,  
                vdsl2ChConfProfMaxDelayRtxUs    ,
                vdsl2ChConfProfMinDelayRtxDs    ,
                vdsl2ChConfProfMinDelayRtxUs    ,
                vdsl2ChConfProfMinInpShineRtxDs ,
                vdsl2ChConfProfMinInpShineRtxUs ,
                vdsl2ChConfProfMinInp8ShineRtxDs,
                vdsl2ChConfProfMinInp8ShineRtxUs,
                vdsl2ChConfProfShineRatioRtxDs  ,
                vdsl2ChConfProfShineRatioRtxUs  ,
                vdsl2ChConfProfMinInpReinRtxDs  ,
                vdsl2ChConfProfMinInpReinRtxUs  ,
                vdsl2ChConfProfMinInp8ReinRtxDs ,
                vdsl2ChConfProfMinInp8ReinRtxUs ,
                vdsl2ChConfProfIatReinRtxDs     ,
                vdsl2ChConfProfIatReinRtxUs                     
                }
            STATUS     current
            DESCRIPTION
                "The group of objects in a channel configuration profile."
            ::= { vdsl2Groups 13 }
        
        vdsl2ChConfProfileAtmGroup OBJECT-GROUP
            OBJECTS
                {
                vdsl2ChConfProfImaEnabled,
                vdsl2ChStatusAtmStatus
                }
            
            STATUS     current
            DESCRIPTION
                "The group of configuration objects required when the data
                 path is ATM.
                "
            ::= { vdsl2Groups 14 }
        
        vdsl2ChConfProfileMinResGroup OBJECT-GROUP
            OBJECTS
                {
                vdsl2ChConfProfMinResDataRateDs,
                vdsl2ChConfProfMinResDataRateUs
                }
            STATUS     current
            DESCRIPTION
                "The group of configuration objects required for the
                 reserved data rate.
                "
            ::= { vdsl2Groups 15 }
        
        vdsl2LineAlarmConfTemplateGroup OBJECT-GROUP
            OBJECTS
                {
                vdsl2LAlarmConfTempLineProfile,
                vdsl2LAlarmConfTempChan1ConfProfile,
                vdsl2LAlarmConfTempChan2ConfProfile,
                vdsl2LAlarmConfTempChan3ConfProfile,
                vdsl2LAlarmConfTempChan4ConfProfile,
                vdsl2LAlarmConfTempRowStatus
                }
            STATUS     current
            DESCRIPTION
                "The group of objects in a line alarm
                 template.
                "
            ::= { vdsl2Groups 16 }
        
        vdsl2LineAlarmConfProfileGroup OBJECT-GROUP
            OBJECTS
                {
                vdsl2LineAlarmConfProfileXtucThresh15MinFecs,
                vdsl2LineAlarmConfProfileXtucThresh15MinEs,
                vdsl2LineAlarmConfProfileXtucThresh15MinSes,
                vdsl2LineAlarmConfProfileXtucThresh15MinLoss,
                vdsl2LineAlarmConfProfileXtucThresh15MinUas,
                vdsl2LineAlarmConfProfileXturThresh15MinFecs,
                vdsl2LineAlarmConfProfileXturThresh15MinEs,
                vdsl2LineAlarmConfProfileXturThresh15MinSes,
                vdsl2LineAlarmConfProfileXturThresh15MinLoss,
                vdsl2LineAlarmConfProfileXturThresh15MinUas,
                vdsl2LineAlarmConfProfileThresh15MinFailedFullInt,
                vdsl2LineAlarmConfProfileThresh15MinFailedShrtInt,
                vdsl2LineAlarmConfProfileRowStatus,
                vdsl2LineAlarmConfProfileThresh15MinFullInt,                
                vdsl2LineAlarmConfProfileXtucThresh15MinLeftrs,
                vdsl2LineAlarmConfProfileXturThresh15MinLeftrs      
                }
            STATUS     current
            DESCRIPTION
                "The group of objects in a line alarm profile."
            ::= { vdsl2Groups 17 }
        
        vdsl2ChAlarmConfProfileGroup OBJECT-GROUP
            OBJECTS
                {
                vdsl2ChAlarmConfProfileXtucThresh15MinCodingViolations,
                vdsl2ChAlarmConfProfileXtucThresh15MinCorrected,
                vdsl2ChAlarmConfProfileXturThresh15MinCodingViolations,
                vdsl2ChAlarmConfProfileXturThresh15MinCorrected,
                vdsl2ChAlarmConfProfileMonitoringRateDs,
                vdsl2ChAlarmConfProfileMonitoringRateUs,
                vdsl2ChAlarmConfProfileRowStatus
                }
            STATUS     current
            DESCRIPTION
                "The group of objects in a channel alarm profile."
            ::= { vdsl2Groups 18 }
        
        vdsl2PMLineCurrGroup OBJECT-GROUP
            OBJECTS
                {
                vdsl2PMLCurrValidIntervals,
                vdsl2PMLCurrInvalidIntervals,
                vdsl2PMLCurr15MTimeElapsed,
                vdsl2PMLCurr15MFecs,
                vdsl2PMLCurr15MEs,
                vdsl2PMLCurr15MSes,
                vdsl2PMLCurr15MLoss,
                vdsl2PMLCurr15MUas,
                vdsl2PMLCurr1DayValidIntervals,
                vdsl2PMLCurr1DayInvalidIntervals,
                vdsl2PMLCurr1DayTimeElapsed,
                vdsl2PMLCurr1DayFecs,
                vdsl2PMLCurr1DayEs,
                vdsl2PMLCurr1DaySes,
                vdsl2PMLCurr1DayLoss,
                vdsl2PMLCurr1DayUas,
                vdsl2PMLEverBeforeFecs,
                vdsl2PMLEverBeforeEs,
                vdsl2PMLEverBeforeSes,
                vdsl2PMLEverBeforeLoss,
                vdsl2PMLEverBeforeUas
                }
            STATUS     current
            DESCRIPTION
                "The group of objects that report the line level
                 counters for current PM intervals.
                "
            ::= { vdsl2Groups 19 }
        
        vdsl2PMLineCurrInitGroup OBJECT-GROUP
            OBJECTS
                {
                vdsl2PMLCurrInit15MTimeElapsed,
                vdsl2PMLCurrInit15MFullInits,
                vdsl2PMLCurrInit15MFailedFullInits,
                vdsl2PMLCurrInit1DayTimeElapsed,
                vdsl2PMLCurrInit1DayFullInits,
                vdsl2PMLCurrInit1DayFailedFullInits,
                vdsl2PMLInitEverBeforeFullInits,     
                vdsl2PMLInitEverBeforeFailedFullInits
                }
            STATUS     current
            DESCRIPTION
                "The group of objects that report the full
                 initializations counters for current PM intervals.
                "
            ::= { vdsl2Groups 20 }
        
        vdsl2PMLineCurrInitShortGroup OBJECT-GROUP
            OBJECTS
                {
                vdsl2PMLCurrInit15MShortInits,
                vdsl2PMLCurrInit15MFailedShortInits,
                vdsl2PMLCurrInit1DayShortInits,
                vdsl2PMLCurrInit1DayFailedShortInits,
                vdsl2PMLInitEverBeforeShortInits,
                vdsl2PMLInitEverBeforeFailedShortInits
                }
            STATUS     current
            DESCRIPTION
                "The group of objects that report the short
                 initializations counters for current PM intervals.
                "
            ::= { vdsl2Groups 21 }
        
        vdsl2PMLineHist15MinGroup OBJECT-GROUP
            OBJECTS
                {
                vdsl2PMLHist15MMonitoredTime,
                vdsl2PMLHist15MFecs,
                vdsl2PMLHist15MEs,
                vdsl2PMLHist15MSes,
                vdsl2PMLHist15MLoss,
                vdsl2PMLHist15MUas,
                vdsl2PMLHist15MValidInterval
                }
            STATUS     current
            DESCRIPTION
                "The group of line level PM counters for the previous
                 15 minutes intervals.
                "
            ::= { vdsl2Groups 22 }
        
        vdsl2PMLineHist1DayGroup OBJECT-GROUP
            OBJECTS
                {
                vdsl2PMLHist1DMonitoredTime,
                vdsl2PMLHist1DFecs,
                vdsl2PMLHist1DEs,
                vdsl2PMLHist1DSes,
                vdsl2PMLHist1DLoss,
                vdsl2PMLHist1DUas,
                vdsl2PMLHist1DValidInterval
                }
            STATUS     current
            DESCRIPTION
                "The group of line level PM counters for the previous
                 24 hours intervals.
                "
            ::= { vdsl2Groups 23 }
        
        vdsl2PMLineInitHist15MinGroup OBJECT-GROUP
            OBJECTS
                {
                vdsl2PMLHistInit15MMonitoredTime,
                vdsl2PMLHistInit15MFullInits,
                vdsl2PMLHistInit15MFailedFullInits,
                vdsl2PMLHistInit15MValidInterval
                }
            STATUS     current
            DESCRIPTION
                "The group of PM counters for the previous 15 minutes
                 intervals full initializations.
                "
            ::= { vdsl2Groups 24 }
        
        vdsl2PMLineInitHist15MinShortGroup OBJECT-GROUP
            OBJECTS
                {
                vdsl2PMLHistInit15MShortInits,
                vdsl2PMLHistInit15MFailedShortInits
                }
            STATUS     current
            DESCRIPTION
                "The group of PM counters for the previous 15 minutes
                 intervals short initializations.
                "
            ::= { vdsl2Groups 25 }
        
        vdsl2PMLineInitHist1DayGroup OBJECT-GROUP
            OBJECTS
                {
                vdsl2PMLHistinit1DMonitoredTime,
                vdsl2PMLHistinit1DFullInits,
                vdsl2PMLHistinit1DFailedFullInits,
                vdsl2PMLHistinit1DValidInterval
                }
            STATUS     current
            DESCRIPTION
                "The group of PM counters for the previous 24 hours
                 intervals full initializations.
                "
            ::= { vdsl2Groups 26 }
        
        vdsl2PMLineInitHist1DayShortGroup OBJECT-GROUP
            OBJECTS
                {
                vdsl2PMLHistinit1DShortInits,
                vdsl2PMLHistinit1DFailedShortInits
                }
            STATUS     current
            DESCRIPTION
                "The group of PM counters for the previous 24 hours
                 intervals short initializations.
                "
            ::= { vdsl2Groups 27 }
        
        vdsl2PMChCurrGroup OBJECT-GROUP
            OBJECTS
                {
                vdsl2PMChCurrValidIntervals,
                vdsl2PMChCurrInvalidIntervals,
                vdsl2PMChCurr15MTimeElapsed,
                vdsl2PMChCurr15MCodingViolations,
                vdsl2PMChCurr15MCorrectedBlocks,
                vdsl2PMChCurr1DayValidIntervals,
                vdsl2PMChCurr1DayInvalidIntervals,
                vdsl2PMChCurr1DayTimeElapsed,
                vdsl2PMChCurr1DayCodingViolations,
                vdsl2PMChCurr1DayCorrectedBlocks,
                vdsl2PMChEverBeforeCodingViolations,
                vdsl2PMChEverBeforeCorrectedBlocks  
                }
            STATUS     current
            DESCRIPTION
                "The group of objects that report the channel level
                 counters for current PM intervals.
                "
            ::= { vdsl2Groups 28 }
        
        vdsl2PMChHist15MinGroup OBJECT-GROUP
            OBJECTS
                {
                vdsl2PMChHist15MMonitoredTime,
                vdsl2PMChHist15MCodingViolations,
                vdsl2PMChHist15MCorrectedBlocks,
                vdsl2PMChHist15MValidInterval
                }
            STATUS     current
            DESCRIPTION
                "The group of objects that report the channel level
                 counters for previous 15 minutes PM intervals.
                "
            ::= { vdsl2Groups 29 }
        
        vdsl2PMChHist1DGroup OBJECT-GROUP
            OBJECTS
                {
                vdsl2PMChHist1DMonitoredTime,
                vdsl2PMChHist1DCodingViolations,
                vdsl2PMChHist1DCorrectedBlocks,
                vdsl2PMChHist1DValidInterval
                }
            STATUS     current
            DESCRIPTION
                "The group of objects that report the channel level
                 counters for previous 24 hours PM intervals.
                "
            ::= { vdsl2Groups 30 }
        
        vdsl2ScalarDeltGroup OBJECT-GROUP
            OBJECTS
                {
                vdsl2ScalarSCMaxInterfaces,
                vdsl2ScalarSCAvailInterfaces
                }
            STATUS     current
            DESCRIPTION
                "The group of objects that report the available memory
                 resources for DELT processes.
                "
            ::= { vdsl2Groups 31 }
            
        vdsl2ThreshNotificationGroup NOTIFICATION-GROUP
            NOTIFICATIONS
            {
            vdsl2LinePerfFECSThreshXtuc,
            vdsl2LinePerfFECSThreshXtur,
            vdsl2LinePerfESThreshXtuc,
            vdsl2LinePerfESThreshXtur,
            vdsl2LinePerfSESThreshXtuc,
            vdsl2LinePerfSESThreshXtur,
            vdsl2LinePerfLOSSThreshXtuc,
            vdsl2LinePerfLOSSThreshXtur,
            vdsl2LinePerfUASThreshXtuc,
            vdsl2LinePerfUASThreshXtur,
            vdsl2LinePerfCodingViolationsThreshXtuc,
            vdsl2LinePerfCodingViolationsThreshXtur,
            vdsl2LinePerfCorrectedThreshXtuc,
            vdsl2LinePerfCorrectedThreshXtur,
            vdsl2LinePerfFailedFullInitThresh,
            vdsl2LinePerfFailedShortInitThresh,
            vdsl2LinePerfFullInitThresh
            }
            STATUS      current
            DESCRIPTION
                "This notification indicates alarm when this group supports notifications 
                 of significant conditions associated with VDSL2 lines.
                "
            ::= { vdsl2Groups 32 }
        
        vdsl2StatusChangeNotificationGroup NOTIFICATION-GROUP
            NOTIFICATIONS
            {
            vdsl2LineStatusChangeXtuc,
            vdsl2LineStatusChangeXtur
            }
            STATUS      current
            DESCRIPTION
                "This notification indicates alarm when this group supports notifications 
                 of thresholds crossing associated with VDSL2 lines.
                "
            ::= { vdsl2Groups 33 }
            
            
             -- mode information
        
        hwvdslmodecfg  OBJECT-TYPE
            SYNTAX  Vdsl2CfgMode
            MAX-ACCESS  read-write
            STATUS  current
            DESCRIPTION
                "This object is used to change VDSL management mode.
                 After the mode being changed, system will automatically
                 save data and reboot.
                "
            ::= { vdsl2Mode 1 }
            
              -- VDSL DPBO ESEL
        
        vdsl2DpboEselGlobalConfigSwitch   OBJECT-TYPE       
            SYNTAX INTEGER       
            {       
            enabled(1),       
            disabled(2)      
            }       
            MAX-ACCESS  read-write       
            STATUS      current       
            DESCRIPTION       
                "Enable/Disable VDSL port DPBOESEL shall Feature.
                 This object is defaulted disabled(2).
                 Options:
                 1. enabled(1)  - enabled the switch
                 2. disabled(2) - disabled the switch
                "       
                   
            ::= { vdsl2GlobalConfig 1 }       
        
        vdsl2DpboEselGlobalConfigValue  OBJECT-TYPE     
            SYNTAX      Unsigned32 (0..511)       
            UNITS       "0.5dB"       
            MAX-ACCESS  read-write       
            STATUS      current       
            DESCRIPTION       
                "This configuration parameter defines the assumed electrical length of        
                  cables (E-side cables) connecting exchange based DSL services to a remote       
                  flexibility point (cabinet), that hosts the xTU-C that is subject to        
                  spectrally shaped downstream power back-off depending on this length.        
                  For this parameter the electrical length is defined as the loss (in dB)        
                  of an equivalent length of hypothetical cable at a reference frequency        
                  defined by the network operator or in spectrum management regulations.        
                  DPBOESEL shall be coded as an unsigned integer representing an electrical        
                  length from 0 dB (coded as 0) to 255.5 dB (coded as 511) in steps of 0.5 dB.        
                  All values in the range are valid.If DPBOESEL is set to zero, the DPBO in        
                  this section shall be disabled. This object is defaulted 84.
                  Unit: 0.5dB
                 "        
            REFERENCE    "ITU-T G.997.1(200604), paragraph 7.3.1.2.13" 
            
            ::= { vdsl2GlobalConfig 2 }
            
        vdsl2ProfileAutoNegotiationSwitch   OBJECT-TYPE       
            SYNTAX INTEGER       
            {       
            enabled(1),       
            disabled(2)      
            }       
            MAX-ACCESS  read-write       
            STATUS      current       
            DESCRIPTION       
                "Enable/Disable the VDSL2 G993.2 profile auto-negotiation function.
                 Default values:disabled(2).
                 Options:
                 1. enabled(1)  - enabled the switch
                 2. disabled(2) - disabled the switch
                "  
            ::= { vdsl2GlobalConfig 3  }   
            
        vdsl2MaximumInterleavedDepth   OBJECT-TYPE       
            SYNTAX INTEGER       
            {       
            maxInterleavedDepth64(1),       
            maxInterleavedDepth511(2)      
            }       
            MAX-ACCESS  read-write       
            STATUS      current       
            DESCRIPTION       
                "Set the VDSL2 maximum interleaved depth function.
                 Default values:maxInterleavedDepth511(2).
                 Options:
                 1. maxInterleavedDepth64(1)  - it means the interleaving depth up to 64 can be selected
                 2. maxInterleavedDepth511(2) - it means the interleaving depth up to 512 can be selected
                "  
            ::= { vdsl2GlobalConfig 4  }   
        
         -- VDSL auto delete profile unused
        
        hwvdsl2AutoDeleteProfUnusedProfType   OBJECT-TYPE       
            SYNTAX INTEGER       
            {       
            vdsl2LineConfTemplate(1),       
            vdsl2LineConfProf(2),
            vdsl2ChConfProfile(3),
            vdsl2LineAlarmConfTemplate(4),
            vdsl2LineAlarmConfProfile(5),
            vdsl2ChAlarmConfProfile(6),
            vdsl2ServProf(7),
            vdsl2SpectrumProf(8),
            vdsl2DpboProf(9),
            vdsl2UpboProf(10),
            vdsl2NoiseMarginProf(11),
            vdsl2DelayInpProf(12),
            vopDataRateConfProf(13),
            vopLineSpectrumConfProf(14),
            vopUPBOConfProf(15),
            vopDPBOConfProf(16),
            vopRFIConfProf(17),
            vopSNRMarginConfProf(18),
            vopINPDelayConfProf(19),
            vopVirtualNoiseConfProf(20),
            vopModeSpecificPSDConfProf(21)
            }       
            MAX-ACCESS  read-write       
            STATUS      current       
            DESCRIPTION       
               "The profile type of deleting unused VDSL profile.
               Options:
               1. vdsl2LineConfTemplate(1)          - VDSL2 line template
               2. vdsl2LineConfProf(2)              - VDSL2 line profile
               3. vdsl2ChConfProfile(3)             - VDSL2 channel profile
               4. vdsl2LineAlarmConfTemplate(4)     - VDSL2 alarm template
               5. vdsl2LineAlarmConfProfile(5)      - VDSL2 alarm profile
               6. vdsl2ChAlarmConfProfile(6)        - VDSL2 channel alarm profile
               7. vdsl2ServProf(7)                  - VDSL2 service profile
               8. vdsl2SpectrumProf(8)              - VDSL2 spectrum profile
               9. vdsl2DpboProf(9)                  - VDSL2 dpbo profile
               10. vdsl2UpboProf(10)                - VDSL2 upbo profile
               11. vdsl2NoiseMarginProf(11)         - VDSL2 noise-margin profile
               12. vdsl2DelayInpProf(12)            - VDSL2 inp-delay profile
               13. vopDataRateConfProf(13)          - XDSL data rate profile
               14. vopLineSpectrumConfProf(14)      - XDSL line spectrum profile
               15. vopUPBOConfProf(15)              - XDSL upbo profile
               16. vopDPBOConfProf(16)              - XDSL dpbo profile
               17. vopRFIConfProf(17)               - XDSL rfi profile
               18. vopSNRMarginConfProf(18)         - XDSL noise-margin profile
               19. vopINPDelayConfProf(19)          - XDSL inp-delay profile
               20. vopVirtualNoiseConfProf(20)      - XDSL virtual noise profile
               21. vopModeSpecificPSDConfProf(21)   - XDSL PSD profile
               "       
                   
            ::= { hwvdsl2AutoDeleteProfUnused 1 }       
        
        hwvdsl2AutoDeleteProfUnusedOperType  OBJECT-TYPE
            SYNTAX INTEGER       
            {       
                first(1),       
                all(2)      
            }
            MAX-ACCESS  read-write       
            STATUS      current       
            DESCRIPTION       
                "The operation type of deleting unused VDSL profile.
                 This object is defaulted all(2).
                 Options:
                 1. first(1)   - Delete first profile
                 2. all(2)     - Delete all profile
                "        
                
            ::= { hwvdsl2AutoDeleteProfUnused 2 }
        
--        hwvdsl2TrapsVbOids         
        
        hwvdsl2LinePMThresholdItem OBJECT-TYPE
            SYNTAX OCTET STRING (SIZE (0..1024))
            MAX-ACCESS accessible-for-notify
            STATUS current
            DESCRIPTION
                "Indicate the threshold item."
            ::= { hwvdsl2TrapsVbOids 1 }
           
        hwvdsl2LinePMThresholdValue OBJECT-TYPE
            SYNTAX Integer32
            MAX-ACCESS accessible-for-notify
            STATUS current
            DESCRIPTION
                "VDSL threshold value"
            ::= { hwvdsl2TrapsVbOids 2 }
           
        hwvdsl2PortActFailReason OBJECT-TYPE
            SYNTAX OCTET STRING (SIZE (0..1024))
            MAX-ACCESS accessible-for-notify
            STATUS current
            DESCRIPTION
                "Indicate the the reason of the active port fail."
            ::= { hwvdsl2TrapsVbOids 3 }
            
        hwvdsl2ChPMThresholdItem OBJECT-TYPE
            SYNTAX OCTET STRING (SIZE (0..1024))
            MAX-ACCESS accessible-for-notify
            STATUS current
            DESCRIPTION
                "Indicate the threshold value of threshold item ."
            ::= { hwvdsl2TrapsVbOids 4 }
           
        hwvdsl2ChPMCurrentValue OBJECT-TYPE
            SYNTAX Integer32
            MAX-ACCESS accessible-for-notify
            STATUS current
            DESCRIPTION
                "Indicate the current value of threshold item."
            ::= { hwvdsl2TrapsVbOids 5 }
           
        hwvdsl2ChPMThresholdValue OBJECT-TYPE
            SYNTAX Integer32
            MAX-ACCESS accessible-for-notify
            STATUS current
            DESCRIPTION
                "Indicate the threshold value of threshold item."
            ::= { hwvdsl2TrapsVbOids 6 }
           
        hwvdsl2LineActRateUs OBJECT-TYPE
            SYNTAX Integer32
            MAX-ACCESS accessible-for-notify
            STATUS current
            DESCRIPTION
                "Indicate the line active data rate in 
                 the upstream direction.
                "
            ::= { hwvdsl2TrapsVbOids 7 }
           
        hwvdsl2LineActRateDs OBJECT-TYPE
            SYNTAX Integer32
            MAX-ACCESS accessible-for-notify
            STATUS current
            DESCRIPTION
                "Indicate the line active data rate in 
                 the downstream direction.
                "
            ::= { hwvdsl2TrapsVbOids 8 }
           
        hwvdsl2ChipsetID OBJECT-TYPE
            SYNTAX Integer32
            MAX-ACCESS accessible-for-notify
            STATUS current
            DESCRIPTION
                "ChipsetID, the chipset id of the board."
            ::= { hwvdsl2TrapsVbOids 9 }   
           
        hwvdsl2ModeSwitchResult OBJECT-TYPE
            SYNTAX  INTEGER {
                       success(0),    
                       fail(1)                     
                    }
            MAX-ACCESS accessible-for-notify
            STATUS current
            DESCRIPTION
                "VDSL mode switch result.
                 Options:
                 1. success(0)  - success
                 2. fail(1)     - fail   
                "
            ::= { hwvdsl2TrapsVbOids 10 }
           
        hwvdsl2LinePMCurrentValue OBJECT-TYPE
            SYNTAX Integer32
            MAX-ACCESS accessible-for-notify
            STATUS current     
            DESCRIPTION  
                "Indicate the current value of threshold item."
            ::= { hwvdsl2TrapsVbOids 11 }
           
        hwVdsl2RequestID OBJECT-TYPE
            SYNTAX Integer32
            MAX-ACCESS accessible-for-notify
            STATUS current
            DESCRIPTION
                "Request ID"
           ::= { hwvdsl2TrapsVbOids 12 }
        
        hwACTChngeDesc OBJECT-TYPE
            SYNTAX OCTET STRING (SIZE(1..256))
            MAX-ACCESS accessible-for-notify
            STATUS current
            DESCRIPTION
                "The VDSL port actived rate change description."
            ::= { hwvdsl2TrapsVbOids 13 }
            
        hwVdsl2TemplateType OBJECT-TYPE
            SYNTAX INTEGER {   
                 lineConfTemplate(1),
                 alarmConfTemplate(2),
                 spectrumProf(3),
                 dpboProf(4),
                 upboProf(5),
                 serviceProf(6),
                 noiseMarginProf(7),
                 delayInpProf(8)                            
                 }
            MAX-ACCESS accessible-for-notify
            STATUS current
            DESCRIPTION
                "Type of the VDSL template ID.
                 Options:
                 1. lineConfTemplate(1)   - VDSL2 line template
                 2. alarmConfTemplate(2)  - VDSL2 alarm template
                 3. spectrumProf(3)       - VDSL2 spectrum profile
                 4. dpboProf(4)           - VDSL2 dpbo profile
                 5. upboProf(5)           - VDSL2 upbo profile
                 6. serviceProf(6)        - VDSL2 service profile
                 7. noiseMarginProf(7)    - VDSL2 noise-margin profile
                 8. delayInpProf(8)       - VDSL2 delay-inp profile
                "
              
            ::= { hwvdsl2TrapsVbOids 14 }
            
        hwvdsl2ProfOperType OBJECT-TYPE
            SYNTAX INTEGER {   
                 add(1),
                 modify(2),
                 delete(3)
                 }
            MAX-ACCESS accessible-for-notify
            STATUS current
            DESCRIPTION
                "VDSL profile operate type.
                 Options:
                 1.add(1)    - Add a VDSL profile
                 2.modify(2) - Modify a VDSL profile
                 3.delete(3) - Delete a VDSL profile
                "
              
            ::= { hwvdsl2TrapsVbOids 15 }
                     
--        VDSL TRAP          
          
        hwvdsl2ModeSwitchTrap NOTIFICATION-TYPE
            OBJECTS {
                    hwvdsl2ModeSwitchResult           
                } 
            STATUS current
            DESCRIPTION
                "VDSL mode switch trap. 
                 This trap message is generated when the VDSL line mode fails 
                 to be switched.
                "    
            ::= { hwvdsl2CommonTraps     0 1 }
           
        hwvdsl2CurrentModeTrap NOTIFICATION-TYPE
            OBJECTS {
                    hwvdslmodecfg          
                } 
            STATUS current
            DESCRIPTION
                "VDSL current mode trap. 
                 This trap message is generated when the current mode of the VDSL 
                 line is reported to the NMS periodically.
                "  
            ::= { hwvdsl2CommonTraps     0 2 } 
            
        hwvdsl2PortStatusChangeTrap NOTIFICATION-TYPE                 
            OBJECTS {                                                  
                    hwFrameIndex,
                    hwSlotIndex,
                    hwPortIndex,
                    hwPortOperStatus,
                    hwPortPrimaryStatus,
                    hwPortSecondaryStatus
             }                                                          
            STATUS current                                             
            DESCRIPTION                                                
                "VDSL port status change trap.
                 This trap message is generated when the port status changes, 
                 for example from up to down or from down to up.The parameter
                 information about the trap message describes the current
                 status of the link and the location where the trap message
                 is generated."                      
            ::= { hwvdsl2CommonTraps  0 3 }    
           
        hwvdsl2DeltOperResultTrap NOTIFICATION-TYPE
            OBJECTS {
                    hwVdsl2RequestID,
                    vdsl2LineCmndConfLdsfFailReason,
                    ifIndex
             } 
            STATUS current
            DESCRIPTION
                "VDSL delt trap. 
                 This trap message is generated when the result of the DELT performed 
                 on the VDSL line is reported.
                "  
            ::= { hwvdsl2CommonTraps 0 4 }   
            
        hwvdsl2TemplateIDChangeTrap NOTIFICATION-TYPE
            OBJECTS {
                hwConfigChangeIP,
                hwVdsl2TemplateType,
                ifIndex,
                hwXdslProfName
    	    } 
            STATUS current
            DESCRIPTION
               "VDSL template change trap.
                This trap message is generated when the VDSL templete changed.
               "
            ::= { hwvdsl2CommonTraps 0 5 }        
            
        hwvdsl2LConfTempTemplateChangeTrap NOTIFICATION-TYPE
            OBJECTS {
                hwConfigChangeIP,
                hwvdsl2ProfOperType,
                vdsl2LConfTempTemplateName
    	    } 
            STATUS current
            DESCRIPTION
               "VDSL line template change trap.
                This trap message is generated when the VDSL line template changed.
               "
            ::= { hwvdsl2CommonTraps 0 6 }    
            
        hwvdsl2LConfProfProfileChangeTrap NOTIFICATION-TYPE
            OBJECTS {
                hwConfigChangeIP,
                hwvdsl2ProfOperType,
                vdsl2LConfProfProfileName
    	    } 
            STATUS current
            DESCRIPTION
               "VDSL line profile change trap.
                This trap message is generated when the VDSL line profile changed.
               "
            ::= { hwvdsl2CommonTraps 0 7 }    
            
        hwvdsl2ChConfProfProfileChangeTrap NOTIFICATION-TYPE
            OBJECTS {
                hwConfigChangeIP,
                hwvdsl2ProfOperType,
                vdsl2ChConfProfProfileName
    	    } 
            STATUS current
            DESCRIPTION
               "VDSL channel profile change trap.
                This trap message is generated when the VDSL channel profile changed.
               "
            ::= { hwvdsl2CommonTraps 0 8 } 
                                                
     --   VDSL ALARM          
        hwvdsl2AutoDeactivateLackLicensesAlarmTrap NOTIFICATION-TYPE
            OBJECTS {
                    hwFrameIndex,
                    hwSlotIndex
                    } 
            STATUS current
            DESCRIPTION
                "This trap message is generated when some xDSL ports or all the xDSL ports 
                 are automatically deactivated due to lack of licenses.
                "
            ::= { hwvdsl2AlarmTraps 0 1 }
           
        hwvdsl2PortAutoDeactiveLineFaultAlarmTrap NOTIFICATION-TYPE
            OBJECTS {
                    hwFrameIndex,
                    hwSlotIndex,
                    hwPortIndex
                    } 
            STATUS current
            DESCRIPTION
                "This trap message is generated when the VDSL port is automatically 
                 deactivated due to the line fault."
            ::= { hwvdsl2AlarmTraps 0 2 }
            
        hwvdsl2PortReactiveAfterRecoverAlarmTrap NOTIFICATION-TYPE
            OBJECTS {
                    hwFrameIndex,
                    hwSlotIndex,
                    hwPortIndex
                    } 
            STATUS current
            DESCRIPTION
                "This trap message is generated when the VDSL port is re-activated 
                 after the VDSL line recovers."
            ::= { hwvdsl2AlarmTraps 0 3 }
           
        hwvdsl2PerformanceStatiReachThresholdAlarmTrap NOTIFICATION-TYPE
            OBJECTS {
                    hwFrameIndex,
                    hwSlotIndex,
                    hwPortIndex,
                    hwvdsl2LinePMThresholdItem,
                    hwvdsl2LinePMCurrentValue,
                    hwvdsl2LinePMThresholdValue
                    } 
            STATUS current
            DESCRIPTION
                "This trap message is generated when the line performance 
                 statistics of the VDSL port reach the threshold."
            ::= { hwvdsl2AlarmTraps 0 4 }
           
       hwvdsl2DownstreamRateLowerThresholdAlarmTrap NOTIFICATION-TYPE
            OBJECTS {
                    hwFrameIndex,
                    hwSlotIndex,
                    hwPortIndex,
                    vdsl2ChStatusChannelNum,
                    vdsl2ChStatusActDataRate
                    } 
            STATUS current
            DESCRIPTION
              "This trap message is generated when the xDSL channel downstream 
               rate is lower than the threshold."
            ::= { hwvdsl2AlarmTraps 0 5 }
           
        hwvdsl2ActivePortFailConfigParaAlarmTrap NOTIFICATION-TYPE
            OBJECTS {
                    hwFrameIndex,
                    hwSlotIndex,
                    hwPortIndex,
                    hwvdsl2PortActFailReason
                    } 
            STATUS current
            DESCRIPTION
                "This trap message is generated when it fails to activate the port 
                 by using the VDSL line configuration parameters."
            ::= { hwvdsl2AlarmTraps 0 6 }
           
        hwvdsl2PerformanceStatisReachThresholdAlarmTrap NOTIFICATION-TYPE
            OBJECTS {
                    hwFrameIndex,
                    hwSlotIndex,
                    hwPortIndex,
                    vdsl2ChStatusChannelNum,
                    hwvdsl2ChPMThresholdItem,
                    hwvdsl2ChPMThresholdValue,
                    hwvdsl2ChPMCurrentValue
                    } 
            STATUS current
            DESCRIPTION
                "This trap message is generated when the channel performance statistics 
                 of the VDSL port reach the threshold."
            ::= { hwvdsl2AlarmTraps 0 7 }
           
        hwvdsl2ChannelUpstreamLowerThresholdAlarmTrap NOTIFICATION-TYPE
            OBJECTS {
                    hwFrameIndex,
                    hwSlotIndex,
                    hwPortIndex,
                    vdsl2ChStatusChannelNum,
                    vdsl2ChStatusActDataRate
                    } 
            STATUS current
            DESCRIPTION
              "This trap message is generated when the xDSL channel upstream rate 
               is lower than the threshold."
            ::= { hwvdsl2AlarmTraps 0 8 }
           
        hwvdsl2VTURPowerOffAlarmTrap NOTIFICATION-TYPE
            OBJECTS {
                    hwFrameIndex,
                    hwSlotIndex,
                    hwPortIndex
                    } 
            STATUS current
            DESCRIPTION
                "This trap message is generated when the VTU-R is powered off."
            ::= { hwvdsl2AlarmTraps 0 9 }
           
        hwvdsl2PortActiveRateChangeAlarmTrap NOTIFICATION-TYPE
            OBJECTS {
                    hwFrameIndex,
                    hwSlotIndex,
                    hwPortIndex,
                    hwvdsl2LineActRateUs,
                    hwvdsl2LineActRateDs,
                    hwACTChngeDesc
                    } 
            STATUS current
            DESCRIPTION
                "This trap message is generated when the VDSL port actived rate change."
            ::= { hwvdsl2AlarmTraps 0 10 }
           
        hwvdsl2ChipsetUnavailableAlarmTrap NOTIFICATION-TYPE
            OBJECTS {
                    hwFrameIndex,
                    hwSlotIndex,
                    hwvdsl2ChipsetID
                    } 
            STATUS current
            DESCRIPTION
                "This trap message is generated when the VDSL chipset is unavailable."
            ::= { hwvdsl2AlarmTraps 0 11 }
           
        hwvdsl2ChipsetRecoverAlarmTrap NOTIFICATION-TYPE
            OBJECTS {
                    hwFrameIndex,
                    hwSlotIndex,
                    hwvdsl2ChipsetID
                    } 
            STATUS current
            DESCRIPTION
                "This trap message is generated when the VDSL chipset recovers from unavailability."
            ::= { hwvdsl2AlarmTraps 0 12 }
           
        hwvdsl2ChannelUpstreamExcThreAlarmTrap NOTIFICATION-TYPE
            OBJECTS {
                    hwFrameIndex,
                    hwSlotIndex,
                    hwPortIndex,
                    vdsl2ChStatusActDataRate
                    } 
            STATUS current
            DESCRIPTION
              "This trap message is generated when the xDSL channel upstream rate 
               increases to a value higher than the threshold."
            ::= { hwvdsl2AlarmTraps 0 13 }
           
        hwvdsl2ChannelUpstreamRestoreThreAlarmTrap NOTIFICATION-TYPE
            OBJECTS {
                    hwFrameIndex,
                    hwSlotIndex,
                    hwPortIndex,
                    vdsl2ChStatusActDataRate
                    } 
            STATUS current
            DESCRIPTION
              "This trap message is generated when the xDSL channel upstream rate 
               decreases to a value lower than the threshold."
            ::= { hwvdsl2AlarmTraps 0 14 }
           
        hwvdsl2ChannelDownstreamExcThreAlarmTrap NOTIFICATION-TYPE
            OBJECTS {
                    hwFrameIndex,
                    hwSlotIndex,
                    hwPortIndex,
                    vdsl2ChStatusActDataRate
                    } 
            STATUS current
            DESCRIPTION
              "This trap message is generated when the xDSL channel downstream rate 
               increases to a value higher than the threshold."
            ::= { hwvdsl2AlarmTraps 0 15 }
           
        hwvdsl2ChannelDownstreamRestoreThreAlarmTrap NOTIFICATION-TYPE
            OBJECTS {
                    hwFrameIndex,
                    hwSlotIndex,
                    hwPortIndex,
                    vdsl2ChStatusActDataRate
                    } 
            STATUS current
            DESCRIPTION
              "This trap message is generated when the xDSL channel downstream rate 
               decreases to a value lower than the threshold."
            ::= { hwvdsl2AlarmTraps 0 16 }
            
        hwvdsl2UnSuppVectorPortActFailAlarmTrap NOTIFICATION-TYPE
            OBJECTS {
                    hwFrameIndex,
                    hwSlotIndex,
                    hwPortIndex
                    } 
            STATUS current
            DESCRIPTION
              "When the CPE connected to the port does not support vectoring and 
               cannot be activated in 993.2 mode, this trap is sent."
            ::= { hwvdsl2AlarmTraps 0 17 }        
    END
