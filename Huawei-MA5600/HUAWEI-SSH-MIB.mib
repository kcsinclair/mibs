-- ==================================================================
-- Copyright (C) 2010 by HUAWEI TECHNOLOGIES. All rights reserved.
-- Description: This mib which contains objects manages the 
--              SSH server and SSH client configuration. 
-- Reference:  
-- Version: V1.07
-- ==================================================================

-- ==================================================================
-- 
-- Varibles and types are imported
--
-- ==================================================================
    HUAWEI-SSH-MIB DEFINITIONS ::= BEGIN
 
        IMPORTS
            hwDatacomm          
                FROM HUAWEI-MIB         
            OBJECT-GROUP, MODULE-COMPLIANCE, NOTIFICATION-GROUP         
                FROM SNMPv2-CONF            
            Integer32, OBJECT-TYPE, MODULE-IDENTITY, NOTIFICATION-TYPE          
                FROM SNMPv2-SMI         
            RowStatus, DisplayString            
                FROM SNMPv2-TC;
    
    

        hwSSH MODULE-IDENTITY 
            LAST-UPDATED "201011090000Z"        
            ORGANIZATION "Huawei Technologies co.,Ltd."
            CONTACT-INFO                                        
                         "Huawei Industrial Base                
                          Bantian, Longgang                     
                          Shenzhen 518129                       
                          People's Republic of China            
                          Website: http://www.huawei.com        
                          Email: support@huawei.com             
                         "                                      
            DESCRIPTION 
                "This mib which contains objects manages the 
                SSH server and SSH client configuration. 
                "   
 --  Revision history
            REVISION    "201011090000Z"
            DESCRIPTION "V1.07, The description of this MIB is modified according to the tool."
             
            REVISION    "201008250000Z"
            DESCRIPTION "V1.06, modified the contact-info and the revision history. Modified the description of leaves."
             
            REVISION    "201006170000Z"
            DESCRIPTION "V1.05, the description of hwSSHServerTimeOut, hwSSHServerPort, hwSSHServerKeyTimeOut, hwSSHUserTable, 
                         hwSSHUserEntry, hwSSHUserAuthType and hwSSHUserServiceType were modified and supplemented." 

            REVISION    "201004180000Z"
            DESCRIPTION "V1.04, DT requirements were implemented and the syntax and semantics of SIMPLETEST were changed." 
                          
            REVISION    "201003030000Z"
            DESCRIPTION "V1.03, DT requirements were implemented and the syntax and semantics of SIMPLETEST were changed."
            
            REVISION    "201001290000Z"        
            DESCRIPTION "V1.02, hwRSAPublicKeyTable was added."  
                
            REVISION    "200609050000Z"
            DESCRIPTION "V1.00, completed the draft."
            ::= { hwDatacomm 118 }
               
--
-- Node definitions
--
    
--  ==================================================================
-- 
-- ======================= definition begin =========================
-- 
-- ==================================================================       
        hwSSHServer OBJECT IDENTIFIER ::= { hwSSH 1 }

        
        hwStelnetServerEnable OBJECT-TYPE
            SYNTAX INTEGER
                {
                    enable(1),
                    disable(2)
                }
            MAX-ACCESS read-write
            STATUS current
            DESCRIPTION
                "
                The object specifies whether the SSH stelnet server is enable.
                Options:
                1. enable(1) -The SSH stelnet server is enable.
                2. disable(2)-The SSH stelnet server is disable.
                "
            -- DEFVAL { 2 } 
            ::= { hwSSHServer 1 }

        
        hwSftpServerEnable OBJECT-TYPE
            SYNTAX INTEGER
                {
                    enable(1),
                    disable(2)
                }
            MAX-ACCESS read-write
            STATUS current
            DESCRIPTION
                "
                The object specifies whether the sftp server is enable.
                Options:
                1.enable(1) -the sftp server is enable
                2.disable(2)-the sftp server is disable.
                "
            -- DEFVAL { 2 }
            ::= { hwSSHServer 2 }

        
        hwSSHServerComp1x OBJECT-TYPE
            SYNTAX INTEGER
                {
                    enable(1),
                    disable(2)
                }
            MAX-ACCESS read-write
            STATUS current
            DESCRIPTION
                "
                The object specifies whether the SSH server is compatible with SSH1.x. 
                Options:
                1. enable(1) -indicates that the version compatibility function of the SSH server is enabled 
                              so that the SSH server is compatible with the SSHv1.x client.
                2. disable(2)-indicates that the version compatibility function of the SSH server is disabled 
                              and therefore the SSH server is incompatible with the SSHv1.x client.
                "
            --DEFVAL { 1 }
            ::= { hwSSHServer 3 }

        
        hwSSHServerTimeOut OBJECT-TYPE
            SYNTAX Integer32 (60..120)   
            UNITS      "second"       
            MAX-ACCESS read-write          
            STATUS     current
            DESCRIPTION
                "
                The object specifies the time when SSH authentication times out.              
                Range: 60-120
                Unit:  second           
                " 
            ::= { hwSSHServer 4 }

        
        hwSSHServerRetry OBJECT-TYPE
            SYNTAX Integer32 (1..5)
            MAX-ACCESS read-write
            STATUS current
            DESCRIPTION
                "
                The object specifies authentication-retry times for SSH user. 
                Default: 3
                "
            ::= { hwSSHServer 5 }

        
        hwSSHServerPort OBJECT-TYPE
            SYNTAX Integer32 (22|1025..55535)
            MAX-ACCESS read-write
            STATUS current
            DESCRIPTION
                "
                ID of the monitoring port on the SSH server.
                "
            ::= { hwSSHServer 6 }

        
        hwSSHServerKeyTimeOut OBJECT-TYPE
            SYNTAX     Integer32 (0..24) 
            UNITS      "hour"
            MAX-ACCESS read-write
            STATUS     current
            DESCRIPTION
                "
                The interval of updating the SSH server key pair.    
                By default, value is 0 hour, which means server key can't be updated forever.
                Range: 0-24
                Unit: hour
                "
            ::= { hwSSHServer 7 }
            
            
        hwSSHServerAlarmEnable OBJECT-TYPE
            SYNTAX INTEGER
                {
                    enable(1),
                    disable(2)
                }
            MAX-ACCESS read-write
            STATUS current
            DESCRIPTION
                "
                The object specifies whether send trap information to NMS.
                Options:
                1.enable(1) -Only when its value enable, allowed to send trap informations to NMS.
                2.disable(2)-Can not to send trap informations to NMS.
                "
            --DEFVAL { 2 }
            ::= { hwSSHServer 8 }
            
            
        hwSftpMaxUserNum OBJECT-TYPE
            SYNTAX Integer32(0..5)
            MAX-ACCESS read-only
            STATUS current
            DESCRIPTION
                "
                The object specifies the max number of sftp user that sftp server supporting.
                "
            ::= { hwSSHServer 9 }
            
            
        hwSftpOnLineUserNum OBJECT-TYPE
            SYNTAX Integer32(0..5)
            MAX-ACCESS read-only
            STATUS current
            DESCRIPTION
                "
                The object specifies the number of sftp user that has been connected to sftp server currently.
                "
            ::= { hwSSHServer 10 }
            
        
        hwSSHUserTable OBJECT-TYPE
            SYNTAX SEQUENCE OF HwSSHUserEntry
            MAX-ACCESS not-accessible
            STATUS current
            DESCRIPTION
                "
                This table is used for querying and setting the information about SSH user.
                The index of this table is hwSSHUserIndex. 
                "
            ::= { hwSSHServer 11 }

        
        hwSSHUserEntry OBJECT-TYPE
            SYNTAX HwSSHUserEntry
            MAX-ACCESS not-accessible
            STATUS current
            DESCRIPTION
                "
                This table is used for querying and setting the information about SSH user.
                The index of this entry is hwSSHUserIndex.                 
                "
            INDEX { hwSSHUserIndex }
            ::= { hwSSHUserTable 1 }

        
        HwSSHUserEntry ::=
            SEQUENCE 
            {
                hwSSHUserIndex
                    Integer32, 
                hwSSHUserName
                    OCTET STRING,
                hwSSHUserAssignKey
                    OCTET STRING,
                hwSSHUserAuthType
                    INTEGER,
                hwSSHUserServiceType
                    INTEGER,
                hwSSHUserSftpDirectory
                    OCTET STRING,
                hwSSHUserAuthorizationCMD
                    INTEGER,
                hwSSHUserRowStatus
                    RowStatus
             }

        hwSSHUserIndex OBJECT-TYPE
            SYNTAX Integer32 (1..200)
            MAX-ACCESS not-accessible
            STATUS current
            DESCRIPTION
                "
                The object specifies the index of hwSSHUserTable.
                "
            ::= { hwSSHUserEntry 1 }
            
            
        hwSSHUserName OBJECT-TYPE
            SYNTAX OCTET STRING (SIZE (1..64))
            MAX-ACCESS read-create
            STATUS current
            DESCRIPTION
                "
                The object specifies the name of a SSH user.
                "
            ::= { hwSSHUserEntry 2 }

        
        hwSSHUserAssignKey OBJECT-TYPE
            SYNTAX OCTET STRING (SIZE (0..64))
            MAX-ACCESS read-create
            STATUS current
            DESCRIPTION
                "
                The object specifies is a peer public key for a SSH user.
                This peer public key on the SSH server must exist and associate with hwRSAPublicKeyName.
                "
            ::= { hwSSHUserEntry 3 }

        
        hwSSHUserAuthType OBJECT-TYPE
            SYNTAX INTEGER
                {
                    authNULL(1),
                    authPASSWORD(2),
                    authRSA(3),
                    authRSAorPASSWORD(4),
                    authRSAandPASSWORD(5)
                }
            MAX-ACCESS read-create
            STATUS current
            DESCRIPTION
                "
                The object specifies the authentication type of SSH user.
                The default authentication type is authPASSWORD.
                Options: 
                1. authNULL(1)           -No authenticate.
                2. authPASSWORD(2)       -Password authentication.
                3. authRSA(3)            -RSA key authentication.
                4. authRSAorPASSWORD(4)  -Password or RSA key authentication.
                5. authRSAandPASSWORD(5) -Password and RSA key authentication.
                " 
            DEFVAL { authPASSWORD }
            ::= { hwSSHUserEntry 4 }

        
        hwSSHUserServiceType OBJECT-TYPE 
            SYNTAX INTEGER
                {
                    servicetypeNULL(1),
                    servicetypeSTELNET(2),
                    servicetypeSFTP(3),
                    servicetypeALL(4)
                }
            MAX-ACCESS read-create
            STATUS current
            DESCRIPTION
                "
                The object specifies the service type of SSH user. 
                Options: 
                1. servicetypeNULL(1)    -default service type.
                2. servicetypeSTELNET(2) -The service type of the SSH user is STELNET.
                3. servicetypeSFTP(3)    -The service type of the SSH user is SFTP.
                4. servicetypeALL(4)     -The service type of the SSH user is all.               
                "                
            DEFVAL { servicetypeNULL }
            ::= { hwSSHUserEntry 5 }

        
        hwSSHUserSftpDirectory OBJECT-TYPE
            SYNTAX OCTET STRING (SIZE (0..64))
            MAX-ACCESS read-create
            STATUS current
            DESCRIPTION
                "
                The object specifies the working directory for the sftp user.
                "
            ::= { hwSSHUserEntry 6 }

        
        hwSSHUserAuthorizationCMD OBJECT-TYPE
            SYNTAX INTEGER
                {
                    authorizationNULL(1),
                    authorizationAAA(2)
                }
            MAX-ACCESS read-create
            STATUS current
            DESCRIPTION
                "
                The object specifies the authorization type of SSH user.
                Options:
                1.authorizationNULL(1)-The default authorization is authorizationNULL,indicating SSH user 
                                       doesn't need to be authorizated by HWTACACS server.
                2.authorizationAAA(2) -When authorizationAAA is specified,the SSH user will be 
                                       authorizated by HWTACACS server. 
                "
           DEFVAL { authorizationNULL }
            ::= { hwSSHUserEntry 7 }
            

        hwSSHUserRowStatus OBJECT-TYPE
            SYNTAX RowStatus
            MAX-ACCESS read-create
            STATUS current
            DESCRIPTION
                "
                The object specifies the status of this entry.
                When the status is active(1), hwSSHUserAssignKey, hwSSHUserAuthType, 
                hwSSHUserServiceType, hwSSHUserSftpDirectory, and hwSSHUserAuthorizationCMD's 
                value in the entry are allowed to be modified.
                "
            ::= { hwSSHUserEntry 8 }


        hwSSHServerSessionTable OBJECT-TYPE
            SYNTAX SEQUENCE OF HwSSHServerSessionEntry
            MAX-ACCESS not-accessible
            STATUS current
            DESCRIPTION
                "
                The object shows current session information of the SSH server which includes username,
                version information, retry times of online users currently.
                The index of this table is hwSSHSessionIndex.
                "
            ::= { hwSSHServer 12 }

        
        hwSSHServerSessionEntry OBJECT-TYPE
            SYNTAX HwSSHServerSessionEntry
            MAX-ACCESS not-accessible
            STATUS current
            DESCRIPTION
                "
                The object shows current session information of the SSH server which includes username,
                version information, retry times of online users currently.
                The index of this entry is hwSSHSessionIndex.                
                "
            INDEX { hwSSHSessionIndex }
            ::= { hwSSHServerSessionTable 1 }

        
        HwSSHServerSessionEntry ::=
            SEQUENCE 
            { 
                hwSSHSessionIndex
                    Integer32,
                hwSSHSessionUserName
                    DisplayString,
                hwSSHSessionConnectType
                    INTEGER,
                hwSSHSessionVer
                    DisplayString,
                hwSSHSessionState
                    INTEGER,
                hwSSHSessionRetry
                    Integer32,
                hwSSHSessionCtosCipher
                    DisplayString,
                hwSSHSessionStocCipher
                    DisplayString,
                hwSSHSessionCtosHmac
                    DisplayString,
                hwSSHSessionStocHmac
                    DisplayString,
                hwSSHSessionKex
                    DisplayString,
                hwSSHSessionAuthType
                    DisplayString,
                hwSSHSessionServiceType
                    DisplayString
             }
             
        hwSSHSessionIndex OBJECT-TYPE
            SYNTAX Integer32 (1..15)
            MAX-ACCESS not-accessible
            STATUS current
            DESCRIPTION
                "
                The object specifies the index of hwSSHServerSessionTable.
                "
            ::= { hwSSHServerSessionEntry 1 }

        hwSSHSessionUserName OBJECT-TYPE
            SYNTAX DisplayString
            MAX-ACCESS read-only
            STATUS current
            DESCRIPTION
                "
                The object specifies the name of a SSH user,
                which has started a session.
                "
            ::= { hwSSHServerSessionEntry 2 }


        hwSSHSessionConnectType OBJECT-TYPE
            SYNTAX INTEGER
                {
                    vty0(1),
                    vty1(2),
                    vty2(3),
                    vty3(4),
                    vty4(5),
                    vty5(6),
                    vty6(7),
                    vty7(8),
                    vty8(9),
                    vty9(10),
                    vty10(11),
                    vty11(12),
                    vty12(13),
                    vty13(14),
                    vty14(15)
                }
            MAX-ACCESS read-only
            STATUS current
            DESCRIPTION
                "
                The object specifies the line number supports a connection of SSH 
                user which is in connection with SSH server. 
                Options:
                1.vty0(1) -vty0
                2.vty1(2) -vty1
                3.vty2(3) -vty2
                4.vty3(4) -vty3
                5.vty4(5) -vty4
                6.vty5(6) -vty5
                7.vty6(7) -vty6
                8.vty7(8) -vty7
                9.vty8(9) -vty8
                10.vty9(10)-vty9
                11.vty10(11)-vty10
                12.vty11(12)-vty11
                13.vty12(13)-vty12
                14.vty13(14)-vty13
                15.vty14(15)-vty14                
                " 
                ::= { hwSSHServerSessionEntry 3 }


        hwSSHSessionVer OBJECT-TYPE
            SYNTAX DisplayString
            MAX-ACCESS read-only
            STATUS current
            DESCRIPTION
                "
                The object specifies the version information of a SSH 
                user which is in connection with SSH server.
                "
            ::= { hwSSHServerSessionEntry 4 }

        hwSSHSessionState OBJECT-TYPE
            SYNTAX INTEGER { started(1) }
            MAX-ACCESS read-only
            STATUS current
            DESCRIPTION
                "
                The object specifies the state of a SSH user 
                which is in connection with SSH server.
                Options:
                1.started(1)-indicates the state is start.
                "
            ::= { hwSSHServerSessionEntry 5 }


        hwSSHSessionRetry OBJECT-TYPE
            SYNTAX Integer32 (0..5)
            MAX-ACCESS read-only
            STATUS current
            DESCRIPTION
                "
                The object specifies SSH user's retrying times in authentications.
                "
            ::= { hwSSHServerSessionEntry 6 }
        
        hwSSHSessionCtosCipher OBJECT-TYPE
            SYNTAX DisplayString
            MAX-ACCESS read-only
            STATUS current
            DESCRIPTION
                "
                The object specifies the cipher of custom to server.
                "
            ::= { hwSSHServerSessionEntry 7 }
            
        hwSSHSessionStocCipher OBJECT-TYPE
            SYNTAX DisplayString
            MAX-ACCESS read-only
            STATUS current
            DESCRIPTION
                "
                The object specifies the cipher of server to custom.
                "
            ::= { hwSSHServerSessionEntry 8 }
            
        hwSSHSessionCtosHmac OBJECT-TYPE
            SYNTAX DisplayString
            MAX-ACCESS read-only
            STATUS current
            DESCRIPTION
                "
                The object specifies the hmac of custom to server.
                "
            ::= { hwSSHServerSessionEntry 9 }
        
        hwSSHSessionStocHmac OBJECT-TYPE
            SYNTAX DisplayString
            MAX-ACCESS read-only
            STATUS current
            DESCRIPTION
                "
                The object specifies the hmac of server to custom.
                "
            ::= { hwSSHServerSessionEntry 10 }
            
        hwSSHSessionKex OBJECT-TYPE
            SYNTAX DisplayString
            MAX-ACCESS read-only
            STATUS current
            DESCRIPTION
                "
                The object specifies the key exchange.
                "
            ::= { hwSSHServerSessionEntry 11 }
            
        hwSSHSessionAuthType OBJECT-TYPE
            SYNTAX DisplayString
            MAX-ACCESS read-only
            STATUS current
            DESCRIPTION
                "
                The object specifies the authentication type of SSH session.
                "
            ::= { hwSSHServerSessionEntry 12 }

        
        hwSSHSessionServiceType OBJECT-TYPE
            SYNTAX DisplayString
            MAX-ACCESS read-only
            STATUS current
            DESCRIPTION
                "
                The object specifies the service type of SSH session.
                "
            ::= { hwSSHServerSessionEntry 13 }
                        
        hwRSAPublicKeyTable OBJECT-TYPE
            SYNTAX SEQUENCE OF HwRSAPublicKeyEntry
            MAX-ACCESS not-accessible
            STATUS current
            DESCRIPTION
                "
                A table of configuration about RSA Public Key.
                The index of this table is hwRSAPublicKeyName.  
                hwRSAPublicKeyName is the name of RSA Public Key.              
                "
            ::= { hwSSHServer 13 }
            
        hwRSAPublicKeyEntry OBJECT-TYPE
            SYNTAX HwRSAPublicKeyEntry
            MAX-ACCESS not-accessible
            STATUS current
            DESCRIPTION
                "
                A table of configuration about RSA Public Key.
                The index of this entry is hwRSAPublicKeyName.  
                hwRSAPublicKeyName is the name of RSA Public Key.
                "
             INDEX { hwRSAPublicKeyName }
            ::= { hwRSAPublicKeyTable 1 }
            
        HwRSAPublicKeyEntry ::=
            SEQUENCE 
            {
                hwRSAPublicKeyName
                    OCTET STRING, 
                hwRSAPublicKeyCode
                    OCTET STRING,
                hwRSAPublicKeyRowStatus
                    RowStatus
             } 
             
        hwRSAPublicKeyName OBJECT-TYPE
            SYNTAX OCTET STRING (SIZE (1..30))
            MAX-ACCESS not-accessible
            STATUS current
            DESCRIPTION
                "
                The object specifies the name of RSA Public Key.
                "
            ::= { hwRSAPublicKeyEntry 1 } 
            
        hwRSAPublicKeyCode OBJECT-TYPE
            SYNTAX OCTET STRING (SIZE (1..2048))
            MAX-ACCESS read-create
            STATUS current
            DESCRIPTION
                "
                The object specifies is RSA Public Key Code that in the format of ber, the maximum length of the node is 1024.             
                When the RSA public key is created, the index value is the name of the public key, which uses the ASCII code.
                The public key value must be generated through a tool. Firstly, use the PUTTYGEN.EXE tool to generate the matching 
                public key and private key. Then, use the sshkey.exe tool to convert the generated public key to the required public key value.
                "
            ::= { hwRSAPublicKeyEntry 2 }
            
        hwRSAPublicKeyRowStatus OBJECT-TYPE
            SYNTAX RowStatus
            MAX-ACCESS read-create
            STATUS current
            DESCRIPTION
                "
                The object specifies the status of this table entry.
                When the status is active(1), hwRSAPublicKeyName, hwRSAPublicKeyCode's
                value in the entry are allowed to be modified.  
                createAndGo(4) is supplied to create a new instance of a conceptual row.
                destroy(6) is supplied to delete the instances associated with an existing conceptual row.        
                "
            ::= { hwRSAPublicKeyEntry 3 }   

        
        hwSSHClient OBJECT IDENTIFIER ::= { hwSSH 2 }

        
        hwSSHFirstTimeAuthEnable OBJECT-TYPE
            SYNTAX INTEGER
                {
                    enable(1),
                    disable(2)
                }
            MAX-ACCESS read-write
            STATUS current
            DESCRIPTION
                "The object specifies whether the SSH client 
                supports first-time-authentication.
                Options:
                1.enable(1) -indicates the SSH client supports first-time-authentication.
                2.disable(2)-indicates the SSH client does not support first-time-authentication.
                "
            --DEFVAL { 2 }
            ::= { hwSSHClient 1 }

        
        hwSSHServerInfoTable OBJECT-TYPE
            SYNTAX SEQUENCE OF HwSSHServerInfoEntry
            MAX-ACCESS not-accessible
            STATUS current
            DESCRIPTION
                "
                A table of configuration about the relation
                between the SSH server and the rsa peerkey.
                The index of this table is hwSSHServerIndex.
                "
            ::= { hwSSHClient 2 }

        
        hwSSHServerInfoEntry OBJECT-TYPE
            SYNTAX HwSSHServerInfoEntry
            MAX-ACCESS not-accessible
            STATUS current
            DESCRIPTION
                "
                A table of configuration about the relation
                between the SSH server and the rsa peerkey.
                The index of this entry is hwSSHServerIndex.
                "
            INDEX { hwSSHServerIndex }
            ::= { hwSSHServerInfoTable 1 }

        
        HwSSHServerInfoEntry ::=
            SEQUENCE 
            { 
                hwSSHServerIndex
                    Integer32,
                hwSSHServerName
                    OCTET STRING,
                hwSSHServerAssignKey
                    OCTET STRING,
                hwSSHServerRowStatus
                    RowStatus
             }
             
             
        hwSSHServerIndex OBJECT-TYPE
            SYNTAX Integer32 (1..20)
            MAX-ACCESS not-accessible
            STATUS current
            DESCRIPTION
                "
                The object specifies the index of hwSSHServerInfoTable.
                "
            ::= { hwSSHServerInfoEntry 1 }


        hwSSHServerName OBJECT-TYPE
            SYNTAX OCTET STRING (SIZE (1..46))
            MAX-ACCESS read-create
            STATUS current
            DESCRIPTION
                "
                The object specifies the name of a SSH server.
                "
            ::= { hwSSHServerInfoEntry 2 }

        
        hwSSHServerAssignKey OBJECT-TYPE
            SYNTAX OCTET STRING (SIZE (1..64))
            MAX-ACCESS read-create
            STATUS current
            DESCRIPTION
                "
                The object specifies a peer public key for a 
                SSH server. This peer public key must exist.
                "
            ::= { hwSSHServerInfoEntry 3 }

        
        hwSSHServerRowStatus OBJECT-TYPE
            SYNTAX RowStatus
            MAX-ACCESS read-create
            STATUS current
            DESCRIPTION
                "
                The object specifies the status of this entry.
                When the status is active,  
                hwSSHServerAssignKey's value in the entry is 
                allowed to be modified.
                "
            ::= { hwSSHServerInfoEntry 4 }

        
        hwSSHNotifications OBJECT IDENTIFIER ::= { hwSSH 3 }

        
        hwSSHSftpUserNumExceedMax NOTIFICATION-TYPE
            OBJECTS { hwSftpOnLineUserNum, hwSftpMaxUserNum }
            STATUS current
            DESCRIPTION 
                "
                This notification was sent when the total 
                number of sftp users requesting sftp service
                exceeds 5.
                "
            ::= { hwSSHNotifications 1 }

        
--   Conformance information

        hwSSHMIBConformance OBJECT IDENTIFIER ::= { hwSSH 4 }

        
        hwSSHMIBCompliances OBJECT IDENTIFIER ::= { hwSSHMIBConformance 1 }

        
--   this module

        hwSSHMIBCompliance MODULE-COMPLIANCE
            STATUS current
            DESCRIPTION 
                "
                The compliance statement for systems supporting 
                the HUAWEI-SSH-MIB.
                "
            MODULE HUAWEI-SSH-MIB
                MANDATORY-GROUPS { hwSSHServerGroup, hwSSHUserGroup, 
                hwSSHServerSessionGroup, hwSSHClientGroup, hwSSHServerInfoGroup, 
                    hwSSHNotificationGroup }
            ::= { hwSSHMIBCompliances 1 }

        
        hwSSHMIBGroups OBJECT IDENTIFIER ::= { hwSSHMIBConformance 2 }

        
        hwSSHServerGroup OBJECT-GROUP
            OBJECTS { hwStelnetServerEnable, hwSftpServerEnable, hwSSHServerComp1x, 
            hwSSHServerTimeOut, hwSSHServerRetry, hwSSHServerPort, 
            hwSSHServerKeyTimeOut,hwSSHServerAlarmEnable,hwSftpMaxUserNum,hwSftpOnLineUserNum }
            STATUS current
            DESCRIPTION 
                "
                The SSH server attribute group.
                "
            ::= { hwSSHMIBGroups 1 }

        
        hwSSHUserGroup OBJECT-GROUP
            OBJECTS { hwSSHUserName, hwSSHUserAssignKey, hwSSHUserAuthType, 
            hwSSHUserServiceType, hwSSHUserSftpDirectory,hwSSHUserAuthorizationCMD, 
            hwSSHUserRowStatus}
            STATUS current
            DESCRIPTION 
                "
                The SSH user's group.
                "
            ::= { hwSSHMIBGroups 2 }

        
        hwSSHServerSessionGroup OBJECT-GROUP
            OBJECTS { hwSSHSessionUserName, hwSSHSessionConnectType, hwSSHSessionVer,
            hwSSHSessionState, hwSSHSessionRetry,hwSSHSessionCtosCipher,
            hwSSHSessionStocCipher,hwSSHSessionCtosHmac,hwSSHSessionStocHmac,hwSSHSessionKex,
                        hwSSHSessionAuthType,hwSSHSessionServiceType
                 }
            STATUS current
            DESCRIPTION 
                "
                The SSH server's session group.
                "
            ::= { hwSSHMIBGroups 3 }

        
        hwSSHClientGroup OBJECT-GROUP
            OBJECTS { hwSSHFirstTimeAuthEnable }
            STATUS current
            DESCRIPTION 
                "
                The SSH client's attribute group.
                "
            ::= { hwSSHMIBGroups 4 }

        
        hwSSHServerInfoGroup OBJECT-GROUP
            OBJECTS { hwSSHServerName, hwSSHServerAssignKey, hwSSHServerRowStatus }
            STATUS current
            DESCRIPTION 
                "
                The SSH serverInfo's group.
                "
            ::= { hwSSHMIBGroups 5 }

        
        hwSSHNotificationGroup NOTIFICATION-GROUP
            NOTIFICATIONS { hwSSHSftpUserNumExceedMax }
            STATUS current
            DESCRIPTION 
                "
                The SSH Notification group.
                "
            ::= { hwSSHMIBGroups 6 }

        
    
    END

--
-- HUAWEI-SSH-MIB.mib
--
