--
-- Accedian Enterprise Specific MIB
--
-- Copyright (c) 2004-2016, Accedian Networks, Inc.
-- All rights reserved.
--
-- The contents of this document are subject to change without notice.
--

ACD-SHAPER-V2-MIB DEFINITIONS ::= BEGIN

IMPORTS
    MODULE-IDENTITY, OBJECT-TYPE,
    Counter64, Unsigned32
        FROM SNMPv2-SMI
    DisplayString, DateAndTime
        FROM SNMPv2-TC
    MODULE-COMPLIANCE, OBJECT-GROUP
        FROM SNMPv2-CONF
    acdMibs
        FROM ACCEDIAN-SMI;

acdShaperV2Mib MODULE-IDENTITY

    LAST-UPDATED "201609230100Z"
    ORGANIZATION "Accedian Networks, Inc."
    CONTACT-INFO
            "Accedian Technical Assistance Center
             Accedian Networks, Inc.
             2351 Alfred-Nobel blvd., Suite N-410
             Saint-Laurent, Quebec Canada H4S 2A9
             E-mail: support@accedian.com"
    DESCRIPTION
            "Shaper-V2 database for this Accedian Networks device."

    REVISION "201609230100Z"        -- 23 September 2016
    DESCRIPTION
            "Add acdShaperV2QueueStatsHistIndex and
             acdShaperV2QueueStatsHistQueueId to acdRegulatorHistStatsGroup."

    REVISION "201605260100Z"        -- 26 May 2016
    DESCRIPTION
            "Set access level to read-only for acdShaperV2QueueStatsHistIndex,
             acdShaperV2QueueStatsHistQueueId."

    REVISION "201402140000Z"        -- Feb. 14 2014
    DESCRIPTION
            "Initial version of MIB module ACD-SHAPER-V2-MIB."

    ::= { acdMibs 21}

acdShaperV2Notifications OBJECT IDENTIFIER ::= { acdShaperV2Mib 0 }
acdShaperV2MIBObjects    OBJECT IDENTIFIER ::= { acdShaperV2Mib 1 }
acdShaperV2Conformance   OBJECT IDENTIFIER ::= { acdShaperV2Mib 2 }

------------------------------------------------------------------------
 -- Shaper-V2 queue statistics table.
---------------------------------------------------------------------------

acdShaperV2QueueStatsTable OBJECT-TYPE
    SYNTAX      SEQUENCE OF AcdShaperV2QueueStatsEntry
    MAX-ACCESS  not-accessible
    STATUS      current
    DESCRIPTION
        "Shaper-V2 queue statistics table."
    ::= { acdShaperV2MIBObjects 1 }

acdShaperV2QueueStatsEntry OBJECT-TYPE
    SYNTAX      AcdShaperV2QueueStatsEntry
    MAX-ACCESS  not-accessible
    STATUS      current
    DESCRIPTION
        "Shaper-V2 queue statistics table entry."
    INDEX   { acdShaperV2QueueStatsQueueId}
    ::=  { acdShaperV2QueueStatsTable 1 }

AcdShaperV2QueueStatsEntry ::= SEQUENCE {
    acdShaperV2QueueStatsQueueId                         Unsigned32,
    acdShaperV2QueueStatsQueueName                       DisplayString,
    acdShaperV2QueueStatsCntGreenForwardNoDelayFrames    Counter64,
    acdShaperV2QueueStatsCntGreenForwardNoDelayBytes     Counter64,
    acdShaperV2QueueStatsCntYellowForwardNoDelayFrames   Counter64,
    acdShaperV2QueueStatsCntYellowForwardNoDelayBytes    Counter64,
    acdShaperV2QueueStatsCntGreenForwardWithDelayFrames  Counter64,
    acdShaperV2QueueStatsCntGreenForwardWithDelayBytes   Counter64,
    acdShaperV2QueueStatsCntYellowForwardWithDelayFrames Counter64,
    acdShaperV2QueueStatsCntYellowForwardWithDelayBytes  Counter64,
    acdShaperV2QueueStatsCntGreenDiscardFullFrames       Counter64,
    acdShaperV2QueueStatsCntGreenDiscardFullBytes        Counter64,
    acdShaperV2QueueStatsCntYellowDiscardFullFrames      Counter64,
    acdShaperV2QueueStatsCntYellowDiscardFullBytes       Counter64,
    acdShaperV2QueueStatsCntGreenDiscardBLUEFrames       Counter64,
    acdShaperV2QueueStatsCntGreenDiscardBLUEBytes        Counter64,
    acdShaperV2QueueStatsCntYellowDiscardBLUEFrames      Counter64,
    acdShaperV2QueueStatsCntYellowDiscardBLUEBytes       Counter64,
    acdShaperV2QueueStatsCntCIRCompliantFrames           Counter64,
    acdShaperV2QueueStatsCntCIRCompliantBytes            Counter64,
    acdShaperV2QueueStatsCntEIRCompliantFrames           Counter64,
    acdShaperV2QueueStatsCntEIRCompliantBytes            Counter64
}

acdShaperV2QueueStatsQueueId OBJECT-TYPE
    SYNTAX      Unsigned32
    MAX-ACCESS  not-accessible
    STATUS      current
    DESCRIPTION
        "Identifier of the queue."
    ::= { acdShaperV2QueueStatsEntry 1 }

acdShaperV2QueueStatsQueueName OBJECT-TYPE
    SYNTAX      DisplayString (SIZE (1..32))
    MAX-ACCESS  read-only
    STATUS      current
    DESCRIPTION
        "Name of the queue."
    ::= { acdShaperV2QueueStatsEntry 2 }

acdShaperV2QueueStatsCntGreenForwardNoDelayFrames OBJECT-TYPE
    SYNTAX      Counter64
    MAX-ACCESS  read-only
    STATUS      current
    DESCRIPTION
        "Number of green frames enqueued with no delay."
    ::= { acdShaperV2QueueStatsEntry 3 }

acdShaperV2QueueStatsCntGreenForwardNoDelayBytes OBJECT-TYPE
    SYNTAX      Counter64
    MAX-ACCESS  read-only
    STATUS      current
    DESCRIPTION
        "Number of bytes of green frames enqueued with no delay."
    ::= { acdShaperV2QueueStatsEntry 4 }

acdShaperV2QueueStatsCntYellowForwardNoDelayFrames OBJECT-TYPE
    SYNTAX      Counter64
    MAX-ACCESS  read-only
    STATUS      current
    DESCRIPTION
        "Number of yellow frames enqueued with no delay."
    ::= { acdShaperV2QueueStatsEntry 5 }

acdShaperV2QueueStatsCntYellowForwardNoDelayBytes OBJECT-TYPE
    SYNTAX      Counter64
    MAX-ACCESS  read-only
    STATUS      current
    DESCRIPTION
        "Number of bytes of yellow frames enqueued with no delay."
    ::= { acdShaperV2QueueStatsEntry 6 }

acdShaperV2QueueStatsCntGreenForwardWithDelayFrames OBJECT-TYPE
    SYNTAX      Counter64
    MAX-ACCESS  read-only
    STATUS      current
    DESCRIPTION
        "Number of green frames enqueued with a delay."
    ::= { acdShaperV2QueueStatsEntry 7 }

acdShaperV2QueueStatsCntGreenForwardWithDelayBytes OBJECT-TYPE
    SYNTAX      Counter64
    MAX-ACCESS  read-only
    STATUS      current
    DESCRIPTION
        "Number of bytes of green frames enqueued with a delay."
    ::= { acdShaperV2QueueStatsEntry 8 }

acdShaperV2QueueStatsCntYellowForwardWithDelayFrames OBJECT-TYPE
    SYNTAX      Counter64
    MAX-ACCESS  read-only
    STATUS      current
    DESCRIPTION
        "Number of yellow frames enqueued with a delay."
    ::= { acdShaperV2QueueStatsEntry 9 }

acdShaperV2QueueStatsCntYellowForwardWithDelayBytes OBJECT-TYPE
    SYNTAX      Counter64
    MAX-ACCESS  read-only
    STATUS      current
    DESCRIPTION
        "Number of bytes of yellow frames enqueued with a delay."
    ::= { acdShaperV2QueueStatsEntry 10 }

acdShaperV2QueueStatsCntGreenDiscardFullFrames OBJECT-TYPE
    SYNTAX      Counter64
    MAX-ACCESS  read-only
    STATUS      current
    DESCRIPTION
        "Number of green frames that have been discarded because of tail dropping."
    ::= { acdShaperV2QueueStatsEntry 11 }

acdShaperV2QueueStatsCntGreenDiscardFullBytes OBJECT-TYPE
    SYNTAX      Counter64
    MAX-ACCESS  read-only
    STATUS      current
    DESCRIPTION
        "Number of bytes of green frames that have been discarded because of tail dropping."
    ::= { acdShaperV2QueueStatsEntry 12 }

acdShaperV2QueueStatsCntYellowDiscardFullFrames OBJECT-TYPE
    SYNTAX      Counter64
    MAX-ACCESS  read-only
    STATUS      current
    DESCRIPTION
        "Number of yellow frames that have been discarded because of tail dropping."
    ::= { acdShaperV2QueueStatsEntry 13 }

acdShaperV2QueueStatsCntYellowDiscardFullBytes OBJECT-TYPE
    SYNTAX      Counter64
    MAX-ACCESS  read-only
    STATUS      current
    DESCRIPTION
        "Number of bytes of yellow frames that have been discarded because of tail dropping."
    ::= { acdShaperV2QueueStatsEntry 14 }

acdShaperV2QueueStatsCntGreenDiscardBLUEFrames OBJECT-TYPE
    SYNTAX      Counter64
    MAX-ACCESS  read-only
    STATUS      current
    DESCRIPTION
        "Number of green frames that have been discarded because of the BLUE algorithm."
    ::= { acdShaperV2QueueStatsEntry 15 }

acdShaperV2QueueStatsCntGreenDiscardBLUEBytes OBJECT-TYPE
    SYNTAX      Counter64
    MAX-ACCESS  read-only
    STATUS      current
    DESCRIPTION
        "Number of bytes of green frames that have been discarded because of the BLUE algorithm."
    ::= { acdShaperV2QueueStatsEntry 16 }

acdShaperV2QueueStatsCntYellowDiscardBLUEFrames OBJECT-TYPE
    SYNTAX      Counter64
    MAX-ACCESS  read-only
    STATUS      current
    DESCRIPTION
        "Number of yellow frames that have been discarded because of the BLUE algorithm."
    ::= { acdShaperV2QueueStatsEntry 17 }

acdShaperV2QueueStatsCntYellowDiscardBLUEBytes OBJECT-TYPE
    SYNTAX      Counter64
    MAX-ACCESS  read-only
    STATUS      current
    DESCRIPTION
        "Number of bytes of yellow frames that have been discarded because of the BLUE algorithm."
    ::= { acdShaperV2QueueStatsEntry 18 }

acdShaperV2QueueStatsCntCIRCompliantFrames OBJECT-TYPE
    SYNTAX      Counter64
    MAX-ACCESS  read-only
    STATUS      current
    DESCRIPTION
        "Number of frames dequeued with shaper CIR compliance."
    ::= { acdShaperV2QueueStatsEntry 19 }

acdShaperV2QueueStatsCntCIRCompliantBytes OBJECT-TYPE
    SYNTAX      Counter64
    MAX-ACCESS  read-only
    STATUS      current
    DESCRIPTION
        "Number of bytes dequeued with shaper CIR compliance."
    ::= { acdShaperV2QueueStatsEntry 20 }

acdShaperV2QueueStatsCntEIRCompliantFrames OBJECT-TYPE
    SYNTAX      Counter64
    MAX-ACCESS  read-only
    STATUS      current
    DESCRIPTION
        "Number of frames dequeued with shaper EIR compliance."
    ::= { acdShaperV2QueueStatsEntry 21 }

acdShaperV2QueueStatsCntEIRCompliantBytes OBJECT-TYPE
    SYNTAX      Counter64
    MAX-ACCESS  read-only
    STATUS      current
    DESCRIPTION
        "Number of bytes dequeued with shaper EIR compliance."
    ::= { acdShaperV2QueueStatsEntry 22 }

------------------------------------------------------------------------
 -- Shaper-V2 queue statistics history table.
---------------------------------------------------------------------------

acdShaperV2QueueStatsHistTable OBJECT-TYPE
    SYNTAX      SEQUENCE OF AcdShaperV2QueueStatsHistEntry
    MAX-ACCESS  not-accessible
    STATUS      current
    DESCRIPTION
        "Shaper-V2 queue statistics history table."
    ::= { acdShaperV2MIBObjects 2 }

acdShaperV2QueueStatsHistEntry OBJECT-TYPE
    SYNTAX      AcdShaperV2QueueStatsHistEntry
    MAX-ACCESS  not-accessible
    STATUS      current
    DESCRIPTION
        "Shaper-V2 queue statistics history table entry."
    INDEX   { acdShaperV2QueueStatsHistQueueId, acdShaperV2QueueStatsHistIndex }
    ::=  { acdShaperV2QueueStatsHistTable 1 }

AcdShaperV2QueueStatsHistEntry ::= SEQUENCE {
    acdShaperV2QueueStatsHistIndex                           Unsigned32,
    acdShaperV2QueueStatsHistSamplingEndTime                 DateAndTime,
    acdShaperV2QueueStatsHistQueueId                         Unsigned32,
    acdShaperV2QueueStatsHistQueueName                       DisplayString,
    acdShaperV2QueueStatsHistCntGreenForwardNoDelayFrames    Counter64,
    acdShaperV2QueueStatsHistCntGreenForwardNoDelayBytes     Counter64,
    acdShaperV2QueueStatsHistCntYellowForwardNoDelayFrames   Counter64,
    acdShaperV2QueueStatsHistCntYellowForwardNoDelayBytes    Counter64,
    acdShaperV2QueueStatsHistCntGreenForwardWithDelayFrames  Counter64,
    acdShaperV2QueueStatsHistCntGreenForwardWithDelayBytes   Counter64,
    acdShaperV2QueueStatsHistCntYellowForwardWithDelayFrames Counter64,
    acdShaperV2QueueStatsHistCntYellowForwardWithDelayBytes  Counter64,
    acdShaperV2QueueStatsHistCntGreenDiscardFullFrames       Counter64,
    acdShaperV2QueueStatsHistCntGreenDiscardFullBytes        Counter64,
    acdShaperV2QueueStatsHistCntYellowDiscardFullFrames      Counter64,
    acdShaperV2QueueStatsHistCntYellowDiscardFullBytes       Counter64,
    acdShaperV2QueueStatsHistCntGreenDiscardBLUEFrames       Counter64,
    acdShaperV2QueueStatsHistCntGreenDiscardBLUEBytes        Counter64,
    acdShaperV2QueueStatsHistCntYellowDiscardBLUEFrames      Counter64,
    acdShaperV2QueueStatsHistCntYellowDiscardBLUEBytes       Counter64,
    acdShaperV2QueueStatsHistCntCIRCompliantFrames           Counter64,
    acdShaperV2QueueStatsHistCntCIRCompliantBytes            Counter64,
    acdShaperV2QueueStatsHistCntEIRCompliantFrames           Counter64,
    acdShaperV2QueueStatsHistCntEIRCompliantBytes            Counter64
}

acdShaperV2QueueStatsHistIndex OBJECT-TYPE
    SYNTAX      Unsigned32
    MAX-ACCESS  read-only
    STATUS      current
    DESCRIPTION
        "Index of the queue statistics history table."
    ::= { acdShaperV2QueueStatsHistEntry 1 }

acdShaperV2QueueStatsHistSamplingEndTime OBJECT-TYPE
    SYNTAX      DateAndTime
    MAX-ACCESS  read-only
    STATUS      current
    DESCRIPTION
        "Sampling end time."
    ::= { acdShaperV2QueueStatsHistEntry 2 }

acdShaperV2QueueStatsHistQueueId OBJECT-TYPE
    SYNTAX      Unsigned32
    MAX-ACCESS  read-only
    STATUS      current
    DESCRIPTION
        "Identifier of the queue."
    ::= { acdShaperV2QueueStatsHistEntry 3 }

acdShaperV2QueueStatsHistQueueName OBJECT-TYPE
    SYNTAX      DisplayString (SIZE (1..32))
    MAX-ACCESS  read-only
    STATUS      current
    DESCRIPTION
        "Name of the queue."
    ::= { acdShaperV2QueueStatsHistEntry 4 }

acdShaperV2QueueStatsHistCntGreenForwardNoDelayFrames OBJECT-TYPE
    SYNTAX      Counter64
    MAX-ACCESS  read-only
    STATUS      current
    DESCRIPTION
        "Number of green frames enqueued with no delay."
    ::= { acdShaperV2QueueStatsHistEntry 5 }

acdShaperV2QueueStatsHistCntGreenForwardNoDelayBytes OBJECT-TYPE
    SYNTAX      Counter64
    MAX-ACCESS  read-only
    STATUS      current
    DESCRIPTION
        "Number of bytes of green frames enqueued with no delay."
    ::= { acdShaperV2QueueStatsHistEntry 6 }

acdShaperV2QueueStatsHistCntYellowForwardNoDelayFrames OBJECT-TYPE
    SYNTAX      Counter64
    MAX-ACCESS  read-only
    STATUS      current
    DESCRIPTION
        "Number of yellow frames enqueued with no delay."
    ::= { acdShaperV2QueueStatsHistEntry 7 }

acdShaperV2QueueStatsHistCntYellowForwardNoDelayBytes OBJECT-TYPE
    SYNTAX      Counter64
    MAX-ACCESS  read-only
    STATUS      current
    DESCRIPTION
        "Number of bytes of yellow frames enqueued with no delay."
    ::= { acdShaperV2QueueStatsHistEntry 8 }

acdShaperV2QueueStatsHistCntGreenForwardWithDelayFrames OBJECT-TYPE
    SYNTAX      Counter64
    MAX-ACCESS  read-only
    STATUS      current
    DESCRIPTION
        "Number of green frames enqueued with a delay."
    ::= { acdShaperV2QueueStatsHistEntry 9 }

acdShaperV2QueueStatsHistCntGreenForwardWithDelayBytes OBJECT-TYPE
    SYNTAX      Counter64
    MAX-ACCESS  read-only
    STATUS      current
    DESCRIPTION
        "Number of bytes of green frames enqueued with a delay."
    ::= { acdShaperV2QueueStatsHistEntry 10 }

acdShaperV2QueueStatsHistCntYellowForwardWithDelayFrames OBJECT-TYPE
    SYNTAX      Counter64
    MAX-ACCESS  read-only
    STATUS      current
    DESCRIPTION
        "Number of yellow frames enqueued with a delay."
    ::= { acdShaperV2QueueStatsHistEntry 11 }

acdShaperV2QueueStatsHistCntYellowForwardWithDelayBytes OBJECT-TYPE
    SYNTAX      Counter64
    MAX-ACCESS  read-only
    STATUS      current
    DESCRIPTION
        "Number of bytes of yellow frames enqueued with a delay."
    ::= { acdShaperV2QueueStatsHistEntry 12 }

acdShaperV2QueueStatsHistCntGreenDiscardFullFrames OBJECT-TYPE
    SYNTAX      Counter64
    MAX-ACCESS  read-only
    STATUS      current
    DESCRIPTION
        "Number of green frames that have been discarded because of tail dropping."
    ::= { acdShaperV2QueueStatsHistEntry 13 }

acdShaperV2QueueStatsHistCntGreenDiscardFullBytes OBJECT-TYPE
    SYNTAX      Counter64
    MAX-ACCESS  read-only
    STATUS      current
    DESCRIPTION
        "Number of bytes of green frames that have been discarded because of tail dropping."
    ::= { acdShaperV2QueueStatsHistEntry 14 }

acdShaperV2QueueStatsHistCntYellowDiscardFullFrames OBJECT-TYPE
    SYNTAX      Counter64
    MAX-ACCESS  read-only
    STATUS      current
    DESCRIPTION
        "Number of yellow frames that have been discarded because of tail dropping."
    ::= { acdShaperV2QueueStatsHistEntry 15 }

acdShaperV2QueueStatsHistCntYellowDiscardFullBytes OBJECT-TYPE
    SYNTAX      Counter64
    MAX-ACCESS  read-only
    STATUS      current
    DESCRIPTION
        "Number of bytes of yellow frames that have been discarded because of tail dropping."
    ::= { acdShaperV2QueueStatsHistEntry 16 }

acdShaperV2QueueStatsHistCntGreenDiscardBLUEFrames OBJECT-TYPE
    SYNTAX      Counter64
    MAX-ACCESS  read-only
    STATUS      current
    DESCRIPTION
        "Number of green frames that have been discarded because of the BLUE algorithm."
    ::= { acdShaperV2QueueStatsHistEntry 17 }

acdShaperV2QueueStatsHistCntGreenDiscardBLUEBytes OBJECT-TYPE
    SYNTAX      Counter64
    MAX-ACCESS  read-only
    STATUS      current
    DESCRIPTION
        "Number of bytes of green frames that have been discarded because of the BLUE algorithm."
    ::= { acdShaperV2QueueStatsHistEntry 18 }

acdShaperV2QueueStatsHistCntYellowDiscardBLUEFrames OBJECT-TYPE
    SYNTAX      Counter64
    MAX-ACCESS  read-only
    STATUS      current
    DESCRIPTION
        "Number of yellow frames that have been discarded because of the BLUE algorithm."
    ::= { acdShaperV2QueueStatsHistEntry 19 }

acdShaperV2QueueStatsHistCntYellowDiscardBLUEBytes OBJECT-TYPE
    SYNTAX      Counter64
    MAX-ACCESS  read-only
    STATUS      current
    DESCRIPTION
        "Number of bytes of yellow frames that have been discarded because of the BLUE algorithm."
    ::= { acdShaperV2QueueStatsHistEntry 20 }

acdShaperV2QueueStatsHistCntCIRCompliantFrames OBJECT-TYPE
    SYNTAX      Counter64
    MAX-ACCESS  read-only
    STATUS      current
    DESCRIPTION
        "Number of frames dequeued with shaper CIR compliance."
    ::= { acdShaperV2QueueStatsHistEntry 21 }

acdShaperV2QueueStatsHistCntCIRCompliantBytes OBJECT-TYPE
    SYNTAX      Counter64
    MAX-ACCESS  read-only
    STATUS      current
    DESCRIPTION
        "Number of bytes dequeued with shaper CIR compliance."
    ::= { acdShaperV2QueueStatsHistEntry 22 }

acdShaperV2QueueStatsHistCntEIRCompliantFrames OBJECT-TYPE
    SYNTAX      Counter64
    MAX-ACCESS  read-only
    STATUS      current
    DESCRIPTION
        "Number of frames dequeued with shaper EIR compliance."
    ::= { acdShaperV2QueueStatsHistEntry 23 }

acdShaperV2QueueStatsHistCntEIRCompliantBytes OBJECT-TYPE
    SYNTAX      Counter64
    MAX-ACCESS  read-only
    STATUS      current
    DESCRIPTION
        "Number of bytes dequeued with shaper EIR compliance."
    ::= { acdShaperV2QueueStatsHistEntry 24 }

---------------------------------------------------------------------------
 -- ACD-SHAPER-V2-MIB Module - Conformance Information
---------------------------------------------------------------------------

acdShaperV2Compliances OBJECT IDENTIFIER ::= { acdShaperV2Conformance 1 }
acdShaperV2Groups      OBJECT IDENTIFIER ::= { acdShaperV2Conformance 2 }

---------------------------------------------------------------------------
 -- Units of Conformance
---------------------------------------------------------------------------

acdShaperV2QueueStatsGroup OBJECT-GROUP
    OBJECTS {
        acdShaperV2QueueStatsQueueName,
        acdShaperV2QueueStatsCntGreenForwardNoDelayFrames,
        acdShaperV2QueueStatsCntGreenForwardNoDelayBytes,
        acdShaperV2QueueStatsCntYellowForwardNoDelayFrames,
        acdShaperV2QueueStatsCntYellowForwardNoDelayBytes,
        acdShaperV2QueueStatsCntGreenForwardWithDelayFrames,
        acdShaperV2QueueStatsCntGreenForwardWithDelayBytes,
        acdShaperV2QueueStatsCntYellowForwardWithDelayFrames,
        acdShaperV2QueueStatsCntYellowForwardWithDelayBytes,
        acdShaperV2QueueStatsCntGreenDiscardFullFrames,
        acdShaperV2QueueStatsCntGreenDiscardFullBytes,
        acdShaperV2QueueStatsCntYellowDiscardFullFrames,
        acdShaperV2QueueStatsCntYellowDiscardFullBytes,
        acdShaperV2QueueStatsCntGreenDiscardBLUEFrames,
        acdShaperV2QueueStatsCntGreenDiscardBLUEBytes,
        acdShaperV2QueueStatsCntYellowDiscardBLUEFrames,
        acdShaperV2QueueStatsCntYellowDiscardBLUEBytes,
        acdShaperV2QueueStatsCntCIRCompliantFrames,
        acdShaperV2QueueStatsCntCIRCompliantBytes,
        acdShaperV2QueueStatsCntEIRCompliantFrames,
        acdShaperV2QueueStatsCntEIRCompliantBytes
    }
    STATUS      current
    DESCRIPTION
       "Objects for the Shaper-V2 queue statistics group."
    ::= { acdShaperV2Groups 1 }

acdShaperV2QueueStatsHistGroup OBJECT-GROUP
    OBJECTS {
        acdShaperV2QueueStatsHistIndex,
        acdShaperV2QueueStatsHistSamplingEndTime,
        acdShaperV2QueueStatsHistQueueId,
        acdShaperV2QueueStatsHistQueueName,
        acdShaperV2QueueStatsHistCntGreenForwardNoDelayFrames,
        acdShaperV2QueueStatsHistCntGreenForwardNoDelayBytes,
        acdShaperV2QueueStatsHistCntYellowForwardNoDelayFrames,
        acdShaperV2QueueStatsHistCntYellowForwardNoDelayBytes,
        acdShaperV2QueueStatsHistCntGreenForwardWithDelayFrames,
        acdShaperV2QueueStatsHistCntGreenForwardWithDelayBytes,
        acdShaperV2QueueStatsHistCntYellowForwardWithDelayFrames,
        acdShaperV2QueueStatsHistCntYellowForwardWithDelayBytes,
        acdShaperV2QueueStatsHistCntGreenDiscardFullFrames,
        acdShaperV2QueueStatsHistCntGreenDiscardFullBytes,
        acdShaperV2QueueStatsHistCntYellowDiscardFullFrames,
        acdShaperV2QueueStatsHistCntYellowDiscardFullBytes,
        acdShaperV2QueueStatsHistCntGreenDiscardBLUEFrames,
        acdShaperV2QueueStatsHistCntGreenDiscardBLUEBytes,
        acdShaperV2QueueStatsHistCntYellowDiscardBLUEFrames,
        acdShaperV2QueueStatsHistCntYellowDiscardBLUEBytes,
        acdShaperV2QueueStatsHistCntCIRCompliantFrames,
        acdShaperV2QueueStatsHistCntCIRCompliantBytes,
        acdShaperV2QueueStatsHistCntEIRCompliantFrames,
        acdShaperV2QueueStatsHistCntEIRCompliantBytes
    }
    STATUS      current
    DESCRIPTION
       "Objects for the Shaper-V2 queue statistics history group."
    ::= { acdShaperV2Groups 2 }

acdShaperV2Compliance MODULE-COMPLIANCE
    STATUS      current
    DESCRIPTION
       "The compliance statement for support of the ACD-SHAPER-V2-MIB module."
    MODULE
        MANDATORY-GROUPS {
            acdShaperV2QueueStatsGroup,
            acdShaperV2QueueStatsHistGroup
        }
    ::= { acdShaperV2Compliances 1 }

END
