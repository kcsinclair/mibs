-- orig XDSL_MIB

XDSL-MIB DEFINITIONS ::= BEGIN

IMPORTS
        
        NetworkTimeInSeconds
                FROM ASAM-TC-MIB

        Counter, 
        TimeTicks, 
        Gauge
                FROM RFC1155-SMI

        OBJECT-TYPE
                FROM RFC-1212
                
        ifIndex
                FROM IF-MIB

        RowStatus,
        TruthValue
                FROM SNMPv2-TC

        asam
                FROM SYSTEM-MIB

        AsamNextProfileIndex, 
        AsamMaxProfileIndex, 
        AsamProfileIndex,
        AsamProfilePointer, 
        AsamProfileName, 
        AsamProfileScope,
        AsamProfileRefCount
                FROM ASAM-TC-MIB

        DisplayString
                FROM RFC1213-MIB

        eqptSlotId
                FROM ASAM-EQUIP-MIB;

xdslMIB                          OBJECT IDENTIFIER ::= { asam 39 }

xdslLine                         OBJECT IDENTIFIER ::= { xdslMIB 3 }

xdslFarEndLine                   OBJECT IDENTIFIER ::= { xdslMIB 4 }

xdslChannel                      OBJECT IDENTIFIER ::= { xdslMIB 5 }

xdslFarEndChannel                OBJECT IDENTIFIER ::= { xdslMIB 6 }

xdslTest                         OBJECT IDENTIFIER ::= { xdslMIB 7 }

xdslXturInventory                OBJECT IDENTIFIER ::= { xdslMIB 8 }

xdslXtucInventory                OBJECT IDENTIFIER ::= { xdslMIB 9 }

xdslLineTcaThreshold             OBJECT IDENTIFIER ::= { xdslMIB 10 }

xdslChannelTcaThreshold          OBJECT IDENTIFIER ::= { xdslMIB 11 }

xdslLinkUp                       OBJECT IDENTIFIER ::= { xdslMIB 12 }

xdslDpboProfile                  OBJECT IDENTIFIER ::= { xdslMIB 13 }

xdslBoard                        OBJECT IDENTIFIER ::= { xdslMIB 14 }

xdslLineOverruleData             OBJECT IDENTIFIER ::= { xdslMIB 15 }

xdslError                        OBJECT IDENTIFIER ::= { xdslMIB 16 }

xdslRtxProfile                   OBJECT IDENTIFIER ::= { xdslMIB 17 }

xdslLineServiceProfile           OBJECT IDENTIFIER ::= { xdslLine 3 }

xdslLineSpectrumProfile          OBJECT IDENTIFIER ::= { xdslLine 6 }

xdslLineCurrent                  OBJECT IDENTIFIER ::= { xdslLine 8 }

xdslLinePrevious                 OBJECT IDENTIFIER ::= { xdslLine 9 }

xdslLineDfltProfiles             OBJECT IDENTIFIER ::= { xdslLine 11 }

xdslFarEndLineCurrent            OBJECT IDENTIFIER ::= { xdslFarEndLine 1 }

xdslFarEndLinePrevious           OBJECT IDENTIFIER ::= { xdslFarEndLine 2 }

xdslChannelCurrent               OBJECT IDENTIFIER ::= { xdslChannel 1 }

xdslChannelPrevious              OBJECT IDENTIFIER ::= { xdslChannel 2 }

xdslFarEndChannelCurrent         OBJECT IDENTIFIER ::= { xdslFarEndChannel 1 }

xdslFarEndChannelPrevious        OBJECT IDENTIFIER ::= { xdslFarEndChannel 2 }

xdslTestTypes                    OBJECT IDENTIFIER ::= { xdslTest 1 }

xdslTestCodes                    OBJECT IDENTIFIER ::= { xdslTest 2 }

XdslRAModeType ::=           INTEGER {
                                 operatorControlledRateAdaptive(1),
                                 automaticRateAdaptiveAtStartup(2),
                                 dynamicRateAdaptive(3)
                                        }
XdslActualRAModeType ::=     INTEGER {
                                 operatorControlledRateAdaptive (1),
                                 automaticRateAdaptiveAtStartup (2),
                                 dynamicRateAdaptive            (3),
                                 unknownNotSupported            (255)
                                        }

SplitterOptimizationType ::= INTEGER {
                                 pots      (1),
                                 isdn      (2)
                                 } 

OpModeType ::=               OCTET STRING (SIZE (16))

TpsTcModeType ::=            INTEGER {
                                 atm        (1),
                                 ptm        (2),
                                 default    (3)
                                 }

CarrierSpacingType ::=       INTEGER {
                                 singleCarrierSpacing(1),
                                 doubleCarrierSpacing(2),
                                 halfCarrierSpacing(3),
                                 quarterCarrierSpacing(4)
                                 }

SubCarrierGroupSizeType ::= INTEGER (1..8) 

FrequencyType ::=            INTEGER(0..30000)

VdslBandPlanType ::=         INTEGER {
                                 bandPlanCustom   (1),
                                 bandPlanA4       (2),
                                 bandPlanA3       (3),
                                 bandPlanA2       (4),
                                 bandPlanB4       (5),
                                 bandPlanB3       (6),
                                 bandPlanB2       (7),
                                 bandPlanC4       (8),
                                 bandPlanC3       (9),
                                 bandPlanC2      (10),
                                 bandPlanChinaA3 (11), 
                                 bandPlanChinaA2 (12),
                                 bandPlanChinaB3 (13),
                                 bandPlanChinaB2 (14),
                                 bandPlanAU2ext  (15),
                                 bandPlanAnnexA998 (16),
                                 bandPlanAnnexB997e (17),
                                 bandPlanAnnexB998e (18),      
                                 bandPlanAnnexB998ade (19), 
                                 bandPlanAnnexBhpe (20),    
                                 bandPlanAnnexC (21)             
                                 }

OptBandUsageType ::=         INTEGER {
                                 optBandOff(1),
                                 optBandUpstream(2),
                                 optBandDownstream(3)
                                 }

AdslPsdDownstreamType ::=    INTEGER {
                                 adslCustomPsdDownstream(1),
                                 adslStdPsdDownstream (2)
                                 }

AdslPsdUpstreamType ::=      INTEGER {
                                 adslCustomPsdUpstream(1),
                                 adslStdPsdUpstream (2),
                                 adslPsdMask32Upstream(3),
                                 adslPsdMask36Upstream(4),
                                 adslPsdMask40Upstream(5),
                                 adslPsdMask44Upstream(6),
                                 adslPsdMask48Upstream(7),
                                 adslPsdMask52Upstream(8),
                                 adslPsdMask56Upstream(9),
                                 adslPsdMask60Upstream(10),
                                 adslPsdMask64Upstream(11)
                                 }
ReAdsl2PsdDownstreamType ::= INTEGER {
                                 reAdsl2CustomPsdDownstream(1),
                                 reAdsl2StdPsdDownstream (2)
                                 }

ReAdsl2PsdUpstreamType ::=   INTEGER {
                                 reAdsl2CustomPsdUpstream(1),
                                 reAdsl2StdPsdUpstream (2)
                                 }

Adsl2PlusPsdDownstreamType ::= INTEGER {
                                 adsl2PlusCustomPsdDownstream(1),
                                 adsl2PlusStdPsdDownstream (2),
                                 adsl2PlusCa100PsdDownstream (3),
                                 adsl2PlusCa110PsdDownstream (4),
                                 adsl2PlusCa120PsdDownstream (5),
                                 adsl2PlusCa130PsdDownstream (6),
                                 adsl2PlusCa140PsdDownstream (7),
                                 adsl2PlusCa150PsdDownstream (8),
                                 adsl2PlusCa160PsdDownstream (9),
                                 adsl2PlusCa170PsdDownstream (10),
                                 adsl2PlusCa180PsdDownstream (11),
                                 adsl2PlusCa190PsdDownstream (12),
                                 adsl2PlusCa200PsdDownstream (13),
                                 adsl2PlusCa210PsdDownstream (14),
                                 adsl2PlusCa220PsdDownstream (15),
                                 adsl2PlusCa230PsdDownstream (16),
                                 adsl2PlusCa240PsdDownstream (17),
                                 adsl2PlusCa250PsdDownstream (18),
                                 adsl2PlusCa260PsdDownstream (19),
                                 adsl2PlusCa270PsdDownstream (20),
                                 adsl2PlusCa280PsdDownstream (21)
                                 }

Adsl2PlusPsdUpstreamType ::= INTEGER {
                                 adsl2PlusCustomPsdUpstream(1),
                                 adsl2PlusStdPsdUpstream (2),
                                 adsl2PlusPsdMask32Upstream (3),
                                 adsl2PlusPsdMask36Upstream (4),
                                 adsl2PlusPsdMask40Upstream (5),
                                 adsl2PlusPsdMask44Upstream (6),
                                 adsl2PlusPsdMask48Upstream (7),
                                 adsl2PlusPsdMask52Upstream (8),
                                 adsl2PlusPsdMask56Upstream (9),
                                 adsl2PlusPsdMask60Upstream (10),
                                 adsl2PlusPsdMask64Upstream (11)
                                 }

VdslPsdDownstreamType ::=    INTEGER {
                                 vdslCustomPsdDownstream(1),
                                 vdslAnsiFttexM1PsdDownstream(2),
                                 vdslAnsiFttexM2PsdDownstream(3),
                                 vdslAnsiFttcabM1PsdDownstream(4),
                                 vdslAnsiFttcabM2PsdDownstream(5),
                                 vdslEtsiPexP1M1PsdDownstream(6),
                                 vdslEtsiPexP1M2PsdDownstream(7),
                                 vdslEtsiPexP2M1PsdDownstream(8),
                                 vdslEtsiPexP2M2PsdDownstream(9),
                                 vdslEtsiPcabM1PsdDownstream(10),
                                 vdslEtsiPcabM2PsdDownstream(11),
                                 vdslAnsiFttCabM1AdslPsdDownstream(12),
                                 vdslAnsiFttCabM2AdslPsdDownstream(13),
                                 vdslAnsiFttCabM1Adsl2PlusPsdDownstream(14),
                                 vdslAnsiFttCabM2Adsl2PlusPsdDownstream(15),
                                 vdslEtsiPcabXM1AdslPsdDownstream(16),
                                 vdslEtsiPcabXM2AdslPsdDownstream(17),
                                 vdslEtsiPcabM1Adsl2PlusPsdDownstream(18),
                                 vdslEtsiPcabM2Adsl2PlusPsdDownstream(19),
                                 vdslEtsiPexM2AdslSample1PsdDownstream(20),
                                 vdslEtsiPexM2AdslSample2PsdDownstream(21),
                                 vdslEtsiPexM2AdslSample3PsdDownstream(22),
                                 vdslEtsiPexM2AdslSample4PsdDownstream(23)
                                }

VdslPsdUpstreamType ::=      INTEGER {
                                 vdslCustomPsdUpstream(1),
                                 vdslAnsiFttexM1PsdUpstream(2),
                                 vdslAnsiFttexM2PsdUpstream(3),
                                 vdslAnsiFttcabM1PsdUpstream(4),
                                 vdslAnsiFttcabM2PsdUpstream(5),
                                 vdslEtsiPM1PsdUpstream(6),
                                 vdslEtsiPM2PsdUpstream(7)
                                 }

VdslRxPsdUpstreamType ::=    INTEGER {
                                 vdslCustomRxPsdUpstream(1),
                                 vdslAnsiARxPsdUpstream(2),
                                 vdslAnsiFRxPsdUpstream(3),
                                 vdslAnsiCustomExRxPsdUpstream(4),
                                 vdslAnsiCustomCabRxPsdUpstream(5),
                                 vdslEtsiARxPsdUpstream(6),
                                 vdslEtsiBRxPsdUpstream(7),
                                 vdslEtsiCRxPsdUpstream(8),
                                 vdslEtsiDRxPsdUpstream(9),
                                 vdslEtsiERxPsdUpstream(10),
                                 vdslEtsiFRxPsdUpstream(11),
                                 vdslEtsiCustomExRxPsdUpstream(12),
                                 vdslEtsiCustomCabRxPsdUpstream(13),
                                 vdslABParamRxPsdUpstream(14),
                                 vdslEqualFextRxPsdUpstream(15)
                                 }

Vdsl2PsdUpstreamType ::=     INTEGER {
                                 vdsl2CustomPsdUpstream(1),
                                 vdsl2RegionAPsdUpstream(2),
                                 vdsl2RegionBM1PsdUpstream(3),
                                 vdsl2RegionBM2PsdUpstream(4),
                                 vdsl2RegionCPsdUpstream(5)
                                 }

Vdsl2PsdDownstreamType ::=   INTEGER {
                                 vdsl2CustomPsdDownstream(1),
                                 vdsl2RegionAPsdDownstream(2),
                                 vdsl2RegionBM1PsdDownstream(3),
                                 vdsl2RegionBM2PsdDownstream(4),
                                 vdsl2RegionCPsdDownstream(5)
                                 }

SnrmMode ::=                 INTEGER {
                                 snrmMode1(1),
                                 snrmMode2(2),
                                 snrmMode3(3)
                                 }

CustomPsdShapeType ::=       OCTET STRING (SIZE (0..97))

VirtualNoisePsdDownType ::=  OCTET STRING (SIZE (0..97))

VirtualNoisePsdUpType ::=    OCTET STRING (SIZE (0..49))

ExchangePsdShapeType ::=     OCTET STRING (SIZE (0..65))

DpboCustomPsdShapeType ::=   OCTET STRING (SIZE (0..129))

PerBandABParamType  ::=      OCTET STRING (SIZE (10))

PerBandOperDataType ::=      OCTET STRING (SIZE (10))

PerBandEqualFextParamType ::= OCTET STRING (SIZE (10))

PboModeType ::=              INTEGER {
                                 pboModeOff(1),
                                 pboModeOn(2),
                                 pboModeOnPolicingShutdown(3),
                                 pboModeOnPolicingUS0Only(4),
                                 pbomodeOnPolicingPassive(5)
                                 }

BondingModeType ::=          INTEGER {
                                 native(1),
                                 atmBonding(2)
                                 }

ArtificialNoisePsdDownType ::=  OCTET STRING (SIZE (0..97))

NoisePsdDownType ::=  OCTET STRING (SIZE (0..97))

NoisePsdUpType ::=  OCTET STRING (SIZE (0..49))

IatHistogramType ::=         OCTET STRING (SIZE (16))

EquivInpHistogramType ::=    OCTET STRING (SIZE (34))

EventTraceType ::=           OCTET STRING (SIZE (0..150))

SeltTxSignPsdType ::= INTEGER {
                txSignPsdTypeDefault                    (1), 
                txSignPsdTypeFromConfig                 (2), 
                txSignPsdTypeFromConfigVdsl2            (3),
                txSignPsdTypeFromConfigVdsl1            (4),
                txSignPsdTypeFromConfigAdsl1or2         (5),
                txSignPsdTypeFromConfigAdsl2Plus        (6),
                txSignPsdTypePreDefVdsl2                (7),
                txSignPsdTypePreDefVdsl1                (8),
                txSignPsdTypePreDefAllBandsVdsl2        (9),
                txSignPsdTypePreDefAllBandsAdsl1       (10),
                txSignPsdTypePreDefAllBandsAdsl2Plus   (11),
                txSignPsdTypePreDefVdsl2RegionA        (12),
                txSignPsdTypeFrom8dConfig              (13),
                txSignPsdTypeFrom8dConfigVdsl2         (14)
}

SeltSelectedPsdType ::= INTEGER {
                selectedPsdTypeConfigVdsl2              (1), 
                selectedPsdTypeConfigVdsl1              (2), 
                selectedPsdTypeConfigAdsl1or2           (3),
                selectedPsdTypeConfigAdsl2Plus          (4),
                selectedPsdTypeConfigReAdsl2            (5),
                selectedPsdTypePreDefVdsl2              (6),
                selectedPsdTypePreDefVdsl1              (7),
                selectedPsdTypePreDefAllBandsVdsl2      (8),
                selectedPsdTypePreDefAllBandsAdsl1      (9),
                selectedPsdTypePreDefAllBandsAdsl2Plus (10),
                selectedPsdTypePreDefVdsl2RegionA      (11),
                selectedPsdType8dConfigVdsl2           (12),
                selectedPsdTypeUnknownNotSupported     (255)
}

SeltCarrierSpacingType ::=  INTEGER {
                                 singleCarrierSpacing   (1),
                                 doubleCarrierSpacing   (2),
                                 unknownNotSupported  (255)
                                 }

RtxMode ::=  INTEGER {
                       rtxForbidden  (1),
                       rtxPreferred  (2),
                       rtxForced     (3),
                       rtxTestmode   (4),
                       rtxNoOverrule (255)
                     }

ActualRtxMode ::=     INTEGER {
                                 rtxInUse                           (1),
                                 rtxNotInUseForbidden               (2),
                                 rtxNotInUseNotSupportedXtuC        (3),
                                 rtxNotInUseNotSupportedXtuR        (4),
                                 rtxNotInUseNotSupportedXtuCandXtuR (5),
                                 rtxNotInUseNotSelectedButSupported (6),
                                 unknownNotSupported                (255)
                              }

xdslCoding              OBJECT-TYPE
        SYNTAX          INTEGER {
                                 xdslCodingOther(1),
                                 adslCodingDMT(2),
                                 xdslCodingCAP(3)
                                }
        ACCESS          read-only
        STATUS          mandatory
        DESCRIPTION 
        "This object describes the type of modulation technique in use for the 
         system.

         ALCATEL NOTE:
             ACCESS:   NA                  USAGE:    NA
             PERSIST:  NO                  INSRVMOD: NA
             RANGE:    adslCodingDMT       DEFVALUE: adslCodingDMT
             UNITS:    NA                  SPARSE:   NA
             DESCR:    NA "
::= {xdslMIB 1}
        
xdslPerfInfoTable       OBJECT-TYPE 
        SYNTAX          SEQUENCE OF XdslPerfInfoEntry
        ACCESS          not-accessible
        STATUS          mandatory
        DESCRIPTION     
        "The performance information table.

         ALCATEL NOTE:
             TABLESIZE: DEP [number of XDSL lines and number of XDSL channels]                    
             DESCR:     NA                   "
::= {xdslMIB 2}

xdslPerfInfoEntry       OBJECT-TYPE
        SYNTAX          XdslPerfInfoEntry
        ACCESS          not-accessible
        STATUS          mandatory
        DESCRIPTION     
        "An entry in the XDSL PerfInfo table.

         Row creation : Entries for all XDSL lines and all XDSL channels belonging
                        to a board are created when the board becomes operational.
         Row deletion : Entries for all XDSL lines and all XDSL channels belonging
                        to a board are deleted when the board becomes unavailable. "
        INDEX          {ifIndex}
::= {xdslPerfInfoTable 1}

XdslPerfInfoEntry ::=
        SEQUENCE {
            xdslPerfCurrentIntervalTimeElapsed        INTEGER,
            xdslPerfCurrent1DayTimeElapsed            INTEGER,
            xdslPerfValidIntervals                    INTEGER,
            xdslPerfValid1Days                        INTEGER
        }

xdslPerfCurrentIntervalTimeElapsed     OBJECT-TYPE
        SYNTAX          INTEGER (1..900)
        ACCESS          read-only
        STATUS          mandatory
        DESCRIPTION     
        "The number of seconds, including partial seconds, that have elapsed 
         since the beginning of the current interval error-measurement period.

         ALCATEL NOTE:
             ACCESS:   NA                  USAGE:    NA
             PERSIST:  NO                  INSRVMOD: NA
             RANGE:    NA                  DEFVALUE: 0
             UNITS:    seconds             SPARSE:   NA
             DESCR:    NA "
::= {xdslPerfInfoEntry 1}

xdslPerfCurrent1DayTimeElapsed         OBJECT-TYPE
        SYNTAX          INTEGER (1..86400)
        ACCESS          read-only
        STATUS          mandatory
        DESCRIPTION     
        "The number of seconds, including partial seconds,bthat have elapsed 
         since the beginning of the current 1 day error-measurement period.

         ALCATEL NOTE:
             ACCESS:   NA                  USAGE:    NA
             PERSIST:  NO                  INSRVMOD: NA
             RANGE:    NA                  DEFVALUE: 0
             UNITS:    seconds             SPARSE:   NA
             DESCR:    NA "
::= {xdslPerfInfoEntry 2}

xdslPerfValidIntervals                 OBJECT-TYPE  
        SYNTAX          INTEGER (0..192)
        ACCESS          read-only
        STATUS          mandatory
        DESCRIPTION 
        "The number of previous intervals for which valid data has been stored.
         An XDSL device must support at least n intervals. 
         The minimum value of n is 4, the default value of n is 32 and the 
         maximum value of n is 192. 
         The value of this object will be n unless the device was brought 
         online within the last nx15  minutes, in which case the value will be 
         the number of complete 15 minute intervals the device has been online.

         ALCATEL NOTE:
             ACCESS:   NA                  USAGE:    NA
             PERSIST:  NO                  INSRVMOD: NA
             RANGE:    NA                  DEFVALUE: 0
             UNITS:    NA                  SPARSE:   NA
             DESCR:    NA "
::= {xdslPerfInfoEntry 3}

xdslPerfValid1Days      OBJECT-TYPE
        SYNTAX          INTEGER (0..7)
        ACCESS          read-only
        STATUS          mandatory
        DESCRIPTION 
        "The number of previous 1Days for which valid data has been stored. 
         An XDSL device must support at least n days. The minimum value of n is
         1, the default value of n is 1 and the maximum value of n is 7. 
         The value of this object will be n unless the device was brought 
         online within the last nx24  hours, in which case the value will be 
         the number of complete days the device has been online.

         ALCATEL NOTE:
             ACCESS:   NA                  USAGE:    NA
             PERSIST:  NO                  INSRVMOD: NA
             RANGE:    0..1                DEFVALUE: 0
             UNITS:    NA                  SPARSE:   NA
             DESCR:    NA "
::= {xdslPerfInfoEntry 4}

xdslLineServiceProfileIndexNext        OBJECT-TYPE
        SYNTAX          AsamNextProfileIndex
        ACCESS          read-only
        STATUS          mandatory
        DESCRIPTION     
        "This object contains an appropriate value to be used for 
         xdslLineServiceProfileIndex when creating entries in the
         xdslLineServiceProfileTable. 
         The value 0 indicates that no unassigned entries are available. To 
         obtain the xdslLineNextServiceProfileIndex value for a new entry, the
         manager issues a management protocol retrieval operation to obtain the
         current value of this object.  After each retrieval, the agent should
         modify the value to the next unassigned index.

         ALCATEL NOTE:
             ACCESS:   NA                  USAGE:    NA
             PERSIST:  NO                  INSRVMOD: NA
             RANGE:    0..256              DEFVALUE: 1
             UNITS:    NA                  SPARSE:   NA
             DESCR:    NA "
::= {xdslLine 1}

xdslLineServiceProfileMaxIndex         OBJECT-TYPE
        SYNTAX          AsamMaxProfileIndex
        ACCESS          read-only
        STATUS          mandatory
        DESCRIPTION
        "This object represents the maximum number of xdslLineServiceProfiles
         that can be created. The object xdslLineServiceProfileIndexNext will 
         have values ranging from 0 to the value represented by this object.

         ALCATEL NOTE:
             ACCESS:   NA                  USAGE:    NA
             PERSIST:  NO                  INSRVMOD: NA
             RANGE:    256..256            DEFVALUE: 256
             UNITS:    NA                  SPARSE:   NA
             DESCR:    NA "
::= {xdslLine 2}

xdslLineServiceProfileTable            OBJECT-TYPE
        SYNTAX          SEQUENCE OF XdslLineServiceProfileEntry
        ACCESS          not-accessible
        STATUS          mandatory
        DESCRIPTION     
        "This table contains the service related parameters of the modem
         configuration. One entry in this table reflects a profile which can
         be used to configure the modem for a physical line.

         ALCATEL NOTE:
             TABLESIZE: 256                    
             DESCR:     NA                   "
::= {xdslLineServiceProfile 1}

xdslLineServiceProfileEntry            OBJECT-TYPE
        SYNTAX          XdslLineServiceProfileEntry
        ACCESS          not-accessible
        STATUS          mandatory
        DESCRIPTION     
        "Each entry consists of a list of service related parameters that serve 
         to configure an XDSL modem. A profile can be created in one step with
         all necessary parameter values and xdslLineServiceProfileRowStatus set
         to createAndGo.
         It can also be created in several steps by specifying values of a few
         objects in each step. The xdslLineServiceProfileRowStatus is set to
         createAndWait in the first step and to Active in the last step.

         Row creation : An entry is created when the manager requests to create
                        a service profile.
         Row deletion : An entry is deleted when the manager requests to delete
                        a service profile. "
        INDEX          {xdslLineServiceProfileIndex}
::= {xdslLineServiceProfileTable 1}

XdslLineServiceProfileEntry ::=
        SEQUENCE {
            xdslLineServiceProfileIndex               AsamProfileIndex,
            xdslLineServiceProfileName                AsamProfileName,
            xdslLineServiceProfileScope               AsamProfileScope,
            xdslLineServiceProfileVersionNbr          INTEGER,
            xdslLineServiceProfileUsedStatus          AsamProfileRefCount,
            xdslLineRAModeDownstream                  XdslRAModeType,
            xdslLineRAModeUpstream                    XdslRAModeType,
            xdslLineNumberChannels                    INTEGER,
            xdslLineServiceProfileRowStatus           RowStatus
        }

xdslLineServiceProfileIndex            OBJECT-TYPE
        SYNTAX          AsamProfileIndex
        ACCESS          not-accessible
        STATUS          mandatory
        DESCRIPTION     
        "This object is used to uniquely identify an entry in this table.
         It is used by the line configuration table to identify a row of this
         table. The max value of this object is limited to
         xdslLineServiceProfileMaxIndex value.

         ALCATEL NOTE:
             ACCESS:   NA                  USAGE:    NA
             PERSIST:  YES                 INSRVMOD: NA
             RANGE:    1..256              DEFVALUE: NA
             UNITS:    NA                  SPARSE:   NA
             DESCR:    NA "
::= {xdslLineServiceProfileEntry 1}

xdslLineServiceProfileName             OBJECT-TYPE
        SYNTAX          AsamProfileName
        ACCESS          read-write
        STATUS          mandatory
        DESCRIPTION     
        "A textual name identifying this profile. This name has to be unique
         within the assigned scope.

         ALCATEL NOTE:
             ACCESS:   NA                  USAGE:    MAND 
             PERSIST:  YES                 INSRVMOD: YES
             RANGE:    NA                  DEFVALUE: NA
             UNITS:    characters          SPARSE:   NA
             DESCR:    NA "
::= {xdslLineServiceProfileEntry 2}

xdslLineServiceProfileScope            OBJECT-TYPE
        SYNTAX          AsamProfileScope
        ACCESS          read-write
        STATUS          mandatory
        DESCRIPTION     
        "A profile can be qualified as having a local scope or a network wide 
         scope. As some managers may not support the network profile scope,
         the use of local scope is strongly recommended.

         ALCATEL NOTE:
             ACCESS:   NA                  USAGE:    OPT 
             PERSIST:  YES                 INSRVMOD: YES
             RANGE:    NA                  DEFVALUE: NA
             UNITS:    NA                  SPARSE:   NA
             DESCR:    NA "
        DEFVAL          {localScope}
::= {xdslLineServiceProfileEntry 3}

xdslLineServiceProfileVersionNbr       OBJECT-TYPE
        SYNTAX          INTEGER
        ACCESS          read-write
        STATUS          mandatory
        DESCRIPTION     
        "The manager can associate a version number to the profile. It is set 
         to 1 when the profile is first created and will be incremented by the
         manager when the profile is modified.

         ALCATEL NOTE:
             ACCESS:   NA                  USAGE:    OPT 
             PERSIST:  YES                 INSRVMOD: NO
             RANGE:    NA                  DEFVALUE: NA
             UNITS:    NA                  SPARSE:   NA
             DESCR:    NA "
        DEFVAL          {1}
::= {xdslLineServiceProfileEntry 4}

xdslLineServiceProfileUsedStatus       OBJECT-TYPE
        SYNTAX          AsamProfileRefCount
        ACCESS          read-only
        STATUS          mandatory
        DESCRIPTION
        "Indicates the number of entities using this profile. If the reference
         count is greater than 0, then this profile is 'in use', and may NOT be
         deleted. If the value is 0, then this profile is 'not in use', and can
         be deleted.  
       
         ALCATEL NOTE:
             ACCESS:   NA                  USAGE:    NA
             PERSIST:  NO                  INSRVMOD: NA
             RANGE:    NA                  DEFVALUE: 0
             UNITS:    NA                  SPARSE:   NA
             DESCR:    NA "
::= {xdslLineServiceProfileEntry 5}

xdslLineRAModeDownstream               OBJECT-TYPE
        SYNTAX          XdslRAModeType
        ACCESS          read-write
        STATUS          mandatory
        DESCRIPTION     
        "This object specifies the mode for rate adaptation for the downstream 
         direction: 

         operatorControlledRateAdaptive(1): 
         The object xdslPlannedBitrateDownstream specifies the bitrate the 
         modem must operate at for the corresponding bearer channel in the
         downstream direction, with a noise margin which is larger or equal to
         the specified Target Noise Margin. If the modem fails to achieve 
         this bitrate, it will reinitialize. Although the modem and the line
         might be able to support a higher bitrate, the modem will not transmit
         at a higher rate  than what is requested.
         The modem will maintain the specified planned bitrate during showtime.
         
         automaticRateAdaptiveAtStartup(2) :     
         The object xdslMinBitrateDownstream specifies the minimum data rate 
         the modem must operate at in the downstream direction, with a noise
         margin which is larger or equal to the specified Target Noise Margin.
         If it fails to achieve this bitrate the modem will reinitialize.
         As long as the data rate is below the maximum bitrate, bitrate
         increase has priority over transmit power reduction. The modem is not
         allowed to set up a data rate that is higher than the specified
         maximum data rate. The xdslLineRARatioDownstream object specifies how
         bitrate in excess of the minimum bitrate must be allocated among
         multiple channels. 
         During showtime no rate adaptation is allowed. 

         dynamicRateAdaptive(3):
         In this mode, the data rate is automatically selected at startup (as
         in mode 2), but during showtime, rate adaptation is allowed. The
         downstream data rate can vary between the downstream minimum data rate
         and the downstream maximum data rate. Downstream Rate Adaptation is
         performed when the conditions specified for Downstream Upshift Noise
         Margin and Downstream Upshift Interval - or for Downstream Downshift
         Noise Margin and Downstream Downshift Interval - are satisfied.

         ALCATEL NOTE:
             ACCESS:   NA                  USAGE:    OPT
             PERSIST:  YES                 INSRVMOD: NO
             RANGE:    NA                  DEFVALUE: NA
             UNITS:    NA                  SPARSE:   NA
             DESCR:    NA "
        DEFVAL          {automaticRateAdaptiveAtStartup}           
    ::= {xdslLineServiceProfileEntry 6}

xdslLineRAModeUpstream  OBJECT-TYPE
        SYNTAX          XdslRAModeType
        ACCESS          read-write
        STATUS          mandatory
        DESCRIPTION     
        "This object specifies the mode for rate adaptation for the upstream 
         directions:

         operatorControlledRateAdaptive(1): 
         The object xdslPlannedBitrateUpstream specifies the bitrate the 
         modem must operate at for the corresponding bearer channel in the
         upstream direction, with a noise margin which is larger or equal to
         the specified Target Noise Margin. If the modem fails to achieve 
         this bitrate, it will reinitialize. Although the modem and the line
         might be able to support a higher bitrate, the modem will not transmit
         at a higher rate  than what is requested.
         The modem will maintain the specified planned bitrate during showtime.

         automaticRateAdaptiveAtStartup(2) :     
         The object xdslMinBitrateUpstream specifies the minimum data rate 
         the modem must operate at in the upstream direction, with a noise
         margin which is larger or equal to the specified Target Noise Margin.
         If it fails to achieve this bitrate the modem will reinitialize.
         As long as the data rate is below the maximum bitrate, bitrate
         increase has priority over transmit power reduction. The modem is not
         allowed to set up a data rate that is higher than the specified
         maximum data rate. The xdslLineRARatioUpstream object specifies how
         bitrate in excess of the minimum bitrate must be allocated among
         multiple channels. 
         During showtime no rate adaptation is allowed. 

         dynamicRateAdaptive(3):
         In this mode, the data rate is automatically selected at startup (as
         in mode 2), but during showtime, rate adaptation is allowed. The
         upstream data rate can vary between the upstream minimum data rate and
         the upstream maximum data rate. Upstream Rate Adaptation is performed
         when the conditions specified for Upstream Upshift Noise Margin and
         Upstream Upshift Interval - or for Upstream Downshift Noise Margin and
         Upstream Downshift Interval - are satisfied.

         ALCATEL NOTE:
             ACCESS:   NA                  USAGE:    OPT
             PERSIST:  YES                 INSRVMOD: NO
             RANGE:    NA                  DEFVALUE: NA
             UNITS:    NA                  SPARSE:   NA
             DESCR:    NA "
        DEFVAL          {automaticRateAdaptiveAtStartup}           
::= {xdslLineServiceProfileEntry 7}

xdslLineNumberChannels  OBJECT-TYPE
        SYNTAX          INTEGER
        ACCESS          read-write
        STATUS          mandatory
        DESCRIPTION     
        "This object defines the number of channels on the xdsl line.
         Range: 1 to 4 channels. 

         ALCATEL NOTE:
             ACCESS:   NA                  USAGE:    OPT
             PERSIST:  YES                 INSRVMOD: NO
             RANGE:    1                   DEFVALUE: NA
             UNITS:    channels            SPARSE:   NA
             DESCR:    The object is supported to avoid future database 
                       migration but should not be set.
                       Set requests will be rejected (badvalue) if the value
                       differs from the default value. "
        DEFVAL          {1}           
::= {xdslLineServiceProfileEntry 8}

xdslLineServiceProfileRowStatus        OBJECT-TYPE
        SYNTAX          RowStatus
        ACCESS          read-write
        STATUS          mandatory
        DESCRIPTION 
        "This object is used to create a new row or delete an existing row in
         this table. The usage is as per standard semantics of 'RowStatus'
         defined in SNMPv2-TC.
            o Both 'createAndGo' and 'createAndWait' options of row creation
              are supported.
            o The entry associated with a Profile that is being used may
              not be deleted.

         ALCATEL NOTE:
             ACCESS:   NA                  USAGE:    MAND
             PERSIST:  YES                 INSRVMOD: YES
             RANGE:    NA                  DEFVALUE: NA
             UNITS:    NA                  SPARSE:   NA
             DESCR:    NA "
::= {xdslLineServiceProfileEntry 9}

xdslLineServiceProfileChannelTable     OBJECT-TYPE
        SYNTAX          SEQUENCE OF XdslLineServiceProfileChannelEntry
        ACCESS          not-accessible
        STATUS          mandatory
        DESCRIPTION     
        "This table contains the service related parameters that characterize
         the bearer channels within an xdslLineServiceProfile. The creation of
         an xdslLineServiceProfileEntry includes the creation of an
         xdslLineServiceProfileChannelEntry for each channel of the service
         profile(i.e.  xdslLineNumberChannels entries in total).

         ALCATEL NOTE:
             TABLESIZE: DEP [256 * number of channels (1)]                    
             DESCR:     NA                   "
::= {xdslLineServiceProfile 2}

xdslLineServiceProfileChannelEntry     OBJECT-TYPE
        SYNTAX          XdslLineServiceProfileChannelEntry
        ACCESS          not-accessible
        STATUS          mandatory
        DESCRIPTION     
        "Each entry consists of a list of service related parameters that serve 
         to configure one bearer channel of an xdsl modem configuration
         profile.

         Row creation : When an entry is created in the 
                        xdslLineServiceProfileTable, entries (for each channel)
                        with the same xdslLineServiceProfileIndex are created in
                        this table.
         Row deletion : When an entry is deleted from the
                        xdslLineServiceProfileTable, the entries (for each 
                        channel) with the same xdslLineServiceProfileIndex are
                        deleted from this table.  "
        INDEX          {xdslLineServiceProfileIndex,
                        xdslLineServiceProfileChannelNumber}
::= {xdslLineServiceProfileChannelTable 1}

XdslLineServiceProfileChannelEntry ::=
        SEQUENCE {
            xdslLineServiceProfileChannelNumber       INTEGER,
            xdslRARatioDownstream                     INTEGER,
            xdslRARatioUpstream                       INTEGER,
            xdslMinBitrateDownstream                  INTEGER,
            xdslMinBitrateUpstream                    INTEGER,
            xdslPlannedBitrateDownstream              INTEGER,
            xdslPlannedBitrateUpstream                INTEGER,
            xdslMaxBitrateDownstream                  INTEGER,
            xdslMaxBitrateUpstream                    INTEGER,
            xdslL2LowPowerBitrateDownstream           INTEGER,
            xdslMaxInterleavingDelayDownstream        INTEGER,
            xdslMaxInterleavingDelayUpstream          INTEGER,
            xdslMinImpNoiseProtDownstream             INTEGER,
            xdslMinImpNoiseProtUpstream               INTEGER,
            xdslErasureDetectionDownstream            INTEGER,
            xdslErasureDetectionUpstream              INTEGER,
            xdslSraMaxDelayVarDownstream              INTEGER,
            xdslSraMaxDelayVarUpstream                INTEGER
        }

xdslLineServiceProfileChannelNumber    OBJECT-TYPE
        SYNTAX          INTEGER
        ACCESS          not-accessible
        STATUS          mandatory
        DESCRIPTION     
        "This object is used by the xdslLineServiceProfileChannelTable
         together with the xdslLineServiceProfileIndex to identify a row of
         this table. Range: 1 to 4.

         ALCATEL NOTE:
             ACCESS:   NA                  USAGE:    NA
             PERSIST:  YES                 INSRVMOD: NA
             RANGE:    NA                  DEFVALUE: NA
             UNITS:    NA                  SPARSE:   NA
             DESCR:    NA "
::= {xdslLineServiceProfileChannelEntry 1}

xdslRARatioDownstream   OBJECT-TYPE
        SYNTAX          INTEGER
        ACCESS          read-write
        STATUS          mandatory
        DESCRIPTION     
        "This object specifies the ratio that should be taken into account for
         allocating available data rate (in excess of the minimum data rate
         summed over all bearer channels) among the different bearer channels
         in the downstream direction.
         The ratio is defined as a percentage from 0 to 100.
         This parameter is only meaningfull in case multiple channels are used
         (e.g. 2 for dual latency, possibly up to 4 in the future for ADSL2)
         and must be fixed to 100 in case of single latency.
         The sum of the raRatios for all channels should be 100.
         The excessive bitrate (i.e. the available bitrate - the sum of the
         minimum bitrates) must be distributed among the different channels
         according to their respective raRatio.
         When the max bitrate is achieved for one of the channels, the raRatio
         of that channel must be distributed to the other channels according to
         their respective raRatio share.
         E.g. in case of 3 channels/raRatios: ch1/50%, ch2/20%, ch3/30%
         When ch1 max bit rate is achieved, its 50% raRatio is distributed 
         among ch2 (+20%) and ch3 (+30%) -> ch2/40%, ch3/60%.

         ALCATEL NOTE:
             ACCESS:   NA                  USAGE:    OPT
             PERSIST:  YES                 INSRVMOD: NO
             RANGE:    100                 DEFVALUE: 100
             UNITS:    percent             SPARSE:   NA
             DESCR:    The object is supported to avoid future database 
                       migration but should not be set.
                       Set requests will be rejected (badvalue) if the value
                       differs from the default value. "
::= {xdslLineServiceProfileChannelEntry 2}

xdslRARatioUpstream     OBJECT-TYPE
        SYNTAX          INTEGER
        ACCESS          read-write
        STATUS          mandatory
        DESCRIPTION     
        "This object specifies the ratio that should be taken into account for
         allocating available data rate (in excess of the minimum data rate
         summed over all bearer channels) among the different bearer channels
         in the upstream direction.
         The ratio is defined as a percentage from 0 to 100.
         This parameter is only meaningfull in case multiple channels are used
         (e.g. 2 for dual latency, possibly up to 4 in the future for ADSL2)
         and must be fixed to 100 in case of single latency.
         The sum of the raRatios for all channels should be 100.
         The excessive bitrate (i.e. the available bitrate - the sum of the
         minimum bitrates) must be distributed among the different channels
         according to their respective raRatio.
         When the max bitrate is achieved for one of the channels, the raRatio
         of that channel must be distributed to the other channels according to
         their respective raRatio share.
         E.g. in case of 3 channels/raRatios: ch1/50%, ch2/20%, ch3/30%
         When ch1 max bit rate is achieved, its 50% raRatio is distributed
         among ch2 (+20%) and ch3 (+30%) -> ch2/40%, ch3/60%.

         ALCATEL NOTE:
             ACCESS:   NA                  USAGE:    OPT
             PERSIST:  YES                 INSRVMOD: NO
             RANGE:    100                 DEFVALUE: 100
             UNITS:    percent             SPARSE:   NA
             DESCR:    The object is supported to avoid future database 
                       migration but should not be set.
                       Set requests will be rejected (badvalue) if the value
                       differs from the default value. "
::= {xdslLineServiceProfileChannelEntry 3}

xdslMinBitrateDownstream               OBJECT-TYPE
        SYNTAX          INTEGER
        ACCESS          read-write
        STATUS          mandatory
        DESCRIPTION     
        "This object contains the minimum bitrate that must be set up and
         maintained downstream in case of automaticRateAdaptiveAtStartup RA
         mode. This parameter has no meaning in operatorControlledRateAdaptive
         RA mode. 
         
         ALCATEL NOTE:
             ACCESS:   NA                  USAGE:    OPT
             PERSIST:  YES                 INSRVMOD: NO
             RANGE:    0..262143           DEFVALUE: 1024
             UNITS:    kbits/sec           SPARSE:   NA
             DESCR:    NA "
::= {xdslLineServiceProfileChannelEntry 4}   
        
xdslMinBitrateUpstream  OBJECT-TYPE
        SYNTAX          INTEGER
        ACCESS          read-write
        STATUS          mandatory
        DESCRIPTION     
        "This object contains the minimum bitrate that must be set up and
         maintained upstream in case of automaticRateAdaptiveAtStartup RA
         mode. This parameter has no meaning in operatorControlledRateAdaptive
         RA mode. 

         ALCATEL NOTE:
             ACCESS:   NA                  USAGE:    OPT
             PERSIST:  YES                 INSRVMOD: NO
             RANGE:    0..262143           DEFVALUE: 64
             UNITS:    kbits/sec           SPARSE:   NA
             DESCR:    NA "
::= {xdslLineServiceProfileChannelEntry 5}

xdslPlannedBitrateDownstream           OBJECT-TYPE
        SYNTAX          INTEGER
        ACCESS          read-write
        STATUS          mandatory
        DESCRIPTION     
        "This object contains the planned bitrate for the downstream data flow.
         It specifies the bit rate that must be set up and maintained in case
         of operatorControlledRateAdaptive RA mode. 

         ALCATEL NOTE:
             ACCESS:   NA                  USAGE:    OPT
             PERSIST:  YES                 INSRVMOD: NO
             RANGE:    0..262143           DEFVALUE: 1536
             UNITS:    kbits/sec           SPARSE:   NA
             DESCR:    NA "
::= {xdslLineServiceProfileChannelEntry 6}

xdslPlannedBitrateUpstream             OBJECT-TYPE
        SYNTAX          INTEGER
        ACCESS          read-write
        STATUS          mandatory
        DESCRIPTION     
        "This object contains the planned bitrate for the upstream data flow.
         It specifies the bit rate that must be set up and maintained in case
         of operatorControlledRateAdaptive RA mode.
 
         ALCATEL NOTE:
             ACCESS:   NA                  USAGE:    OPT
             PERSIST:  YES                 INSRVMOD: NO
             RANGE:    0..262143           DEFVALUE: 128
             UNITS:    kbits/sec           SPARSE:   NA
             DESCR:    NA "
::= {xdslLineServiceProfileChannelEntry 7}
                        
xdslMaxBitrateDownstream               OBJECT-TYPE
        SYNTAX          INTEGER
        ACCESS          read-write
        STATUS          mandatory
        DESCRIPTION     
        "This object contains the maximum allowed bit rate which can be set up
         and maintained downstream in case of automaticRateAdaptiveAtStartup RA
         mode. This parameter has no meaning in operatorControlledRateAdaptive
         RA mode. 

         ALCATEL NOTE:
             ACCESS:   NA                  USAGE:    OPT
             PERSIST:  YES                 INSRVMOD: NO
             RANGE:    0..262143           DEFVALUE: 6144
             UNITS:    kbits/sec           SPARSE:   NA
             DESCR:    NA "
::= {xdslLineServiceProfileChannelEntry 8}

xdslMaxBitrateUpstream                 OBJECT-TYPE
        SYNTAX          INTEGER
        ACCESS          read-write
        STATUS          mandatory
        DESCRIPTION     
        "This object contains the maximum allowed bit rate which can be set up
         and maintained upstream in case of automaticRateAdaptiveAtStartup RA
         mode. This parameter has no meaning in operatorControlledRateAdaptive
         RA mode. 

         ALCATEL NOTE:
             ACCESS:   NA                  USAGE:    OPT
             PERSIST:  YES                 INSRVMOD: NO
             RANGE:    0..262143           DEFVALUE: 640
             UNITS:    kbits/sec           SPARSE:   NA
             DESCR:    NA "
::= {xdslLineServiceProfileChannelEntry 9}

xdslL2LowPowerBitrateDownstream        OBJECT-TYPE
        SYNTAX          INTEGER
        ACCESS          read-write
        STATUS          mandatory
        DESCRIPTION     
        "This parameter specifies the minimum downstream net data rate that has
         to be supported for the bearer channel during the low power state L2.
         
         ALCATEL NOTE:
             ACCESS:   NA                  USAGE:    OPT
             PERSIST:  YES                 INSRVMOD: NO
             RANGE:    0..262143           DEFVALUE: 128
             UNITS:    kbits/sec           SPARSE:   NA
             DESCR:    NA "
::= {xdslLineServiceProfileChannelEntry 10}

xdslMaxInterleavingDelayDownstream     OBJECT-TYPE
        SYNTAX          INTEGER
        ACCESS          read-write
        STATUS          mandatory
        DESCRIPTION     
        "This object defines a maximum for the delay introduced by the
         interleaving and deinterleaving function in the given direction.
         The XTU-C and XTU-R must choose their interleaving and coding
         parameters within the max interleaved delay and min impulse noise
         protection constraints.
         When RTX is used in this direction then this parameter is invalidated
         and the xdslRtxMaxDelayDownstream parameter of the RTX profile is 
         taken into account.
         The value 1 is used to specify that fast or pseudo fast latency
         (i.e. no interleaving) must be used.

         ALCATEL NOTE:
             ACCESS:   NA                  USAGE:    OPT
             PERSIST:  YES                 INSRVMOD: NO
             RANGE:    1..63               DEFVALUE: 16
             UNITS:    milliseconds        SPARSE:   NA
             DESCR:    NA "
::= {xdslLineServiceProfileChannelEntry 11}

xdslMaxInterleavingDelayUpstream       OBJECT-TYPE
        SYNTAX          INTEGER
        ACCESS          read-write
        STATUS          mandatory
        DESCRIPTION     
        "This object defines a maximum for the delay introduced by the
         interleaving and deinterleaving function in the given direction.
         The XTU-C and XTU-R must choose their interleaving and coding
         parameters within the max interleaved delay and min impulse noise
         protection constraints.
         When RTX is used in this direction then this parameter is invalidated
         and the xdslRtxMaxDelayUpstream parameter of the RTX profile is 
         taken into account.
         The value 1 is used to specify that fast or pseudo fast latency
         (i.e. no interleaving) must be used.

         ALCATEL NOTE:
             ACCESS:   NA                  USAGE:    OPT
             PERSIST:  YES                 INSRVMOD: NO
             RANGE:    1..63               DEFVALUE: 16
             UNITS:    milliseconds        SPARSE:   NA
             DESCR:    NA "
::= {xdslLineServiceProfileChannelEntry 12}

xdslMinImpNoiseProtDownstream          OBJECT-TYPE
        SYNTAX          INTEGER
        ACCESS          read-write
        STATUS          mandatory
        DESCRIPTION     
        "This object defines the minimum impulse noise protection for the
         given direction. It is expressed in symbols.
         Range: 0 to 16 symbols in steps of 0.1 symbol.
         The minimum impulse noise protection is represented as
         1/10 * xdslMinImpNoiseProtDownstream.

         ALCATEL NOTE:
             ACCESS:   NA                  USAGE:    OPT
             PERSIST:  YES                 INSRVMOD: NA
             RANGE:    0..160              DEFVALUE: 0
             UNITS:    0.1 symbols         SPARSE:   NA
             DESCR:    NA "
::= {xdslLineServiceProfileChannelEntry 13}

xdslMinImpNoiseProtUpstream            OBJECT-TYPE
        SYNTAX          INTEGER
        ACCESS          read-write
        STATUS          mandatory
        DESCRIPTION     
        "This object defines the minimum impulse noise protection for the
         given direction. It is expressed in symbols.
         Range: 0 to 16 symbols in steps of 0.1 symbol.
         The minimum impulse noise protection is represented as
         1/10 * xdslMinImpNoiseProtUpstream.

         ALCATEL NOTE:
             ACCESS:   NA                  USAGE:    OPT
             PERSIST:  YES                 INSRVMOD: NO
             RANGE:    0..160              DEFVALUE: 0
             UNITS:    0.1 symbols         SPARSE:   NA
             DESCR:    NA "
::= {xdslLineServiceProfileChannelEntry 14}

xdslErasureDetectionDownstream         OBJECT-TYPE
        SYNTAX          INTEGER
        ACCESS          read-write
        STATUS          mandatory
        DESCRIPTION
        "Indicates whether the erasure detection mechanism is allowed to be
         taken into account in order to reach the MinInp.
         Value 1 = MinInp must be reached even without erasure
         detection
         Value 0 = MinInp must be reached with or without
         erasure detection

         ALCATEL NOTE:
             ACCESS:   NA                  USAGE:    OPT
             PERSIST:  YES                 INSRVMOD: NO
             RANGE:    0..1                DEFVALUE: 0
             UNITS:    NA                  SPARSE:   NA
             DESCR:    NA "
::= {xdslLineServiceProfileChannelEntry 15}

xdslErasureDetectionUpstream           OBJECT-TYPE
        SYNTAX          INTEGER
        ACCESS          read-write
        STATUS          mandatory
        DESCRIPTION
        "Indicates whether the erasure detection mechanism is allowed to be
         taken into account in order to reach the MinInp.
         Value 1 = MinInp must be reached even without erasure
         detection
         Value 0 = MinInp must be reached with or without
         erasure detection

         ALCATEL NOTE:
             ACCESS:   NA                  USAGE:    OPT
             PERSIST:  YES                 INSRVMOD: NO
             RANGE:    0..1                DEFVALUE: 0
             UNITS:    NA                  SPARSE:   NA
             DESCR:    NA "
::= {xdslLineServiceProfileChannelEntry 16}

xdslSraMaxDelayVarDownstream               OBJECT-TYPE
        SYNTAX          INTEGER
        ACCESS          read-write
        STATUS          mandatory
        DESCRIPTION     
        "This object specifies the maximum delay variation allowed in downstream
         direction during SRA in VDSL2 mode.
         Range: 0.1 ... 25.4 ms in steps of 0.1ms.
         Integer range is actual value / 0.1ms.
         The special value 255 indicates that no delay variation bound is 
         imposed.

         ALCATEL NOTE:
             ACCESS:   NA                  USAGE:    OPT
             PERSIST:  YES                 INSRVMOD: NO
             RANGE:    1..254,255          DEFVALUE: 255
             UNITS:    1/10 milliseconds   SPARSE:   NA
             DESCR:    NA "
::= { xdslLineServiceProfileChannelEntry 18}

xdslSraMaxDelayVarUpstream               OBJECT-TYPE
        SYNTAX          INTEGER
        ACCESS          read-write
        STATUS          mandatory
        DESCRIPTION     
        "This object specifies the maximum delay variation allowed in Upstream 
         direction during SRA in VDSL2 mode.
         Range: 0.1 ... 25.4 ms in steps of 0.1ms.
         Integer range is actual value / 0.1ms
         The special value 255 indicates that no delay variation bound is 
         imposed.

         ALCATEL NOTE:
             ACCESS:   NA                  USAGE:    OPT
             PERSIST:  YES                 INSRVMOD: NO
             RANGE:    1..254,255          DEFVALUE: 255
             UNITS:    1/10 milliseconds   SPARSE:   NA
             DESCR:    NA "
::= { xdslLineServiceProfileChannelEntry 17}

xdslLineServiceProfileMappingTable     OBJECT-TYPE
        SYNTAX          SEQUENCE OF XdslLineServiceProfileMappingEntry
        ACCESS          not-accessible
        STATUS          mandatory
        DESCRIPTION
        "The (conceptual) table listing the profile name to profile Index
         Mapping.

         ALCATEL NOTE:
             TABLESIZE: 256                    
             DESCR:     NA                   "
::= {xdslLineServiceProfile 3}

xdslLineServiceProfileMappingEntry     OBJECT-TYPE
        SYNTAX          XdslLineServiceProfileMappingEntry
        ACCESS          not-accessible
        STATUS          mandatory
        DESCRIPTION
        "An entry (conceptual row) representing the profile Name to Index
         Mapping.

         Row creation : When an entry is created in the 
                        xdslLineServiceProfileTable, an entry is created in
                        this table.
         Row deletion : When an entry is deleted from the
                        xdslLineServiceProfileTable, the entry is deleted from
                        this table.  "
        INDEX          {xdslLineServiceProfileMappingName,
                        xdslLineServiceProfileMappingScope}
::= { xdslLineServiceProfileMappingTable 1 }

XdslLineServiceProfileMappingEntry ::=
        SEQUENCE {
            xdslLineServiceProfileMappingName         AsamProfileName,
            xdslLineServiceProfileMappingScope        AsamProfileScope,
            xdslLineServiceProfileMappingIndex        AsamProfileIndex
        }

xdslLineServiceProfileMappingName      OBJECT-TYPE
        SYNTAX          AsamProfileName
        ACCESS          not-accessible
        STATUS          mandatory
        DESCRIPTION
        "The Service profile name.

         ALCATEL NOTE:
             ACCESS:   NA                  USAGE:    NA
             PERSIST:  NO                  INSRVMOD: NA
             RANGE:    NA                  DEFVALUE: NA
             UNITS:    NA                  SPARSE:   NA
             DESCR:    NA "
::= { xdslLineServiceProfileMappingEntry 1 }

xdslLineServiceProfileMappingScope     OBJECT-TYPE
        SYNTAX          AsamProfileScope
        ACCESS          not-accessible
        STATUS          mandatory
        DESCRIPTION
        "The Service profile scope.

         ALCATEL NOTE:
             ACCESS:   NA                  USAGE:    NA
             PERSIST:  NO                  INSRVMOD: NA
             RANGE:    NA                  DEFVALUE: NA
             UNITS:    NA                  SPARSE:   NA
             DESCR:    NA "
::= { xdslLineServiceProfileMappingEntry 2 }

xdslLineServiceProfileMappingIndex     OBJECT-TYPE
        SYNTAX          AsamProfileIndex
        ACCESS          read-only
        STATUS          mandatory
        DESCRIPTION
        "The Index of the corresponding service profile.

         ALCATEL NOTE:
             ACCESS:   NA                  USAGE:    NA
             PERSIST:  NO                  INSRVMOD: NA
             RANGE:    1..256              DEFVALUE: NA
             UNITS:    NA                  SPARSE:   NA
             DESCR:    NA "
::= { xdslLineServiceProfileMappingEntry 3 }

xdslLineSpectrumProfileIndexNext       OBJECT-TYPE
        SYNTAX          AsamNextProfileIndex
        ACCESS          read-only
        STATUS          mandatory
        DESCRIPTION     
        "This object contains an appropriate value to be used for 
         xdslLineSpectrumProfileIndex when creating entries in the
         xdslLineSpectrumProfileTable. 
         The value 0 indicates that no unassigned entries are available. To 
         obtain the xdslLineNextSpectrumProfileIndex value for a new entry, the
         manager issues a management protocol retrieval operation to obtain the
         current value of this object.  After each retrieval, the agent should
         modify the value to the next unassigned index.

         ALCATEL NOTE:
             ACCESS:   NA                  USAGE:    NA
             PERSIST:  NO                  INSRVMOD: NA
             RANGE:    0..256              DEFVALUE: 1
             UNITS:    NA                  SPARSE:   NA
             DESCR:    NA "
::= {xdslLine 4}

xdslLineSpectrumProfileMaxIndex        OBJECT-TYPE
        SYNTAX          AsamMaxProfileIndex
        ACCESS          read-only
        STATUS          mandatory
        DESCRIPTION
        "This object represents the maximum number of xdslLineSpectrumProfiles
         that can be created. The object xdslLineSpectrumProfileIndexNext will 
         have values ranging from 0 to the value represented by this object.

         ALCATEL NOTE:
             ACCESS:   NA                  USAGE:    NA
             PERSIST:  NO                  INSRVMOD: NA
             RANGE:    256..256            DEFVALUE: 256
             UNITS:    NA                  SPARSE:   NA
             DESCR:    NA "
::= {xdslLine 5}

xdslLineSpectrumProfileTable           OBJECT-TYPE
        SYNTAX          SEQUENCE OF XdslLineSpectrumProfileEntry
        ACCESS          not-accessible
        STATUS          mandatory
        DESCRIPTION     
        "This table contains the spectrum related parameters of the modem
         configuration. One entry in this table reflects a profile which
         can be used to configure the modem for a physical line.

         ALCATEL NOTE:
             TABLESIZE: 256                    
             DESCR:     NA                   "
::= {xdslLineSpectrumProfile 1}

xdslLineSpectrumProfileEntry           OBJECT-TYPE
        SYNTAX          XdslLineSpectrumProfileEntry
        ACCESS          not-accessible
        STATUS          mandatory
        DESCRIPTION     
        "Each entry consists of a list of line related parameters that serve 
         to configure an XDSL modem. A profile can be created in one step with
         all necessary parameter values and xdslLineSpectrumProfileRowStatus
         set to createAndGo.
         It can also be created in several steps by specifying values of a few
         objects in each step. The xdslLineSpectrumProfileRowStatus is set to
         createAndWait in the first step and to Active in the last step.

         Row creation : An entry is created when the manager requests to create
                        a spectrum profile.
         Row deletion : An entry is deleted when the manager requests to delete
                        a spectrum profile. "
        INDEX          {xdslLineSpectrumProfileIndex}
::= {xdslLineSpectrumProfileTable 1}

XdslLineSpectrumProfileEntry ::=
        SEQUENCE {
            xdslLineSpectrumProfileIndex              AsamProfileIndex,
            xdslLineSpectrumProfileName               AsamProfileName,
            xdslLineSpectrumProfileScope              AsamProfileScope,
            xdslLineSpectrumProfileVersionNbr         INTEGER,
            xdslLineSpectrumProfileUsedStatus         AsamProfileRefCount, 
            xdslLineOpMode                            OpModeType,
            xdslLineMinNoiseMarginDownstream          INTEGER,
            xdslLineMinNoiseMarginUpstream            INTEGER,
            xdslLineTargetNoiseMarginDownstream       INTEGER,
            xdslLineTargetNoiseMarginUpstream         INTEGER,
            xdslLineMaxNoiseMarginDownstream          INTEGER,
            xdslLineMaxNoiseMarginUpstream            INTEGER,
            xdslLineCarrierMaskDownstream             OCTET STRING,
            xdslLineCarrierMaskUpstream               OCTET STRING,
            xdslLineRfiBands                          OCTET STRING,
            xdslLinePowerMgtMode                      INTEGER,
            xdslLineL0Time                            INTEGER,   
            xdslLineL2Time                            INTEGER,
            xdslLineL2Atpr                            INTEGER,        
            xdslLineSpectrumProfileRowStatus          RowStatus,
            xdslLineSpectrumProfileModifyStatus       INTEGER,
            xdslLineL2AtprT                           INTEGER,
            xdslLineRAUNoiseMarginDownstream          INTEGER,
            xdslLineRAUNoiseMarginUpstream            INTEGER,
            xdslLineRAUTimeDownstream                 INTEGER,
            xdslLineRAUTimeUpstream                   INTEGER,
            xdslLineRADNoiseMarginDownstream          INTEGER,
            xdslLineRADNoiseMarginUpstream            INTEGER,
            xdslLineRADTimeDownstream                 INTEGER,
            xdslLineRADTimeUpstream                   INTEGER,
            xdslLineArtificialNoisePsdDownstream      ArtificialNoisePsdDownType
        }

xdslLineSpectrumProfileIndex           OBJECT-TYPE
        SYNTAX          AsamProfileIndex
        ACCESS          not-accessible
        STATUS          mandatory
        DESCRIPTION     
        "This object is used to uniquely identify an entry in this table.
         It is used by the line configuration table to identify a row of this
         table. The max value of this object is limited to
         xdslLineSpectrumProfileMaxIndex value.
         In addition, special index values are defined to identify temporary
         entries in this table used to contain the modifications performed on
         an existing profile. The index value of such an entry is obtained by
         adding a fixed offset to the corresponding index. The value of this
         offset is contained in xdslLineSpectrumProfileIndexOffset. A temporary
         entry exists only during the profile modification, it is created at
         xdslLineSpectrumProfileModifyStatus = modifyStart and is deleted at
         modifyCancel or modifyComplete. It can only be accessed during the
         modification to retrieve the updated parameters values of a profile.
         The nominal entry contains the original profile settings and is not
         updated until the profile modification is completed and validated.
         The offset entries are read only, all write operations must be
         performed using the nominal index.
         The getnext can be used to retrieve the nominal spectrum profile
         entries and does not return the temporary profiles entries at the
         special offset index values.

         ALCATEL NOTE:
             ACCESS:   NA                  USAGE:    NA
             PERSIST:  YES                 INSRVMOD: NA
             RANGE:    1..256              DEFVALUE: NA
             UNITS:    NA                  SPARSE:   NA
             DESCR:    NA "
::= {xdslLineSpectrumProfileEntry 1}

xdslLineSpectrumProfileName            OBJECT-TYPE
        SYNTAX          AsamProfileName
        ACCESS          read-write
        STATUS          mandatory
        DESCRIPTION     
        "A textual name identifying this profile. This name has to be unique
         within the assigned scope.

         ALCATEL NOTE:
             ACCESS:   NA                  USAGE:    MAND
             PERSIST:  YES                 INSRVMOD: YES
             RANGE:    NA                  DEFVALUE: NA
             UNITS:    NA                  SPARSE:   NA
             DESCR:    NA "
::= {xdslLineSpectrumProfileEntry 2}

xdslLineSpectrumProfileScope           OBJECT-TYPE
        SYNTAX          AsamProfileScope
        ACCESS          read-write
        STATUS          mandatory
        DESCRIPTION     
        "A  profile can be qualified as having a local scope or a network wide 
         scope. As some managers may not support the network profile scope,
         the use of local scope is strongly recommended.

         ALCATEL NOTE:
             ACCESS:   NA                  USAGE:    OPT 
             PERSIST:  YES                 INSRVMOD: YES
             RANGE:    NA                  DEFVALUE: NA
             UNITS:    NA                  SPARSE:   NA
             DESCR:    NA "
        DEFVAL          {localScope}
::= {xdslLineSpectrumProfileEntry 3}

xdslLineSpectrumProfileVersionNbr      OBJECT-TYPE
        SYNTAX          INTEGER
        ACCESS          read-write
        STATUS          mandatory
        DESCRIPTION     
        "The manager can associate a version number to the profile. It is set
         to 1 when the profile is first created and will be incremented by the
         manager when the profile is modified.

         ALCATEL NOTE:
             ACCESS:   NA                  USAGE:    OPT
             PERSIST:  YES                 INSRVMOD: YES
             RANGE:    NA                  DEFVALUE: NA
             UNITS:    NA                  SPARSE:   NA
             DESCR:    NA "
        DEFVAL          {1}
::= {xdslLineSpectrumProfileEntry 4}

xdslLineSpectrumProfileUsedStatus      OBJECT-TYPE
        SYNTAX          AsamProfileRefCount
        ACCESS          read-only
        STATUS          mandatory
        DESCRIPTION
        "Indicates the number of entities using this profile. If the reference
         count is greater than 0, then this profile is 'in use', and may NOT be
         deleted. If the value is 0, then this profile is 'not in use', and can
         be deleted.

         ALCATEL NOTE:
             ACCESS:   NA                  USAGE:    NA
             PERSIST:  NO                  INSRVMOD: NA
             RANGE:    NA                  DEFVALUE: 0
             UNITS:    NA                  SPARSE:   NA
             DESCR:    NA "
::= {xdslLineSpectrumProfileEntry 5}

xdslLineOpMode          OBJECT-TYPE
        SYNTAX          OpModeType
        ACCESS          read-write
        STATUS          mandatory 
        DESCRIPTION 
        "This object defines the operational modes allowed by the corresponding
         configuration profile. 
         It is coded in a bitmap defined as follows (based on G.997.1,
         transmission system enabling). More than one mode can be set
         simultaneously.
         The respective operational modes correspond to the following integer
         values in the bitmap, other bit positions are reserved for future use.
       
         Octet 1 (ADSL):
         1:  ANSI T1.413-1998
         2:  ETSI DTS/TM06006
         4:  G.992.1 operation over POTS non-overlapped spectrum (Annex A of
             G.992.1)
         8:  G.992.1 operation over POTS overlapped spectrum (Annex A of
             G.992.1)
         16: G.992.1 operation over ISDN non-overlapped spectrum (Annex B
             of G.992.1)
         32: G.992.1 operation over ISDN overlapped spectrum (Annex B of
             G.992.1)
         64: G.992.1 operation in conjunction with TCM-ISDN non-overlapped
             spectrum (Annex C of G.992.1)
         128:G.992.1 operation in conjunction with TCM-ISDN overlapped
             spectrum (Annex C of G.992.1)

         Octet 2 (ADSL):
         1:  G.992.2 operation over POTS non-overlapped spectrum (Annex A of
             G.992.2)
         2:  G.992.2 operation over POTS overlapped spectrum (Annex B of
             G.992.2).
         4:  G.992.2 operation in conjunction with TCM-ISDN non-overlapped
             spectrum (Annex C of G.992.2)
         8:  G.992.2 operation in conjunction with TCM-ISDN overlapped
             spectrum(Annex C of G.992.2)

         Octet 3 (ADSL2):
         4:  G.992.3 operation over POTS non-overlapped spectrum (Annex A of
             G.992.3)
         8:  G.992.3 operation over POTS overlapped spectrum (Annex A of
             G.992.3)
         16: G.992.3 operation over ISDN non-overlapped spectrum (Annex B of
             G.992.3)
         32: G.992.3 operation over ISDN overlapped spectrum (Annex B of
             G.992.3)

         Octet 4 (ADSL2):
         1:  G.992.4 operation over POTS non-overlapped spectrum (Annex A of
             G.992.4)
         2:  G.992.4 operation over POTS overlapped spectrum (Annex A of
             G.992.4)
         16: G.992.3 All Digital Mode operation with non-overlapped spectrum
             (Annex I of G.992.3)
         32: G.992.3 All Digital Mode operation with overlapped spectrum (Annex
             I of G.992.3)
         64: G.992.3 All Digital Mode operation with non-overlapped spectrum
             (Annex J of G.992.3)
         128:G.992.3 All Digital Mode operation with overlapped spectrum
             (Annex J of G.992.3)

         Octet 5 (ADSL2):
         1:  G.992.4 All Digital Mode operation with non-overlapped spectrum
             (Annex I of G.992.4)
         2:  G.992.4 All Digital Mode operation with overlapped spectrum
             (Annex I of G.992.4).
         4:  G.992.3 operation over POTS non-overlapped spectrum US mask 1
             (Annex L mode 1 of G.992.3)
         8:  G.992.3 operation over POTS non-overlapped spectrum US mask 2
             (Annex L mode 2 of G.992.3)
         16: G.992.3 operation over POTS overlapped spectrum US mask 1
             (Annex L mode 3 of G.992.3).
         32: G.992.3 operation over POTS overlapped spectrum US mask 2
             (Annex L mode 4 of G.992.3).
         64: G.992.3 Extended Upstream operation over POTS with non-overlapped
             spectrum (Annex M of G.992.3)
         128:G.992.3 Extended Upstream operation over POTS with overlapped
             spectrum (Annex M of G.992.3)

         Octet 6 (ADSL2):
         1:  G.992.5 operation over POTS non-overlapped spectrum (Annex A of
             G.992.5)
         2:  G.992.5 operation over POTS overlapped spectrum (Annex A of
             G.992.5)
         4:  G.992.5 operation over ISDN non-overlapped spectrum (Annex B of
             G.992.5)
         8:  G.992.5 operation over ISDN overlapped spectrum (Annex B of
             G.992.5)
         64: G.992.5 All Digital Mode operation with non-overlapped spectrum
             (Annex I of G.992.5)
         128:G.992.5 All Digital Mode operation with overlapped spectrum
             (Annex I of G.992.5)

         Octet 7 (VDSL):
         1:  ANSI T1.424
         2:  ETSI TS 101 270
         4:  ITU G.993.1
         8:  IEEE 802.3ah

         Octet 8 (ADSL2):
         1:  G.992.5 All Digital Mode operation with non-overlapped spectrum
             (Annex J of G.992.5)
         2:  G.992.5 All Digital Mode operation with overlapped spectrum
             (Annex J of G.992.5)
         4:  G.992.5 Extended Upstream operation over POTS non-overlapped 
             spectrum
             (Annex M of G.992.5)
         8:  G.992.5 Extended Upstream operation over POTS overlapped spectrum
             (Annex M of G.992.5)       

         Octet 9 (VDSL2):
         1:  G.993.2_ 8A VDSL-2 with profile 8A
         2:  G.993.2_ 8B VDSL-2 with profile 8B
         4:  G.993.2_ 8C VDSL-2 with profile 8C
         8:  G.993.2_ 8D VDSL-2 with profile 8D
         16: G.993.2_12A VDSL-2 with profile 12A
         32: G.993.2_12B VDSL-2 with profile 12B
         64: G.993.2_17A VDSL-2 with profile 17A
         128:G.993.2_30A VDSL-2 with profile 30A

         Octet 10-16:  Reserved for further use

         The actual operational mode is reflected by the
         xdslLineActualOperationalMode object.

         ALCATEL NOTE:
             ACCESS:   NA                  USAGE:    OPT
             PERSIST:  YES                 INSRVMOD: YES
             RANGE:    NA                  DEFVALUE: NA
             UNITS:    NA                  SPARSE:   NA
             DESCR:    NA "
        DEFVAL          {'1701140100000200FF00000000000000'H}
::= {xdslLineSpectrumProfileEntry 6}

xdslLineMinNoiseMarginDownstream       OBJECT-TYPE
        SYNTAX          INTEGER
        ACCESS          read-write   
        STATUS          mandatory
        DESCRIPTION
        "Used during showtime and independant of rate adaptation mode. When
         current noise margin falls below the Minimum Noise Margin and no
         bitswap action can help this anymore, the modem will reinitialize.
         Limitation: Minimum Noise Margin <= Target Noise Margin
         Expressed in dB.
         Range: 0 to 31 dB with 0,1 dB steps.
         The minimum noise margin is represented as
         1/10 * xdslLineMinNoiseMarginDownstream.

         ALCATEL NOTE:
             ACCESS:   NA                  USAGE:    OPT
             PERSIST:  YES                 INSRVMOD: YES
             RANGE:    0..310              DEFVALUE: NA
             UNITS:    dB / 10             SPARSE:   NA
             DESCR:    NA "
        DEFVAL          {0}           
::= {xdslLineSpectrumProfileEntry 7}

xdslLineMinNoiseMarginUpstream         OBJECT-TYPE
        SYNTAX          INTEGER
        ACCESS          read-write
        STATUS          mandatory 
        DESCRIPTION 
        "Used during showtime and independant of rate adaptation mode. When
         current noise margin falls below the Minimum Noise Margin and no 
         bitswap action can help this anymore, the modem will reinitialize.
         Limitation: Minimum Noise Margin <= Target Noise Margin
         Expressed in dB.
         Range: 0 to 31 dB with 0,1 dB steps.
         The minimum noise margin is represented as
         1/10 * xdslLineMinNoiseMarginUpstream.
    
         ALCATEL NOTE:
             ACCESS:   NA                  USAGE:    OPT
             PERSIST:  YES                 INSRVMOD: YES
             RANGE:    0..310              DEFVALUE: NA
             UNITS:    dB / 10             SPARSE:   NA
             DESCR:    NA "
        DEFVAL          {0}           
::= {xdslLineSpectrumProfileEntry 8}

xdslLineTargetNoiseMarginDownstream    OBJECT-TYPE
        SYNTAX          INTEGER
        ACCESS          read-write
        STATUS          mandatory
        DESCRIPTION     
        "Used at startup for all rate adaptation modes. This is the Noise
         Margin the XTU-R receiver shall achieve, relative to a BER of 1E-7 or 
         better for each of the downstream bearer channels, to successfully
         complete initialization. It is expressed in dB.
         Range: 0 to 31 dB with 0,1 dB steps.
         The target noise margin is represented as
         1/10 * xdslLineTargetNoiseMarginDownstream.

         ALCATEL NOTE:
             ACCESS:   NA                  USAGE:    OPT
             PERSIST:  YES                 INSRVMOD: NA
             RANGE:    0..310              DEFVALUE: NA
             UNITS:    dB / 10             SPARSE:   NA
             DESCR:    NA "
        DEFVAL          {60}           
::= {xdslLineSpectrumProfileEntry 9}

xdslLineTargetNoiseMarginUpstream      OBJECT-TYPE
        SYNTAX          INTEGER
        ACCESS          read-write
        STATUS          mandatory    
        DESCRIPTION     
        "Used at startup for all rate adaptation modes. This is the Noise 
         Margin the ATU-C receiver shall achieve, relative to a BER of 1E-7 or 
         better for each of the upstream bearer channels, to successfully
         complete initialization. It is expressed in dB.
         Range: 0 to 31 dB with 0,1 dB steps.
         The target noise margin is represented as
         1/10 * xdslLineTargetNoiseMarginUpstream.

         ALCATEL NOTE:
             ACCESS:   NA                  USAGE:    OPT
             PERSIST:  YES                 INSRVMOD: YES
             RANGE:    0..310              DEFVALUE: NA
             UNITS:    dB / 10             SPARSE:   NA
             DESCR:    NA "
        DEFVAL          {60}           
::= {xdslLineSpectrumProfileEntry 10}

xdslLineMaxNoiseMarginDownstream       OBJECT-TYPE
        SYNTAX          INTEGER
        ACCESS          read-write
        STATUS          mandatory 
        DESCRIPTION 
        "Used at startup and showtime, independently of RA mode.
         When the noise margin is higher than the Maximum Noise Margin, then
         the modem will take action to reduce the peer modem power to get the
         noise margin below this value.
         When the noise margin is lower than the Maximum Noise Margin, then the
         modem will take action to increase the peer modem power to get the
         noise margin as close as possible to this value.
         Expressed in dB.
         Range: 0 to 31 dB with 0,1 dB steps, plus value 51,1 dB used as 
         special value.
         Special value 51,1 dB is used to indicate that no max noise margin 
         limit must be applied.
         The maximum noise margin is represented as
         1/10 * xdslLineMaxNoiseMarginDownstream.

         ALCATEL NOTE:
             ACCESS:   NA                  USAGE:    OPT
             PERSIST:  YES                 INSRVMOD: YES
             RANGE:    0..310, 511         DEFVALUE: NA
             UNITS:    dB / 10             SPARSE:   NA
             DESCR:    NA "
        DEFVAL          {511}           
::= {xdslLineSpectrumProfileEntry 11}
    
xdslLineMaxNoiseMarginUpstream         OBJECT-TYPE
        SYNTAX          INTEGER
        ACCESS          read-write
        STATUS          mandatory 
        DESCRIPTION 
        "Used at startup and showtime, independently of RA mode.
         When the noise margin is higher than the Maximum Noise Margin, then 
         the modem will take action to reduce the peer modem power to get the 
         noise margin below this value.
         When the noise margin is lower than the Maximum Noise Margin, then the
         modem will take action to increase the peer modem power to get the
         noise margin as close as possible to this value.
         Expressed in dB.
         Range: 0 to 31 dB with 0,1 dB steps, plus value 51,1 dB used as
         special value.
         Special value 51,1 dB is used to indicate that no max noise margin 
         limit must be applied.
         The maximum noise margin is represented as
         1/10 * xdslLineMaxNoiseMarginUpstream.    

         ALCATEL NOTE:
             ACCESS:   NA                  USAGE:    OPT
             PERSIST:  YES                 INSRVMOD: YES
             RANGE:    0..310, 511         DEFVALUE: NA
             UNITS:    dB / 10             SPARSE:   NA
             DESCR:    NA "
        DEFVAL          {511}           
::= {xdslLineSpectrumProfileEntry 12}

xdslLineCarrierMaskDownstream          OBJECT-TYPE
        SYNTAX          OCTET STRING (SIZE (64))
        ACCESS          read-write
        STATUS          mandatory
        DESCRIPTION     
        "The downstream carrier mask pattern is a bitlist of 512 bits, each bit
         corresponding to one frequency carrier of the DMT modem system. 
         Carrier 0 is represented by the most significant bit of the map, 
         carrier 511 is represented by the least significant bit of the map.
         A downstream carrier is suppressed by setting its corresponding bit to
         1.
         Pilot tones may not be suppressed. If one of the masked carrier is
         defined as a pilot tone in the applicable DSL standard, the modem will 
         not initialize.
         The masking of carriers that are not used in the downstream direction
         or that are not used by the XDSL operational mode will be ignored.
         Carriers 0 to 255 are used for all ADSL/ADSL2 operational modes except 
         for ADSL2 Plus which uses carriers 0 to 511.
         The carrier mask is not used in VDSL mode and will be ignored.

         ALCATEL NOTE:
             ACCESS:   NA                  USAGE:    OPT
             PERSIST:  YES                 INSRVMOD: YES
             RANGE:    NA                  DEFVALUE: NA
             UNITS:    NA                  SPARSE:   NA
             DESCR:    NA "
        DEFVAL      {'00000000000000000000000000000000000000000000000000000000000000000000000000000000000000000000000000000000000000000000000000000000'H}
::= {xdslLineSpectrumProfileEntry 13}

xdslLineCarrierMaskUpstream            OBJECT-TYPE
        SYNTAX          OCTET STRING (SIZE (8))
        ACCESS          read-write
        STATUS          mandatory
        DESCRIPTION     
        "The upstream carrier mask pattern is a bitlist of 64 bits, each bit
         corresponding to one frequency carrier of the DMT modem system. 
         Carrier 0 is represented by the most significant bit of the map, 
         carrier 63 is represented by the least significant bit of the map.
         An upstream carrier is suppressed by setting its corresponding bit to
         1.
         Pilot tones may not be suppressed. If one of the masked carrier is 
         defined as a pilot tone in the applicable DSL standard, the modem will
         not initialize.
         The masking of carriers that are not used in the upstream direction
         or that are not used by the XDSL operational mode will be ignored.
         Carriers 0 to 63 are used for all ADSL/ADSL2 operational modes.
         The carrier mask is not used in VDSL mode and will be ignored.

         ALCATEL NOTE:
             ACCESS:   NA                  USAGE:    OPT
             PERSIST:  YES                 INSRVMOD: YES
             RANGE:    NA                  DEFVALUE: NA
             UNITS:    NA                  SPARSE:   NA
             DESCR:    NA "
        DEFVAL          {'0000000000000000'H }
::= {xdslLineSpectrumProfileEntry 14}

xdslLineRfiBands        OBJECT-TYPE
        SYNTAX          OCTET STRING (SIZE (0..80))
        ACCESS          read-write
        STATUS          mandatory
        DESCRIPTION     
        "This object specifies a list of RF bands (HAM or AM) for
         egress control and ingress cancelling. Up to 16 RF signals can be
         specified.
         The RF band list is coded as a variable length octet string defined
         as follows.
         OCTET 0..4 define the characteristics of RF BAND #1:
         OCTET 0..1: INTEGER (0..30000), start frequency (in kHz) of the
         first RF signal. In case of a single carrier RF signal, it is equal
         to the carrier frequency of the signal. 
         The value is defined as MSB-LSB (big-endian).
         OCTETS 2..3: INTEGER (0..30000), stop frequency (in kHz)of the first
         RF signal. In case of a single carrier RF signal, it is equal
         to the carrier frequency of the signal.
         The value is defined as MSB-LSB (big-endian).
         OCTET 4 - bits 0..1: INTEGER (0..3), indicates the type of RF signal:
         Hamband (1), AM signal (2).
         OCTETS 4 - bits 2..3: INTEGER (0..3), egress control, defines whether
         and how egress control must be applied in the corresponding RF band:
         egressNoControl(1), egressNotched(2).
         OCTETS 4 - bits 4..5: INTEGER (0..3), ingress level, defines the
         level of ingress to be expected from the corresponding RF signal:
         ingressLow(1), ingressWeak(2), ingressStrong (3).     
         And so on  up to
         OCTETS (N-1)*5..(N*5)-1: define the characteristics of the last
         RF BAND #N with N<=16.

         ALCATEL NOTE:
             ACCESS:   NA                  USAGE:    OPT
             PERSIST:  YES                 INSRVMOD: YES
             RANGE:    NA                  DEFVALUE: NA
             UNITS:    NA                  SPARSE:   NA
             DESCR:    NA "
        DEFVAL          {'071207D0190DAC0ED8191B581BBC19277427A619'H }
::= {xdslLineSpectrumProfileEntry 15}

xdslLinePowerMgtMode    OBJECT-TYPE
        SYNTAX          INTEGER
        ACCESS          read-write
        STATUS          mandatory
        DESCRIPTION     
        "This object specifies the permission of power management states.
         It is coded in a bitmap. The respective power states correspond to
         the following integer values in the bitmap, other bit positions are
         reserved for future use.
         1:  L2 allowed
         2:  L3 allowed
         Because autonomous transitions to L3 are not supported, only the 
         L3 triggered from CPE shall be supported. 
         The integer values 0 (no L2, no L3), 
                            1 (L2, no L3), 
                            2 (no L2, L3) and
                            3 (L2, L3) can be set.

         ALCATEL NOTE:
             ACCESS:   NA                  USAGE:    OPT
             PERSIST:  YES                 INSRVMOD: YES
             RANGE:    0..3                DEFVALUE: NA
             UNITS:    NA                  SPARSE:   NA
             DESCR:    NA "
        DEFVAL          {0}
::= {xdslLineSpectrumProfileEntry 16}

xdslLineL0Time          OBJECT-TYPE
        SYNTAX          INTEGER
        ACCESS          read-write
        STATUS          mandatory
        DESCRIPTION     
        "This object specifies the minimum time between an exit from the L2
         state and the next entry into the L2 state. 

         ALCATEL NOTE:
             ACCESS:   NA                  USAGE:    OPT
             PERSIST:  YES                 INSRVMOD: YES
             RANGE:    0..1800             DEFVALUE: NA
             UNITS:    seconds             SPARSE:   NA
             DESCR:    NA "
        DEFVAL          {255}
::= {xdslLineSpectrumProfileEntry 17}

xdslLineL2Time          OBJECT-TYPE
        SYNTAX          INTEGER
        ACCESS          read-write
        STATUS          mandatory
        DESCRIPTION     
        "This object specifies the time between L2 entry and first power trim
         or between two consecutive power trims. 

         ALCATEL NOTE:
             ACCESS:   NA                  USAGE:    OPT
             PERSIST:  YES                 INSRVMOD: YES
             RANGE:    0..1800             DEFVALUE: NA
             UNITS:    seconds             SPARSE:   NA
             DESCR:    NA "
        DEFVAL          {60}
::= {xdslLineSpectrumProfileEntry 18}

xdslLineL2Atpr          OBJECT-TYPE
        SYNTAX          INTEGER
        ACCESS          read-write
        STATUS          mandatory
        DESCRIPTION     
        "This object specifies the maximum aggregate transmit power reduction
         that can be performed in the L2 Request or through a single power trim 
         in the L2 state. It is expressed in dB.

         ALCATEL NOTE:
             ACCESS:   NA                  USAGE:    OPT
             PERSIST:  YES                 INSRVMOD: YES
             RANGE:    0..31               DEFVALUE: NA
             UNITS:    dB                  SPARSE:   NA
             DESCR:    NA "
        DEFVAL          {3}
::= {xdslLineSpectrumProfileEntry 19}

xdslLineSpectrumProfileRowStatus       OBJECT-TYPE
        SYNTAX          RowStatus
        ACCESS          read-write
        STATUS          mandatory
        DESCRIPTION 
        "This object is used to create a new row or delete an existing row in
         this table. The usage is as per standard semantics of 'RowStatus'
         defined in SNMPv2-TC.
            o Both 'createAndGo' and 'createAndWait' options of row creation
              are supported.
            o The entry associated with a Profile that is being used may
              not be deleted.

         ALCATEL NOTE:
             ACCESS:   NA                  USAGE:    MAND
             PERSIST:  YES                 INSRVMOD: YES
             RANGE:    NA                  DEFVALUE: NA
             UNITS:    NA                  SPARSE:   NA
             DESCR:    NA "
::= {xdslLineSpectrumProfileEntry 20}

xdslLineSpectrumProfileModifyStatus OBJECT-TYPE
        SYNTAX          INTEGER {
                            modifyStart (1),
                            modifyCancel (2),
                            modifyComplete (3)
                        }
        ACCESS          read-write
        STATUS          mandatory 
        DESCRIPTION 
        "This variable is used to modify a line spectrum profile after
         it has been created.
         The following values are defined:
          - modifyStart (1): set by the manager to enable the
            modification of the parameters of the spectrum profile.
          - modifyCancel (2): set by the manager to stop the profile
            modification and cancel all changes. The original profile
            settings are maintained.
          - modifyComplete (3): used by the manager to activate the
            changes and replace the old profile. The modification of the
            spectrum profile parameters (other than name, scope, version) 
            is disabled.
            The system will also set the 
            xdslLineSpectrumProfileModifyStatus value to 'modifyComplete'
            after a modifyCancel request from the manager.
           See xdslLineSpectrumProfileIndex about the retrieval of the
           original or the updated profile setting values during the profile
           modification.

         ALCATEL NOTE:
             ACCESS:   NA                  USAGE:    OPT
             PERSIST:  YES                 INSRVMOD: YES
             RANGE:    NA                  DEFVALUE: NA
             UNITS:    NA                  SPARSE:   NA
             DESCR:    NA "
        DEFVAL          {modifyComplete}
 ::= {xdslLineSpectrumProfileEntry 21}

xdslLineL2AtprT         OBJECT-TYPE
        SYNTAX          INTEGER
        ACCESS          read-write
        STATUS          mandatory
        DESCRIPTION     
        "This object specifies the total maximum aggregate transmit power
         reduction that can be performed in the L2 state. This is the sum of 
         all reductions of L2 Request and power trims in the L2 state. It is
         expressed in dB.

         ALCATEL NOTE:
             ACCESS:   NA                  USAGE:    OPT
             PERSIST:  YES                 INSRVMOD: YES
             RANGE:    0..31               DEFVALUE: NA
             UNITS:    dB                  SPARSE:   NA
             DESCR:    NA "
        DEFVAL          {31}
::= {xdslLineSpectrumProfileEntry 22}

xdslLineRAUNoiseMarginDownstream       OBJECT-TYPE
        SYNTAX          INTEGER
        ACCESS          read-write
        STATUS          mandatory
        DESCRIPTION      
        "This object specifies the Downstream Upshift Noise Margin for Rate
         Adaptation. If the downstream noise margin is above the Downstream
         Upshift Noise Margin and stays above that for more than the time
         specified by the Downstream Minimum Upshift Rate Adaptation Interval, 
         the XTU R shall attempt to increase the downstream net data rate. It 
         is expressed in dB.
         Range: 0 to 31 dB in steps of 0.1 dB. The Downstream Upshift Noise 
         Margin is represented as 1/10 * xdslLineRAUNoiseMarginDownstream.

         ALCATEL NOTE:
             ACCESS:   NA                  USAGE:    OPT
             PERSIST:  YES                 INSRVMOD: YES
             RANGE:    0..310              DEFVALUE: NA
             UNITS:    dB / 10             SPARSE:   NA
             DESCR:    NA "
        DEFVAL          {70}           
::= {xdslLineSpectrumProfileEntry 23}

xdslLineRAUNoiseMarginUpstream         OBJECT-TYPE
        SYNTAX          INTEGER
        ACCESS          read-write
        STATUS          mandatory
        DESCRIPTION      
        "This object specifies the Upstream Upshift Noise Margin for Rate
         Adaptation. If the upstream noise margin is above the Upstream Upshift
         Noise Margin and stays above that for more than the time specified by
         the Upstream Minimum Upshift Rate Adaptation Interval, the XTU C shall
         attempt to increase the upstream net data rate. It is expressed in dB.
         Range: 0 to 31 dB in steps of 0.1 dB. The Upstream Upshift Noise 
         Margin is represented as 1/10 * xdslLineRAUNoiseMarginUpstream.

         ALCATEL NOTE:
             ACCESS:   NA                  USAGE:    OPT
             PERSIST:  YES                 INSRVMOD: YES
             RANGE:    0..310              DEFVALUE: NA
             UNITS:    dB / 10             SPARSE:   NA
             DESCR:    NA "
        DEFVAL          {70}           
::= {xdslLineSpectrumProfileEntry 24}

xdslLineRAUTimeDownstream              OBJECT-TYPE
        SYNTAX          INTEGER
        ACCESS          read-write
        STATUS          mandatory
        DESCRIPTION      
        "This object specifies the Downstream Minimum Upshift Rate Adaptation
         Interval. This is the interval of time the downstream noise margin 
         should stay above the Downstream Upshift Noise Margin before the XTU R 
         shall attempt to increase the downstream net data rate.

         ALCATEL NOTE:
             ACCESS:   NA                  USAGE:    OPT
             PERSIST:  YES                 INSRVMOD: YES
             RANGE:    0..16383            DEFVALUE: NA
             UNITS:    seconds             SPARSE:   NA
             DESCR:    NA "
        DEFVAL          {300}           
::= {xdslLineSpectrumProfileEntry 25}

xdslLineRAUTimeUpstream OBJECT-TYPE
        SYNTAX          INTEGER
        ACCESS          read-write
        STATUS          mandatory
        DESCRIPTION      
        "This object specifies the Upstream Minimum Upshift Rate Adaptation
         Interval. This is the interval of time the upstream noise margin 
         should stay above the Upstream Upshift Noise Margin before the XTU C 
         shall attempt to increase the upstream net data rate.

         ALCATEL NOTE:
             ACCESS:   NA                  USAGE:    OPT
             PERSIST:  YES                 INSRVMOD: YES
             RANGE:    0..16383            DEFVALUE: NA
             UNITS:    seconds             SPARSE:   NA
             DESCR:    NA "
        DEFVAL          {300}           
::= {xdslLineSpectrumProfileEntry 26}

xdslLineRADNoiseMarginDownstream       OBJECT-TYPE
        SYNTAX          INTEGER
        ACCESS          read-write
        STATUS          mandatory
        DESCRIPTION      
        "This object specifies the Downstream Downshift Noise Margin for Rate
         Adaptation. If the downstream noise margin is below the Downstream
         Downshift Noise Margin and stays below that for more than the time
         specified by the Downstream Minimum Downshift Rate Adaptation 
         Interval, the XTU R shall attempt to decrease the downstream net data 
         rate. It is expressed in dB.
         Range: 0 to 31 dB in steps of 0.1 dB. The Downstream Downshift Noise
         Margin is represented as 1/10 * xdslLineRADNoiseMarginDownstream.

         ALCATEL NOTE:
             ACCESS:   NA                  USAGE:    OPT
             PERSIST:  YES                 INSRVMOD: YES
             RANGE:    0..310              DEFVALUE: NA
             UNITS:    dB / 10             SPARSE:   NA
             DESCR:    NA "
        DEFVAL          {20} 
::= {xdslLineSpectrumProfileEntry 27}

xdslLineRADNoiseMarginUpstream         OBJECT-TYPE
        SYNTAX          INTEGER
        ACCESS          read-write
        STATUS          mandatory
        DESCRIPTION      
        "This object specifies the Upstream Downshift Noise Margin for Rate
         Adaptation. If the upstream noise margin is below the Upstream
         Downshift Noise Margin and stays below that for more than the time
         specified by the Upstream Minimum Downshift Rate Adaptation Interval,
         the XTU C shall attempt to decrease the upstream net data rate. It is 
         expressed in dB.
         Range: 0 to 31 dB in steps of 0.1 dB. The Upstream Downshift Noise
         Margin is represented as 1/10 * xdslLineRADNoiseMarginUpstream.

         ALCATEL NOTE:
             ACCESS:   NA                  USAGE:    OPT
             PERSIST:  YES                 INSRVMOD: YES
             RANGE:    0..310              DEFVALUE: NA
             UNITS:    dB / 10             SPARSE:   NA
             DESCR:    NA "
        DEFVAL          {20}           
::= {xdslLineSpectrumProfileEntry 28}

xdslLineRADTimeDownstream              OBJECT-TYPE
        SYNTAX          INTEGER
        ACCESS          read-write
        STATUS          mandatory
        DESCRIPTION      
        "This object specifies the Downstream Minimum Downshift Rate Adaptation
         Interval. This is the interval of time the downstream noise margin 
         should stay below the Downstream Downshift Noise Margin before the XTU
         R shall attempt to decrease the downstream net data rate.

         ALCATEL NOTE:
             ACCESS:   NA                  USAGE:    OPT
             PERSIST:  YES                 INSRVMOD: YES
             RANGE:    0..16383            DEFVALUE: NA
             UNITS:    seconds             SPARSE:   NA
             DESCR:    NA "
        DEFVAL          {30}           
::= {xdslLineSpectrumProfileEntry 29}

xdslLineRADTimeUpstream OBJECT-TYPE
        SYNTAX          INTEGER
        ACCESS          read-write
        STATUS          mandatory
        DESCRIPTION      
        "This object specifies the Upstream Minimum Downshift Rate Adaptation
         Interval. This is the interval of time the upstream noise margin 
         should stay below the Upstream Downshift Noise Margin before the XTU C 
         shall attempt to decrease the upstream net data rate.

         ALCATEL NOTE:
             ACCESS:   NA                  USAGE:    OPT
             PERSIST:  YES                 INSRVMOD: YES
             RANGE:    0..16383            DEFVALUE: NA
             UNITS:    seconds             SPARSE:   NA
             DESCR:    NA "
        DEFVAL          {30}           
::= {xdslLineSpectrumProfileEntry 30}

xdslLineArtificialNoisePsdDownstream         OBJECT-TYPE
        SYNTAX          ArtificialNoisePsdDownType
        ACCESS          read-write
        STATUS          mandatory
        DESCRIPTION     
        "This object specifies the transmitter-referred artificial noise level
         to be used as additional noise source at the downstream transmitter.
         A number of 2 to 32 Artificial Noise PSD points can be specified
         downstream.
         An empty sequence means that no artificial noise shall be used.
         The successive PSD points must have increasing (>/=) frequencies.
         It is allowed that for two successive PSD points, different PSD
         levels are defined at a same frequency (brickwall).
         Artificial Noise PSD points are defined in the range -140dBm/Hz..-40 
         dBm/Hz.
         A special value (-167,5 dBm/Hz) states no artificial noise has to be
         applied.
         The Artificial Noise PSD Shape is coded as a variable length octet string
         defined as follows:
         Octet 0: reserved 
         Octet 1..3: defines PSD point #1
         OCTETS 1..2: INTEGER (0..30000), frequency of PSD point #1,
         expressed in kHz. The value is defined as MSB-LSB (big-endian).
         OCTET 3: INTEGER (0..200,255), -2*(40 + PSD level) (in dBm/Hz) of
         PSD point#1.
         OCTETS 4..6: define the frequency and PSD level of PSD point #2.
         ....        up to
         OCTETS 3*N-2..3*N: define the frequency and PSD level of the last PSD
         point #N with N<=32.

         ALCATEL NOTE:
             ACCESS:   NA                  USAGE:    OPT
             PERSIST:  YES                 INSRVMOD: YES
             RANGE:    0..97               DEFVALUE: NA
             UNITS:    octets              SPARSE:   NA
             DESCR:    NA "
        DEFVAL              {''H}
::= {xdslLineSpectrumProfileEntry 31}

xdslLineSpectrumProfileAdslAdsl2Table  OBJECT-TYPE
        SYNTAX          SEQUENCE OF XdslLineSpectrumProfileAdslAdsl2Entry
        ACCESS          not-accessible
        STATUS          mandatory
        DESCRIPTION     
        "This table is part of the line profile. It contains the line
         related parameters of the modem configuration that apply to the ADSL
         and/or ADSL2 operational modes and use specific values for these modes
         of operation. These parameters are ignored in case another operational
         mode is used.

         ALCATEL NOTE:
             TABLESIZE: 256                    
             DESCR:     NA                   "
::= {xdslLineSpectrumProfile 2}

xdslLineSpectrumProfileAdslAdsl2Entry  OBJECT-TYPE
        SYNTAX          XdslLineSpectrumProfileAdslAdsl2Entry
        ACCESS          not-accessible
        STATUS          mandatory
        DESCRIPTION     
        "Each entry consists of a list of line related parameters that serve 
         to configure an XDSL modem in case the ADSL or ADSL2 modes of
         operation are used.

         Row creation : When an entry is created in the 
                        xdslLineSpectrumProfileTable, an entry with the same 
                        xdslLineSpectrumIndex is created in this table.
         Row deletion : When an entry is deleted from the
                        xdslLineSpectrumProfileTable, the entry with the same
                        xdslLineSpectrumIndex is deleted from this table.  "
        INDEX          {xdslLineSpectrumProfileIndex}
::= {xdslLineSpectrumProfileAdslAdsl2Table 1}

XdslLineSpectrumProfileAdslAdsl2Entry ::=
        SEQUENCE {
            adslModemFeatures                         INTEGER,
            adslMaxAggregatePowerLevelDownstream      INTEGER,
            adslMaxAggregatePowerLevelUpstream        INTEGER,
            adslMaxPsdLevelDownstream                 INTEGER,
            adslMaxPsdLevelUpstream                   INTEGER,
            adslPsdShapeDownstream                    AdslPsdDownstreamType,
            adslCustomPsdShapeDownstream              CustomPsdShapeType, 
            adslPsdShapeUpstream                      AdslPsdUpstreamType,
            adslCustomPsdShapeUpstream                CustomPsdShapeType,
            adslPboModeUpstream                       PboModeType,
            adslMaxRxAggregatePowerLevelUpstream      INTEGER
        }
       
adslModemFeatures       OBJECT-TYPE
        SYNTAX          INTEGER (0..4294967295)
        ACCESS          read-write
        STATUS          mandatory 
        DESCRIPTION 
        "This object allows to enable/disable specific features of the modem.
         It is a bitmap represented as a sum and allows multiple features to be
         configured simultaneously.
         Bitmap values:
         1   Strict compliancy, the modem should turn off all
             features not strictly compliant with the standards.
             The modem is allowed to use proprietary features when
             bit 0 is set to 0.
          Each other bit definition can be found in the modem-TRS.

         ALCATEL NOTE:
             ACCESS:   NA                  USAGE:    OPT
             PERSIST:  YES                 INSRVMOD: YES
             RANGE:    0..4294967295       DEFVALUE: 1
             UNITS:    NA                  SPARSE:   NA
             DESCR:    NA "
::= {xdslLineSpectrumProfileAdslAdsl2Entry 1}

adslMaxAggregatePowerLevelDownstream   OBJECT-TYPE
        SYNTAX          INTEGER
        ACCESS          read-write
        STATUS          mandatory
        DESCRIPTION     
        "This parameter indicates the maximum power allowed on 
         the line for the downstream direction. If the necessary power level 
         exceeds the level given by this parameter the modem will reinitialize.  
         The aggregate power has a range of 0 dBm to +25.5 dBm in steps of 0.1
         dB. It is represented as 1/10 * adslMaxAggregatePowerLevelDownstream.
         In case the corresponding DSL standard imposes a more stringent value
         for this parameter, the configured value will be ignored and the
         standard value will apply.

         ALCATEL NOTE:
             ACCESS:   NA                  USAGE:    OPT
             PERSIST:  YES                 INSRVMOD: NA
             RANGE:    0..255              DEFVALUE: 255
             UNITS:    dBm / 10            SPARSE:   NA
             DESCR:    NA "
::=  {xdslLineSpectrumProfileAdslAdsl2Entry 2}
        
adslMaxAggregatePowerLevelUpstream     OBJECT-TYPE
        SYNTAX          INTEGER
        ACCESS          read-write
        STATUS          mandatory
        DESCRIPTION     
        "This parameter indicates the maximum power allowed on the line for the 
         upstream direction. If the necessary power level exceeds the level 
         given by this parameter the modem will re-initialize. 
         The aggregate power has a range of 0 dBm to +25.5 dBm in steps of 0.1
         dB. It is represented as 1/10 * adslMaxAggregatePowerLevelUpstream.
         In case the corresponding DSL standard imposes a more stringent value
         for this parameter, the configured value will be ignored and the
         standard value will be used.

         ALCATEL NOTE:
             ACCESS:   NA                  USAGE:    OPT
             PERSIST:  YES                 INSRVMOD: YES
             RANGE:    0..255              DEFVALUE: 255
             UNITS:    dBm / 10            SPARSE:   NA
             DESCR:    NA "
::=  {xdslLineSpectrumProfileAdslAdsl2Entry 3}

adslMaxPsdLevelDownstream              OBJECT-TYPE
        SYNTAX          INTEGER
        ACCESS          read-write
        STATUS          mandatory
        DESCRIPTION     
        "This object gives the power spectral density allowed on the line
         for the downstream band. A lower value results in reduction of 
         power consumption, by paying the price of having a lower capacity. 
         It is expressed in dBm/Hz.
         When a PSD shape is configured, this parameter can be used to specify
         an additional constraint on the max PSD level.
         The PSD has a range of -60 dBm/Hz to -40 dBm/Hz in steps of 0.1 dB.
         It is represented as 1/10* xdslLineMaxPsdLevelDownstream.
         In case the corresponding DSL standard imposes a more stringent value
         for this parameter, the configured value will be ignored and the
         standard value will apply.

         ALCATEL NOTE:
             ACCESS:   NA                  USAGE:    OPT
             PERSIST:  YES                 INSRVMOD: YES
             RANGE:    -600..-400          DEFVALUE: -400
             UNITS:    dBm/Hz * 1/10       SPARSE:   NA
             DESCR:    NA "
::= {xdslLineSpectrumProfileAdslAdsl2Entry 4}

adslMaxPsdLevelUpstream                OBJECT-TYPE
        SYNTAX          INTEGER
        ACCESS          read-write
        STATUS          mandatory
        DESCRIPTION     
        "This object gives the power spectral density (in dBm/Hz) allowed on 
         the line for the upstream band. A lower value results in reduction of 
         power consumption, by paying the price of having a lower capacity. 
         It is expressed in dBm/Hz.
         When a PSD shape is configured, this parameter can be used to specify
         an additional constraint on the max PSD level.
         The PSD has a range of -60 dBm/Hz to -38 dBm/Hz in steps of 0.1 dB.
         It is represented as 1/10* xdslLineMaxPsdLevelUpstream.
         In case the corresponding DSL standard imposes a more stringent value
         for this parameter, the configured value will be ignored and the
         standard value will apply.

         ALCATEL NOTE:
             ACCESS:   NA                  USAGE:    OPT
             PERSIST:  YES                 INSRVMOD: YES
             RANGE:    -600..-380          DEFVALUE: -380
             UNITS:    dBm/Hz * 1/10       SPARSE:   NA
             DESCR:    NA "
::= {xdslLineSpectrumProfileAdslAdsl2Entry 5}

adslPsdShapeDownstream                 OBJECT-TYPE
        SYNTAX          AdslPsdDownstreamType
        ACCESS          read-write
        STATUS          mandatory
        DESCRIPTION     
        "This parameter defines the PSD shape that must be applied for ADSL
         in the downstream direction.
         adslCustomPsdDownstream: a custom PSD Shape is defined in
         adslCustomPsdShapeDownstream.
         adslStdPsdDownstream: the standard PSD shape is applied.

         ALCATEL NOTE:
             ACCESS:   NA                  USAGE:    OPT
             PERSIST:  YES                 INSRVMOD: YES
             RANGE:    adslStdPsdDownstream 
             DEFVALUE: adslStdPsdDownstream
             UNITS:    NA                  SPARSE:   NA
             DESCR:    The object is supported to avoid future database 
                       migration but should not be set.
                       Set requests will be rejected (badvalue) if the value
                       differs from the default value. "
::= {xdslLineSpectrumProfileAdslAdsl2Entry 6}

adslCustomPsdShapeDownstream           OBJECT-TYPE
        SYNTAX          CustomPsdShapeType 
        ACCESS          read-write
        STATUS          mandatory
        DESCRIPTION     
        "This object specifies PSD points of a custom ADSL PSD Shape for
         the downstream direction in case adslPsdShapeDownstream =
         adslCustomPsdDownstream and it will be ignored otherwise.
         A number of 2 to 20 PSD points can be specified.
         The successive PSD points must have increasing (>/=) frequencies.
         It is allowed that for two successive PSD points, different PSD
         levels are defined at a same frequency (brickwall).
         The custom PSD Shape is coded as a variable length octet string
         defined as follows:
         OCTET 0: defines the frequency scale to be used for the interpolation
         of the PSD Shape data (0x00= linear frequency scale,
         0x01 = logarithmic frequency scale).
         OCTETS 1..2: INTEGER (0..1104), frequency of the first PSD point
         expressed in kHz. The value is defined as MSB-LSB (big-endian).
         OCTET 3: INTEGER (0..255), -2*PSD level (in dBm/Hz) of the first
         PSD point.  Only PSD values within the standard range from
         -95 to 0 dBm/Hz are guaranteed
         OCTETS 4..6: define the frequency and PSD level of PSD point 2.
         ....        up to
         OCTETS 3*N-2..3*N: define the frequency and PSD level of the last PSD
         point N with N<=20.

         ALCATEL NOTE:
             ACCESS:   NA                  USAGE:    OPT
             PERSIST:  YES                 INSRVMOD: YES
             RANGE:    0                   DEFVALUE: ''H
             UNITS:    OCTETS              SPARSE:   NA
             DESCR:    The object is supported to avoid future database 
                       migration but should not be set.
                       Set requests will be rejected (badvalue) if the value
                       differs from the default value. "
::= {xdslLineSpectrumProfileAdslAdsl2Entry 7}

adslPsdShapeUpstream    OBJECT-TYPE
        SYNTAX          AdslPsdUpstreamType
        ACCESS          read-write
        STATUS          mandatory
        DESCRIPTION     
        "This parameter defines the PSD Shape that must be applied for ADSL
         in the upstream direction.
         adslCustomPsdUpstream: a custom PSD Shape is defined in
         adslCustomPsdShapeUpstream.
         adslStdPsdUpstream: the standard PSD shape is applied. For the
         mode AnnexM or AnnexJ, it corresponds to adslPsdMask56Upstream.
         adslPsdMask32Upstream, ....adslPsdMask64Upstream: selection of standard 
         PSD masks for Annex M (EU-xx) and Annex J (ADLU-xx) with maximum 
         carrier index 32, .... 64 respectively.

         ALCATEL NOTE:
             ACCESS:   NA                  USAGE:    OPT
             PERSIST:  YES                 INSRVMOD: YES
             RANGE: adslStdPsdUpstream,
                    adslPsdMask32Upstream,
                    ..., 
                    adslPsdMask64Upstream  
                                           DEFVALUE: adslStdPsdUpstream
             UNITS:    NA                  SPARSE:   NA
             DESCR:    The object is used for annex M and annex J upstream PSD 
                       selection. For boards not supporting upstream PSD 
                       selection only the adslStdPsdUpstream default value is 
                       valid. "
::= {xdslLineSpectrumProfileAdslAdsl2Entry 8}

adslCustomPsdShapeUpstream             OBJECT-TYPE
        SYNTAX          CustomPsdShapeType 
        ACCESS          read-write
        STATUS          mandatory
        DESCRIPTION     
        "This object specifies PSD points of a custom ADSL PSD Shape for
         the upstream direction in case adslPsdShapeUpstream =
         adslCustomPsdUpstream and it will be ignored otherwise.
         A number of 2 to 20 points can be specified.
         The successive PSD points must have increasing (>/=) frequencies.
         It is allowed that for two successive PSD points, different PSD
         levels are defined at a same frequency (brickwall).
         The custom PSD Shape is coded as a variable length octet string
         defined as follows:
         OCTET 0: defines the frequency scale to be used for the interpolation
         of the PSD Shape data (0x00= linear frequency scale,
         0x01 = logarithmic frequency scale).
         OCTETS 1..2: INTEGER (0..1104), frequency of the first PSD point
         expressed in kHz. The value is defined as MSB-LSB (big-endian).
         OCTET 3: INTEGER (0..255), represents -2*PSD level (in dBm/Hz)
         of the first PSD point.  Only PSD values within the standard range 
         from -95 to 0 dBm/Hz are guaranteed
         OCTETS 4..6:  define the frequency and PSD level of PSD point 2.
         ....        up to
         OCTETS 3*N-2..3*N: define the frequency and PSD level of the last PSD
         point N with N<=20.

         ALCATEL NOTE:
             ACCESS:   NA                  USAGE:    OPT
             PERSIST:  YES                 INSRVMOD: YES
             RANGE:    0                   DEFVALUE: ''H
             UNITS:    OCTETS              SPARSE:   NA
             DESCR:    The object is supported to avoid future database 
                       migration but should not be set.
                       Set requests will be rejected (badvalue) if the value
                       differs from the default value. "
::= {xdslLineSpectrumProfileAdslAdsl2Entry 9}

adslPboModeUpstream     OBJECT-TYPE
        SYNTAX          PboModeType
        ACCESS          read-write
        STATUS          mandatory
        DESCRIPTION     
        "Identifies the upstream power backoff mode.
         pboModeOff: upstream power backoff is OFF, no power cutback is applied
            by the receiver.
         pboModeOn: upstream power backoff is ON, upstream power cutback is
            requested if the RX aggregate power exceeds the max RX aggregate
            power (adslMaxRxAggregatePowerUpstream).
         All other pbo modes are rejected.

         ALCATEL NOTE:
             ACCESS:   NA                        USAGE:    OPT
             PERSIST:  YES                       INSRVMOD: YES
             RANGE:    pboModeOff, pboModeOn     DEFVALUE: pboModeOff
             UNITS:    NA                        SPARSE:   NA
             DESCR:    NA "
::= {xdslLineSpectrumProfileAdslAdsl2Entry 10}

adslMaxRxAggregatePowerLevelUpstream   OBJECT-TYPE
        SYNTAX          INTEGER
        ACCESS          read-write
        STATUS          mandatory
        DESCRIPTION     
        "This parameter indicates the maximum receive power allowed on the line
         for the upstream direction.
         The aggregate power has a range of -25.5 dBm to +25.5 dBm in steps of
         0.1 dB. It is represented as 1/10 * adslMaxRxAggregatePowerUpstream.

         ALCATEL NOTE:
             ACCESS:   NA                  USAGE:    OPT
             PERSIST:  YES                 INSRVMOD: YES
             RANGE:    -255..255           DEFVALUE: 255
             UNITS:    dBm / 10            SPARSE:   NA
             DESCR:    NA "
::= {xdslLineSpectrumProfileAdslAdsl2Entry 11}

xdslLineSpectrumProfileReAdsl2Table    OBJECT-TYPE
        SYNTAX          SEQUENCE OF XdslLineSpectrumProfileReAdsl2Entry
        ACCESS          not-accessible
        STATUS          mandatory
        DESCRIPTION     
        "This table is part of the line profile. It contains the line
         related parameters of the modem configuration that apply to the
         READSL2 operational mode and use specific values for this mode of
         operation. These parameters are ignored in case another operational
         mode is used.

         ALCATEL NOTE:
             TABLESIZE: 256                   
             DESCR:     NA                   "
::= {xdslLineSpectrumProfile 3}

xdslLineSpectrumProfileReAdsl2Entry    OBJECT-TYPE
        SYNTAX          XdslLineSpectrumProfileReAdsl2Entry
        ACCESS          not-accessible
        STATUS          mandatory
        DESCRIPTION     
        "Each entry consists of a list of line related parameters that serve 
         to configure an XDSL modem in case the READSL2 mode of operation is
         used.

         Row creation : When an entry is created in the 
                        xdslLineSpectrumProfileTable, an entry with the same 
                        xdslLineSpectrumIndex is created in this table.
         Row deletion : When an entry is deleted from the
                        xdslLineSpectrumProfileTable, the entry with the same
                        xdslLineSpectrumIndex is deleted from this table.  "
        INDEX          {xdslLineSpectrumProfileIndex}
::= {xdslLineSpectrumProfileReAdsl2Table 1}

XdslLineSpectrumProfileReAdsl2Entry ::=
        SEQUENCE {
            reAdsl2ModemFeatures                      INTEGER,
            reAdsl2MaxAggregatePowerLevelDownstream   INTEGER,
            reAdsl2MaxAggregatePowerLevelUpstream     INTEGER,
            reAdsl2MaxPsdLevelDownstream              INTEGER,
            reAdsl2MaxPsdLevelUpstream                INTEGER,
            reAdsl2PsdShapeDownstream                 ReAdsl2PsdDownstreamType,
            reAdsl2CustomPsdShapeDownstream           CustomPsdShapeType,
            reAdsl2PsdShapeUpstream                   ReAdsl2PsdUpstreamType,
            reAdsl2CustomPsdShapeUpstream             CustomPsdShapeType,
            reAdsl2PboModeUpstream                    PboModeType,
            reAdsl2MaxRxAggregatePowerLevelUpstream   INTEGER
        }

reAdsl2ModemFeatures    OBJECT-TYPE
        SYNTAX          INTEGER (0..4294967295)
        ACCESS          read-write
        STATUS          mandatory 
        DESCRIPTION 
        "This object allows to enable/disable specific features of the modem.
         It is a bitmap represented as a sum and allows multiple features to be
         configured simultaneously. 
         Bitmap values:
          1   Strict compliancy, the modem should turn off all features not
              strictly compliant with the standards.
              The modem is allowed to use proprietary features when
              bit 0 is set to 0.
          Each other bit definition can be found in the modem-TRS.

         ALCATEL NOTE:
             ACCESS:   NA                  USAGE:    OPT
             PERSIST:  YES                 INSRVMOD: YES
             RANGE:    0..4294967295       DEFVALUE: 1
             UNITS:    NA                  SPARSE:   NA
             DESCR:    NA "
::= {xdslLineSpectrumProfileReAdsl2Entry 1}

reAdsl2MaxAggregatePowerLevelDownstream          OBJECT-TYPE
        SYNTAX          INTEGER
        ACCESS          read-write
        STATUS          mandatory
        DESCRIPTION     
        "This parameter indicates the maximum power allowed on 
         the line for the downstream direction. If the necessary power level 
         exceeds the level given by this parameter the modem will re-
         initialize.  
         The aggregate power has a range of 0 dBm to +25.5 dBm in steps of 0.1
         dB.
         It is represented as 1/10 * reAdsl2MaxAggregatePowerLevelDownstream.
         In case the corresponding DSL standard imposes a more stringent value
         for this parameter, the configured value will be ignored and the
         standard value will apply.

         ALCATEL NOTE:
             ACCESS:   NA                  USAGE:    OPT
             PERSIST:  YES                 INSRVMOD: YES
             RANGE:    0..255              DEFVALUE: 255
             UNITS:    dBm / 10            SPARSE:   NA
             DESCR:    NA "
::= {xdslLineSpectrumProfileReAdsl2Entry 2}

reAdsl2MaxAggregatePowerLevelUpstream  OBJECT-TYPE
        SYNTAX          INTEGER
        ACCESS          read-write
        STATUS          mandatory
        DESCRIPTION     
        "This parameter indicates the maximum power allowed on the line for the 
         upstream direction. If the necessary power level exceeds the level 
         given by this parameter the modem will re-initialize. 
         The aggregate power has a range of 0 dBm to 25.5 dBm in steps of 0.1
         dB.
         It is represented as 1/10 * reAdsl2MaxAggregatePowerLevelUpstream.
         In case the corresponding DSL standard imposes a more stringent value
         for this parameter, the configured value will be ignored and the
         standard value will apply.

         ALCATEL NOTE:
             ACCESS:   NA                  USAGE:    OPT
             PERSIST:  YES                 INSRVMOD: YES
             RANGE:    0..255              DEFVALUE: 255
             UNITS:    dBm / 10            SPARSE:   NA
             DESCR:    NA "
::= {xdslLineSpectrumProfileReAdsl2Entry 3}

reAdsl2MaxPsdLevelDownstream           OBJECT-TYPE
        SYNTAX          INTEGER
        ACCESS          read-write
        STATUS          mandatory
        DESCRIPTION     
        "This object gives the power spectral density allowed on the line
         for the downstream band. A lower value results in reduction of 
         power consumption, by paying the price of having a lower capacity. 
         It is expressed in dBm/Hz.
         When a PSD shape is configured, this parameter can be used to specify
         an additional constraint on the max PSD level.
         The PSD has a range of -60 dBm/Hz to -37 dBm/Hz in steps of 0.1 dB.
         It is represented as 1/10* reAdsl2MaxPsdLevelDownstream.
         In case the corresponding DSL standard imposes a more stringent value
         for this parameter, the configured value will be ignored and the
         standard value will apply.

         ALCATEL NOTE:
             ACCESS:   NA                  USAGE:    OPT
             PERSIST:  YES                 INSRVMOD: YES
             RANGE:    -600..-370          DEFVALUE: -370
             UNITS:    dBm/Hz * 1/10       SPARSE:   NA
             DESCR:    NA "
::= {xdslLineSpectrumProfileReAdsl2Entry 4}

reAdsl2MaxPsdLevelUpstream             OBJECT-TYPE
        SYNTAX          INTEGER
        ACCESS          read-write
        STATUS          mandatory
        DESCRIPTION     
        "This object gives the power spectral density allowed on the line
         for the upstream band. A lower value results in reduction of 
         power consumption, by paying the price of having a lower capacity. 
         It is expressed in dBm/Hz.
         When a PSD shape is configured, this parameter can be used to specify
         an additional constraint on the max PSD level.
         The PSD has a range of -60 dBm/Hz to -32.9 dBm/Hz in steps of 0.1 dB.
         It is represented as 1/10* reAdsl2MaxPsdLevelUpstream.
         In case the corresponding DSL standard imposes a more stringent value
         for this parameter, the configured value will be ignored and the
         standard value will apply.

         ALCATEL NOTE:
             ACCESS:   NA                  USAGE:    OPT
             PERSIST:  YES                 INSRVMOD: YES
             RANGE:    -600..-329          DEFVALUE: -329
             UNITS:    dBm/Hz * 1/10       SPARSE:   NA
             DESCR:    NA "
::= {xdslLineSpectrumProfileReAdsl2Entry 5}

reAdsl2PsdShapeDownstream              OBJECT-TYPE
        SYNTAX          ReAdsl2PsdDownstreamType
        ACCESS          read-write
        STATUS          mandatory
        DESCRIPTION     
        "This parameter defines the PSD Shape that must be applied for READSL2
         in the downstream direction.
         reAdsl2CustomPsdDownstream: a custom PSD Shape is defined in
         reAdsl2CustomPsdShapeDownstream.
         reAdsl2StdPsdDownstream: the standard PSD shape is applied.

         ALCATEL NOTE:
             ACCESS:   NA                  USAGE:    OPT
             PERSIST:  YES                 INSRVMOD: YES
             RANGE:    reAdsl2StdPsdDownstream 
             DEFVALUE: reAdsl2StdPsdDownstream
             UNITS:    NA                  SPARSE:   NA
             DESCR:    The object is supported to avoid future database 
                       migration but should not be set.
                       Set requests will be rejected (badvalue) if the value
                       differs from the default value. "
::= {xdslLineSpectrumProfileReAdsl2Entry 6}

reAdsl2CustomPsdShapeDownstream        OBJECT-TYPE
        SYNTAX          CustomPsdShapeType 
        ACCESS          read-write
        STATUS          mandatory
        DESCRIPTION     
        "This object specifies PSD points of a custom READSL2 PSD Shape for
         the downstream direction in case reAdsl2PsdShapeDownstream =
         reAdsl2CustomPsdDownstream and it will be ignored otherwise.
         A number of 2 to 20 PSD points can be specified.
         The successive PSD points must have increasing (>/=) frequencies.
         It is allowed that for two successive PSD points, different PSD
         levels are defined at a same frequency (brickwall).
         The custom PSD Shape is coded as a variable length octet string
         defined as follows:
         OCTET 0: defines the frequency scale to be used for the interpolation
         of the PSD Shape data (0x00= linear frequency scale,
         0x01 = logarithmic frequency scale).
         OCTETS 1..2: INTEGER (0..2208), frequency of the first PSD point
         expressed in kHz. The value is defined as MSB-LSB (big-endian).
         OCTET 3: INTEGER (0..255), -2*PSD level (in dBm/Hz) of the first
         PSD point.  Only PSD values within the standard range from
         -95 to 0 dBm/Hz are guaranteed
         OCTETS 4..6: define the frequency and PSD level of PSD point 2.
         ....       up to
         OCTETS 3*N-2..3*N: define the frequency and PSD level of the last PSD
         point N with N<=20.

         ALCATEL NOTE:
             ACCESS:   NA                  USAGE:    OPT
             PERSIST:  YES                 INSRVMOD: YES
             RANGE:    0                   DEFVALUE: ''H
             UNITS:    OCTETS              SPARSE:   NA
             DESCR:    The object is supported to avoid future database 
                       migration but should not be set.
                       Set requests will be rejected (badvalue) if the value
                       differs from the default value. "
::= {xdslLineSpectrumProfileReAdsl2Entry 7}

reAdsl2PsdShapeUpstream                OBJECT-TYPE
        SYNTAX          ReAdsl2PsdUpstreamType
        ACCESS          read-write
        STATUS          mandatory
        DESCRIPTION     
        "This parameter defines the PSD Shape that must be applied for READSL2
         in the upstream direction.
         reAdsl2CustomPsdUpstream: a custom PSD Shape is defined in
         reAdsl2CustomPsdShapeUpstream.
         reAdsl2StdPsdUpstream: the standard PSD shape is applied.

         ALCATEL NOTE:
             ACCESS:   NA                  USAGE:    OPT
             PERSIST:  YES                 INSRVMOD: YES
             RANGE:    reAdsl2StdPsdUpstream
             DEFVALUE: reAdsl2StdPsdUpstream
             UNITS:    NA                  SPARSE:   NA
             DESCR:    The object is supported to avoid future database 
                       migration but should not be set.
                       Set requests will be rejected (badvalue) if the value
                       differs from the default value. "
::= {xdslLineSpectrumProfileReAdsl2Entry 8}

reAdsl2CustomPsdShapeUpstream          OBJECT-TYPE
        SYNTAX          CustomPsdShapeType 
        ACCESS          read-write
        STATUS          mandatory
        DESCRIPTION     
        "This object specifies PSD points of a custom READSL2 PSD Shape for
         the upstream direction in case reAdsl2PsdShapeUpstream =
         reAdsl2CustomPsdUpstream and it will be ignored otherwise.
         A number of 2 to 20 points can be specified.
         The successive PSD points must have increasing (>/=) frequencies.
         It is allowed that for two successive PSD points, different PSD
         levels are defined at a same frequency (brickwall).
         The custom PSD Shape is coded as a variable length octet string
         defined as follows:
         OCTET 0: defines the frequency scale to be used for the interpolation
         of the PSD Shape data (0x00= linear frequency scale,
         0x01 = logarithmic frequency scale).
         OCTETS 1..2: INTEGER (0..2208), frequency of the first PSD point
         expressed in kHz. The value is defined as MSB-LSB (big-endian).
         OCTET 3: INTEGER (0..255), represents -2*PSD level (in dBm/Hz)
         of the first PSD point.  Only PSD values within the standard range 
         from -95 to 0 dBm/Hz are guaranteed
         OCTETS 4..6:  define the frequency and PSD level of PSD point 2.
         ....       up to
         OCTETS 3*N-2..3*N: define the frequency and PSD level of the last PSD
         point N with N<=20.

         ALCATEL NOTE:
             ACCESS:   NA                  USAGE:    OPT
             PERSIST:  YES                 INSRVMOD: YES
             RANGE:    0                   DEFVALUE: ''H
             UNITS:    OCTETS              SPARSE:   NA
             DESCR:    The object is supported to avoid future database 
                       migration but should not be set.
                       Set requests will be rejected (badvalue) if the value
                       differs from the default value. "
::= {xdslLineSpectrumProfileReAdsl2Entry 9}

reAdsl2PboModeUpstream  OBJECT-TYPE
        SYNTAX          PboModeType
        ACCESS          read-write
        STATUS          mandatory
        DESCRIPTION     
        "Identifies the upstream PSD power backoff mode.
         pboModeOff: upstream power backoff is OFF, no power cutback is applied
         by the receiver.
         pboModeOn: upstream power backoff is ON, upstream power cutback is
         requested if the RX aggregate power exceeds the max RX aggregate power
         (reAdsl2MaxRxAggregatePowerUpstream).
         All other pbo modes are rejected.

         ALCATEL NOTE:
             ACCESS:   NA                        USAGE:    OPT
             PERSIST:  YES                       INSRVMOD: YES
             RANGE:    pboModeOff, pboModeOn     DEFVALUE: pboModeOff
             UNITS:    NA                        SPARSE:   NA
             DESCR:    NA "
::= {xdslLineSpectrumProfileReAdsl2Entry 10}

reAdsl2MaxRxAggregatePowerLevelUpstream     OBJECT-TYPE
        SYNTAX          INTEGER
        ACCESS          read-write
        STATUS          mandatory
        DESCRIPTION     
        "This parameter indicates the maximum receive power allowed on the line
         for the upstream direction.
         The aggregate power has a range of -25.5 dBm to +25.5 dBm in steps of
         0.1 dB. 
         It is represented as 1/10 * reAdsl2MaxRxAggregatePowerUpstream.

         ALCATEL NOTE:
             ACCESS:   NA                  USAGE:    OPT
             PERSIST:  YES                 INSRVMOD: YES
             RANGE:    -255..255           DEFVALUE: 255
             UNITS:    dBm / 10            SPARSE:   NA
             DESCR:    NA "
::= {xdslLineSpectrumProfileReAdsl2Entry 11}

xdslLineSpectrumProfileAdsl2PlusTable  OBJECT-TYPE
        SYNTAX          SEQUENCE OF XdslLineSpectrumProfileAdsl2PlusEntry
        ACCESS          not-accessible
        STATUS          mandatory
        DESCRIPTION     
        "This table is part of the line profile. It contains the line
         related parameters of the modem configuration that apply to the ADSL2
         Plus operational mode and use specific values for this mode of
         operation. These parameters are ignored in case another operational
         mode is used.

         ALCATEL NOTE:
             TABLESIZE: 256                    
             DESCR:     NA                   "
::= {xdslLineSpectrumProfile 4}

xdslLineSpectrumProfileAdsl2PlusEntry  OBJECT-TYPE
        SYNTAX          XdslLineSpectrumProfileAdsl2PlusEntry
        ACCESS          not-accessible
        STATUS          mandatory
        DESCRIPTION     
        "Each entry consists of a list of line related parameters that serve 
         to configure an XDSL modem in case the ADSL2 Plus mode of operation is
         used.

         Row creation : When an entry is created in the 
                        xdslLineSpectrumProfileTable, an entry with the same 
                        xdslLineSpectrumIndex is created in this table.
         Row deletion : When an entry is deleted from the
                        xdslLineSpectrumProfileTable, the entry with the same
                        xdslLineSpectrumIndex is deleted from this table.  "
        INDEX          {xdslLineSpectrumProfileIndex}
::= {xdslLineSpectrumProfileAdsl2PlusTable 1}

XdslLineSpectrumProfileAdsl2PlusEntry ::=
        SEQUENCE {
            adsl2PlusModemFeatures                    INTEGER,
            adsl2PlusMaxAggregatePowerLevelDownstream INTEGER,
            adsl2PlusMaxAggregatePowerLevelUpstream   INTEGER,
            adsl2PlusMaxPsdLevelDownstream            INTEGER,
            adsl2PlusMaxPsdLevelUpstream              INTEGER,
            adsl2PlusPsdShapeDownstream             Adsl2PlusPsdDownstreamType,
            adsl2PlusCustomPsdShapeDownstream         CustomPsdShapeType,
            adsl2PlusPsdShapeUpstream                 Adsl2PlusPsdUpstreamType,
            adsl2PlusCustomPsdShapeUpstream           CustomPsdShapeType,
            adsl2PlusPboModeUpstream                  PboModeType,
            adsl2PlusMaxRxAggregatePowerLevelUpstream INTEGER
        }

adsl2PlusModemFeatures                 OBJECT-TYPE
        SYNTAX      INTEGER (0..4294967295)
        ACCESS      read-write
        STATUS      mandatory 
        DESCRIPTION 
        "This object allows to enable/disable specific features of the modem.
         It is a bitmap represented as a sum and allows multiple features to be
         configured simultaneously. 
         Bitmap values:
          1   Strict compliancy, the modem should turn off all features not
              strictly compliant with the standards.
              The modem is allowed to use proprietary features when
              bit 0 is set to 0.
          Each other bit definition can be found in the modem-TRS.

         ALCATEL NOTE:
             ACCESS:   NA                  USAGE:    OPT
             PERSIST:  YES                 INSRVMOD: YES
             RANGE:    0..4294967295       DEFVALUE: 1
             UNITS:    NA                  SPARSE:   NA
             DESCR:    NA "
::= {xdslLineSpectrumProfileAdsl2PlusEntry 1}

adsl2PlusMaxAggregatePowerLevelDownstream        OBJECT-TYPE
        SYNTAX          INTEGER
        ACCESS          read-write
        STATUS          mandatory
        DESCRIPTION     
        "This parameter indicates the maximum power allowed on 
         the line for the downstream direction. If the necessary power level 
         exceeds the level given by this parameter the modem will re-
         initialize.  
         The aggregate power has a range of 0 dBm to 25.5 dBm in steps of 0.1
         dB.
         It is represented as 1/10 * adsl2PlusMaxAggregatePowerLevelDownstream.
         In case the corresponding DSL standard imposes a more stringent value
         for this parameter, the configured value will be ignored and the
         standard value will apply.

         ALCATEL NOTE:
             ACCESS:   NA                  USAGE:    OPT
             PERSIST:  YES                 INSRVMOD: YES
             RANGE:    0..255              DEFVALUE: 255
             UNITS:    dBm / 10            SPARSE:   NA
             DESCR:    NA "
::= {xdslLineSpectrumProfileAdsl2PlusEntry 2}

adsl2PlusMaxAggregatePowerLevelUpstream          OBJECT-TYPE
        SYNTAX          INTEGER
        ACCESS          read-write
        STATUS          mandatory
        DESCRIPTION     
        "This parameter indicates the maximum power allowed on the line for the 
         upstream direction. If the necessary power level exceeds the level 
         given by this parameter the modem will re-initialize. 
         The aggregate power has a range of 0 dBm to +25.5 dBm in steps of 0.1
         dB.
         It is represented as 1/10 * adsl2PlusMaxAggregatePowerLevelUpstream.
         In case the corresponding DSL standard imposes a more stringent value
         for this parameter, the configured value will be ignored and the
         standard value will apply.

         ALCATEL NOTE:
             ACCESS:   NA                  USAGE:    OPT
             PERSIST:  YES                 INSRVMOD: YES
             RANGE:    0..255              DEFVALUE: 255
             UNITS:    dBm / 10            SPARSE:   NA
             DESCR:    NA "
::= {xdslLineSpectrumProfileAdsl2PlusEntry 3}

adsl2PlusMaxPsdLevelDownstream         OBJECT-TYPE
        SYNTAX          INTEGER
        ACCESS          read-write
        STATUS          mandatory
        DESCRIPTION     
        "This object gives the power spectral density allowed on the line
         for the downstream band. A lower value results in reduction of 
         power consumption, by paying the price of having a lower capacity. 
         It is expressed in dBm/Hz.
         When a PSD shape is configured, this parameter can be used to specify
         an additional constraint on the max PSD level.
         The PSD has a range of -60 dBm/Hz to -40 dBm/Hz in steps of 0.1 dB.
         It is represented as 1/10* adsl2PlusMaxPsdLevelDownstream.
         In case the corresponding DSL standard imposes a more stringent value
         for this parameter, the configured value will be ignored and the
         standard value will apply.

         ALCATEL NOTE:
             ACCESS:   NA                  USAGE:    OPT
             PERSIST:  YES                 INSRVMOD: YES
             RANGE:    -600..-400          DEFVALUE: -400
             UNITS:    dBm/Hz * 1/10       SPARSE:   NA
             DESCR:    NA "
::= {xdslLineSpectrumProfileAdsl2PlusEntry 4}

adsl2PlusMaxPsdLevelUpstream           OBJECT-TYPE
        SYNTAX          INTEGER
        ACCESS          read-write
        STATUS          mandatory
        DESCRIPTION     
        "This object gives the power spectral density allowed on the line
         for the upstream band. A lower value results in reduction of 
         power consumption, by paying the price of having a lower capacity. 
         It is expressed in dBm/Hz.
         When a PSD shape is configured, this parameter can be used to specify
         an additional constraint on the max PSD level.
         The PSD has a range of -60 dBm/Hz to -38 dBm/Hz in steps of 0.1 dB.
         It is represented as 1/10* adsl2PlusMaxPsdLevelUpstream.
         In case the corresponding DSL standard imposes a more stringent value
         for this parameter, the configured value will be ignored and the
         standard value will apply.

         ALCATEL NOTE:
             ACCESS:   NA                  USAGE:    OPT
             PERSIST:  YES                 INSRVMOD: YES
             RANGE:    -600..-380          DEFVALUE: -380
             UNITS:    dBm/Hz * 1/10       SPARSE:   NA
             DESCR:    NA "
::= {xdslLineSpectrumProfileAdsl2PlusEntry 5}

adsl2PlusPsdShapeDownstream            OBJECT-TYPE
        SYNTAX          Adsl2PlusPsdDownstreamType
        ACCESS          read-write
        STATUS          mandatory
        DESCRIPTION     
        "This parameter defines the PSD Shape that must be applied for ADSL2+
         in the downstream direction.
         adsl2PlusCustomPsdDownstream: a custom PSD Shape is defined in
         adsl2PlusCustomPsdShapeDownstream.
         adsl2PlusStdPsdDownstream: the standard PSD mask for central office
         deployment is applied.
         adsl2PlusCa100PsdDownstream, adsl2PlusCa110PsdDownstream,....
         adsl2PlusCa280PsdDownstream: selection of PSD masks for cabinet
         deployment whith cut-off frequencies at carrier 100, 110, .... 280
         respectively.

         ALCATEL NOTE:
             ACCESS:   NA                  USAGE:    OPT
             PERSIST:  YES                 INSRVMOD: YES
             RANGE:    NA                  DEFVALUE: adsl2PlusStdPsdDownstream
             UNITS:    NA                  SPARSE:   NA
             DESCR:    NA "
::= {xdslLineSpectrumProfileAdsl2PlusEntry 6}

adsl2PlusCustomPsdShapeDownstream      OBJECT-TYPE
        SYNTAX          CustomPsdShapeType 
        ACCESS          read-write
        STATUS          mandatory
        DESCRIPTION     
        "This object specifies PSD points of a custom ADSL+ PSD Shape for
         the downstream direction in case adsl2PlusPsdShapeDownstream =
         adsl2PlusCustomPsdDownstream and it will be ignored otherwise.
         A number of 2 to 20 PSD points can be specified.
         The successive PSD points must have increasing (>/=) frequencies.
         It is allowed that for two successive PSD points, different PSD
         levels are defined at a same frequency (brickwall).
         The custom PSD Shape is coded as a variable length octet string
         defined as follows:
         OCTET 0: reserved, fixed value 0x00 when PSD points specified
         OCTETS 1..2: INTEGER (0..2208), frequency of the first PSD point
         expressed in kHz. The value is defined as MSB-LSB (big-endian).
         OCTET 3: INTEGER (0..255), -2*PSD level (in dBm/Hz) of the first
         PSD point.  Only PSD values within the standard range  from -95 
         to 0 dBm/Hz are guaranteed.
         OCTETS 4..6: define the frequency and PSD level of PSD point 2.
         ....       up to
         OCTETS 3*N-2..3*N: define the frequency and PSD level of the last PSD
         point N with N<=20.

         ALCATEL NOTE:
             ACCESS:   NA                  USAGE:    OPT
             PERSIST:  YES                 INSRVMOD: YES
             RANGE:    0..61               DEFVALUE: ''H
             UNITS:    OCTETS              SPARSE:   NA
             DESCR:    NA "
::= {xdslLineSpectrumProfileAdsl2PlusEntry 7}

adsl2PlusPsdShapeUpstream              OBJECT-TYPE
        SYNTAX          Adsl2PlusPsdUpstreamType
        ACCESS          read-write
        STATUS          mandatory
        DESCRIPTION     
        "This parameter defines the PSD Shape that must be applied for ADSL+
         in the upstream direction.
         adsl2PlusCustomPsdUpstream: a custom PSD Shape is defined in
         adsl2PlusCustomPsdShapeUpstream.
         adsl2PlusStdPsdUpstream: the standard PSD shape is applied. For the
         mode AnnexM or AnnexJ, it corresponds to adsl2plusPsdMask56Upstream.
         adsl2plusMask32Upstream, .... adsl2plusMask64Upstream: selection of 
         standard PSD masks for Annex M (EU-xx) and Annex J (ADLU-xx) with 
         maximum carrier index 32, .... 64 respectively.

         ALCATEL NOTE:
             ACCESS:   NA                  USAGE:    OPT
             PERSIST:  YES                 INSRVMOD: YES
             RANGE:    adsl2PlusStdPsdUpstream,
                       adsl2PlusPsdMask32Upstream,
                       ..., 
                       adsl2PlusPsdMask64Upstream  
             DEFVALUE: adsl2PlusStdPsdUpstream
             UNITS:    NA                  SPARSE:   NA
             DESCR:    The object is used for annex M and annex J upstream PSD 
                       selection. For boards not supporting upstream PSD 
                       selection only the adsl2PlustdPsdUpstream default value 
                       is valid. "
::= {xdslLineSpectrumProfileAdsl2PlusEntry 8}

adsl2PlusCustomPsdShapeUpstream        OBJECT-TYPE
        SYNTAX          CustomPsdShapeType 
        ACCESS          read-write
        STATUS          mandatory
        DESCRIPTION     
        "This object specifies PSD points of a custom ADSL+ PSD Shape for
         the upstream direction in case adsl2PlusPsdShapeUpstream =
         adsl2PlusCustomPsdUpstream and it will be ignored otherwise.
         A number of 2 to 20 points can be specified.
         The successive PSD points must have increasing (>/=) frequencies.
         It is allowed that for two successive PSD points, different PSD
         levels are defined at a same frequency (brickwall).
         The custom PSD Shape is coded as a variable length octet string
         defined as follows:
         OCTET 0: reserved, fixed value 0x00 when PSD points specified 
         OCTETS 1..2: INTEGER (0..2208), frequency of the first PSD point
         expressed in kHz. The value is defined as MSB-LSB (big-endian).
         OCTET 3: INTEGER (0..255), represents -2*PSD level (in dBm/Hz)
         of the first PSD point.  Only PSD values within the standard range 
         from -95 to 0 dBm/Hz are guaranteed.
         OCTETS 4..6:  define the frequency and PSD level of PSD point 2.
         ....       up to
         OCTETS 3*N-2..3*N: define the frequency and PSD level of the last PSD
         point N with N<=20.

         ALCATEL NOTE:
             ACCESS:   NA                  USAGE:    OPT
             PERSIST:  YES                 INSRVMOD: YES
             RANGE:    0                   DEFVALUE: ''H
             UNITS:    OCTETS              SPARSE:   NA
             DESCR:    The object is supported to avoid future database 
                       migration but should not be set.
                       Set requests will be rejected (badvalue) if the value
                       differs from the default value. "
::= {xdslLineSpectrumProfileAdsl2PlusEntry 9}

adsl2PlusPboModeUpstream               OBJECT-TYPE
        SYNTAX          PboModeType
        ACCESS          read-write
        STATUS          mandatory
        DESCRIPTION     
        "Identifies the upstream PSD power backoff mode.
         pboModeOff: upstream power backoff is OFF, no power cutback is applied
         by the receiver.
         pboModeOn: upstream power backoff is ON, upstream power cutback is
         requested if the RX aggregate power exceeds the max RX aggregate power
         (adsl2PlusMaxRxAggregatePowerUpstream).
         All other pbo modes are rejected.

         ALCATEL NOTE:
             ACCESS:   NA                        USAGE:    OPT
             PERSIST:  YES                       INSRVMOD: YES
             RANGE:    pboModeOff, pboModeOn     DEFVALUE: pboModeOff
             UNITS:    NA                        SPARSE:   NA
             DESCR:    NA "
::= {xdslLineSpectrumProfileAdsl2PlusEntry 10}

adsl2PlusMaxRxAggregatePowerLevelUpstream       OBJECT-TYPE
        SYNTAX          INTEGER
        ACCESS          read-write
        STATUS          mandatory
        DESCRIPTION     
        "This parameter indicates the maximum receive power allowed on the line
         for the upstream direction.
         The aggregate power has a range of -25.5 dBm to +25.5 dBm in steps of
         0.1 dB.
         It is represented as 1/10 * adsl2PlusMaxRxAggregatePowerUpstream.

         ALCATEL NOTE:
             ACCESS:   NA                  USAGE:    OPT
             PERSIST:  YES                 INSRVMOD: YES
             RANGE:    -255..255           DEFVALUE: 255
             UNITS:    dBm / 10            SPARSE:   NA
             DESCR:    NA "
::= {xdslLineSpectrumProfileAdsl2PlusEntry 11}

xdslLineSpectrumProfileVdslTable       OBJECT-TYPE
        SYNTAX          SEQUENCE OF XdslLineSpectrumProfileVdslEntry
        ACCESS          not-accessible
        STATUS          mandatory
        DESCRIPTION     
        "This table is part of the line profile. It contains the line
         related parameters of the modem configuration that apply to the VDSL
         operational modes (VDSL1 and VDSL2). 
         It contains two types of parameters:
         - The common VDSL parameters that apply to VDSL1 and VDSL2 operational
           modes and have the same value. These parameters are ignored in case
           an ADSL operational mode is used.
         - The VDSL1 specific parameters that contain values only applicable to
           VDSL1 operational modes. These parameters are ignored in case
           another operational mode is used.
         The VDSL2 operational modes also use specific parameters, these are
         included in the xdslLineSpectrumProfileVdsl2Table.

         ALCATEL NOTE:
             TABLESIZE: 256                    
             DESCR:     NA                   "
::= {xdslLineSpectrumProfile 5}

xdslLineSpectrumProfileVdslEntry       OBJECT-TYPE
        SYNTAX          XdslLineSpectrumProfileVdslEntry
        ACCESS          not-accessible
        STATUS          mandatory
        DESCRIPTION     
        "Each entry consists of a list of line related parameters that serve 
         to configure an XDSL modem in case the VDSL mode of operation is
         used (VDSL1 or VDSL2).

         Row creation : When an entry is created in the 
                        xdslLineSpectrumProfileTable, an entry with the same 
                        xdslLineSpectrumIndex is created in this table.
         Row deletion : When an entry is deleted from the
                        xdslLineSpectrumProfileTable, the entry with the same
                        xdslLineSpectrumIndex is deleted from this table.  "
        INDEX          {xdslLineSpectrumProfileIndex}
::= {xdslLineSpectrumProfileVdslTable 1}

XdslLineSpectrumProfileVdslEntry ::=
        SEQUENCE {
            vdslModemFeatures                         INTEGER,
            vdslBandPlan                              VdslBandPlanType,
            vdslBandPlanCFx                           FrequencyType,
            vdslCustomBandPlan                        OCTET STRING,
            vdslOptBandUsage                          OptBandUsageType,
            vdslAdslBandUsage                         INTEGER,
            vdslMaxAggregatePowerLevelDownstream      INTEGER,
            vdslMaxAggregatePowerLevelUpstream        INTEGER,
            vdslPsdShapeDownstream                    VdslPsdDownstreamType,
            vdslCustomPsdShapeDownstream              CustomPsdShapeType,
            vdslPsdShapeUpstream                      VdslPsdUpstreamType,
            vdslCustomPsdShapeUpstream                CustomPsdShapeType,
            vdslPboModeUpstream                       PboModeType,
            vdslRxPsdShapeUpstream                    VdslRxPsdUpstreamType,
            vdslCustomRxPsdShapeUpstream              CustomPsdShapeType,
            vdslOptBandEndFreq                        INTEGER,
            vdslAdslBandEndFreq                       INTEGER,
            vdslGhsTonesTxPowerControl                INTEGER,
            vdslGhsTonesTxPowerControlA43             INTEGER,
            vdslGhsTonesTxPowerControlB43             INTEGER,
            vdslGhsTonesTxPowerControlA43c            INTEGER,
            vdslGhsTonesTxPowerControlV43             INTEGER,
            vdslGhsTonesTxPowerLevelA43               INTEGER,
            vdslGhsTonesTxPowerLevelB43               INTEGER,
            vdslGhsTonesTxPowerLevelA43c              INTEGER,
            vdslGhsTonesTxPowerLevelV43               INTEGER,
            vdslMaxBandNumber                         INTEGER,
            vdslMaxFrequency                          FrequencyType,
            vdslMaxPsdLevelDownstream                 INTEGER,
            vdslMaxPsdLevelUpstream                   INTEGER,
            vdslPsdPboParamAUpstream                  PerBandABParamType,
            vdslPsdPboParamBUpstream                  PerBandABParamType,
            vdslOptBandStartFreq                      INTEGER
        }

vdslModemFeatures       OBJECT-TYPE
        SYNTAX          INTEGER  (0..4294967295)
        ACCESS          read-write
        STATUS          mandatory 
        DESCRIPTION 
        "VDSL1 specific, this object allows to enable/disable specific features
         of the modem.
         It is a bitmap represented as a sum and allows multiple features to be
         configured simultaneously. 
         Bitmap values:
          1   Strict compliancy, the modem should turn off all features not
              strictly compliant with the standards.
              The modem is allowed to use proprietary features when
              bit 0 is set to 0.
          Each other bit definition can be found in the modem-TRS.
         ALCATEL NOTE:
             ACCESS:   NA                  USAGE:    OPT
             PERSIST:  YES                 INSRVMOD: YES
             RANGE:    0..4294967295       DEFVALUE: 1
             UNITS:    NA                  SPARSE:   NA
             DESCR:    NA "
::= {xdslLineSpectrumProfileVdslEntry 1}
       
vdslBandPlan            OBJECT-TYPE
        SYNTAX          VdslBandPlanType
        ACCESS          read-write
        STATUS          mandatory
        DESCRIPTION     
        "Common to VDSL1/VDSL2, this object specifies the VDSL band plan:
         bandPlanCustom: a custom bandplan is defined in vdslCustomBandPlan.
         bandPlanA4:      4 bands 998 band plan (Bandplan-A in ITU-T G.993.1)
         bandPlanA3:      3 bands 998 band plan
         bandPlanA2:      2 bands 998 band plan
         bandPlanB4:      4 bands 997 band plan (Bandplan-B in ITU-T G.993.1)
         bandPlanB3:      3 bands 997 band plan
         bandPlanB2:      2 bands 997 band plan
         bandPlanC4:      4 bands Fx band plan (Bandplan-C in ITU-T G.993.1)
                           This plan uses a variable frequency Fx specified
                           in vdslBandPlanCFx.
         bandPlanC3:      3 bands Fx band plan
         bandPlanC2:      2 bands Fx band plan
         bandPlanChinaA3:  3 bands China band plan 1. 
         bandPlanChinaA2:  2 bands China band plan 1. 
         bandPlanChinaB3:  3 bands China band plan 2. 
         bandPlanChinaB2:  2 bands China band plan 2.
         bandPlanAU2ext:    
         band plan 998 with US2 band extended to 30 MHz.
         bandPlanAnnexA998:    ITU-T G993.2 VDSL2 Annex A (998 extended) band plan 
         bandPlanAnnexB997e:   ITU-T G993.2 VDSL2 Annex B band plan type 997E
         bandPlanAnnexB998e:   ITU-T G993.2 VDSL2 Annex B band plan type 998E 
         bandPlanAnnexB998ade: ITU-T G993.2 VDSL2 Annex B band plan type 998ADE 
         bandPlanAnnexBhpe:    ITU-T G993.2 VDSL2 Annex B band plan type HPE 
         bandPlanAnnexC:       ITU-T G993.2 VDSL2 Annex C band plan 

         ALCATEL NOTE:
             ACCESS:   NA                  USAGE:    OPT
             PERSIST:  YES                 INSRVMOD: YES
             RANGE:    bandplanA4, bandplanA3, bandplanA2, 
                       bandplanB4, bandplanB3, bandplanB2,
                       bandPlanAnnexA998, bandPlanAnnexB997e,
                       bandPlanAnnexB998e, bandPlanAnnexB998ade,
                       bandPlanAnnexBhpe 
             DEFVALUE: bandPlanA4
             UNITS:    NA                  SPARSE:   NA
             DESCR:    NA  "
::= {xdslLineSpectrumProfileVdslEntry 2}

vdslBandPlanCFx         OBJECT-TYPE
        SYNTAX          FrequencyType
        ACCESS          read-write
        STATUS          mandatory
        DESCRIPTION     
        "Common to VDSL1/VDSL2, this object specifies Fx in case of band
         plan C, ignored otherwise.

         ALCATEL NOTE:
             ACCESS:   NA                  USAGE:    OPT
             PERSIST:  YES                 INSRVMOD: YES
             RANGE:    0                   DEFVALUE: 0
             UNITS:    kHz                 SPARSE:   NA
             DESCR:    The object is supported to avoid future database 
                       migration but should not be set.
                       Set requests will be rejected (badvalue) if the value
                       differs from the default value. "
::= {xdslLineSpectrumProfileVdslEntry 3}

vdslCustomBandPlan      OBJECT-TYPE
        SYNTAX          OCTET STRING (SIZE (0..40))
        ACCESS          read-write
        STATUS          mandatory
        DESCRIPTION     
        "Common to VDSL1/VDSL2, this object defines a custom band plan when
         vdslBandPlan = bandPlanCustom, ignored otherwise.
         Up to 8 bands (upstream + downstream) are configurable.
         The custom band plan is coded as a variable length octet string
         defined as follows:
         OCTET 0..4 define the characteristics of BAND #1:
         OCTET 0-1: INTEGER (0..30000), start frequency of band 1 expressed
                    in kHz. The value is defined as MSB-LSB (big-endian).
         OCTET 2-3: INTEGER (0..30000), stop frequency of band 1 expressed
                    in kHz. The value is defined as MSB-LSB (big-endian).
         OCTET 4:    indicates the direction of the band (0x00= downstream,
                    0x01 = upstream).
         OCTET 5-9: Idem, define the characteristics of band #2.
         ....       up to
         OCTETS (N-1)*5..(N*5)-1: define the characteristics of the last
                    BAND #N with N<=8.

         ALCATEL NOTE:
             ACCESS:   NA                  USAGE:    OPT
             PERSIST:  YES                 INSRVMOD: YES
             RANGE:    0                   DEFVALUE: ''H
             UNITS:    octets              SPARSE:   NA
             DESCR:    The object is supported to avoid future database 
                       migration but should not be set.
                       Set requests will be rejected (badvalue) if the value
                       differs from the default value. "
::= {xdslLineSpectrumProfileVdslEntry 4}

vdslOptBandUsage        OBJECT-TYPE
        SYNTAX          OptBandUsageType
        ACCESS          read-write
        STATUS          mandatory
        DESCRIPTION     
        "Common to VDSL1/VDSL2, this object indicates if the XDSL is allowed
         to use the optional band or not and defines its direction in case 
         allowed. 
                 The optional band start frequency is by default 25kHz on POTS boards
         and 120 kHz on ISDN boards, unless configured otherwise via        
         vdslOptBandStartFreq.
         The optional band end frequency is by default 138 kHz on POTS boards and
         276 kHz on ISDN boards, unless configured otherwise via vdslOptBandEndFreq.
         The optional band usage is independent from the ADSL Band usage
         parameter.
         In case the ADSL band usage is not allowed and the optional band usage 
         is allowed, the modem is allowed to use the optional band.
         optBandOff:        usage of optional band is not allowed.
         optBandUpstream:   optional band can be used for upstream.
         optBandDownstream: optional band can be used for downstream.

         ALCATEL NOTE:
             ACCESS:   NA                  USAGE:    OPT
             PERSIST:  YES                 INSRVMOD: YES
             RANGE:    NA                  DEFVALUE: optBandOff
             UNITS:    NA                  SPARSE:   NA
             DESCR:    NA "
::= {xdslLineSpectrumProfileVdslEntry 5}

vdslAdslBandUsage       OBJECT-TYPE
        SYNTAX          INTEGER
        ACCESS          read-write
        STATUS          mandatory
        DESCRIPTION     
        "Common to VDSL1/VDSL2, this object Specifies whether the XDSL is
         allowed or not to use the given ADSL spectrum.
         0: usage of ADSL spectrum is allowed.
         1: usage of the ADSL (25kHz - 1.1Mhz) spectrum is not allowed.
         2: usage of the ADSL2+ (25kHz - 2.2Mhz)spectrum is not allowed.
         3: usage of the ADSL spectrum is not allowed until the ADSL
         frequency specfied in vdslAdslBandEndFreq.
         For VDSL, this controls the use of the ADSL spectrum portion within 
         the VDSL frequency plan defined in vdslBandPlan and vdslOptBandUsage.

         ALCATEL NOTE:
             ACCESS:   NA                  USAGE:    OPT
             PERSIST:  YES                 INSRVMOD: YES
             RANGE:    0..3                DEFVALUE: 1
             UNITS:    NA                  SPARSE:   NA
             DESCR:    NA "
::= {xdslLineSpectrumProfileVdslEntry 6}

vdslMaxAggregatePowerLevelDownstream   OBJECT-TYPE
        SYNTAX          INTEGER
        ACCESS          read-write
        STATUS          mandatory
        DESCRIPTION     
        "VDSL1 specific, this object indicates the maximum power allowed on 
         the line for the downstream direction. If the necessary power level 
         exceeds the level given by this parameter the modem will re-
         initialize.  
         The aggregate power has a range of -31 dBm to +25.5 dBm in steps of
         0.1 dB.
         It is represented as 1/10 * vdslMaxAggregatePowerLevelDownstream.

         ALCATEL NOTE:
             ACCESS:   NA                  USAGE:    OPT
             PERSIST:  YES                 INSRVMOD: YES
             RANGE:    -310..255           DEFVALUE: 255
             UNITS:    dBm / 10            SPARSE:   NA
             DESCR:    NA "
::= {xdslLineSpectrumProfileVdslEntry 7}

vdslMaxAggregatePowerLevelUpstream     OBJECT-TYPE
        SYNTAX          INTEGER
        ACCESS          read-write
        STATUS          mandatory
        DESCRIPTION     
        "VDSL1 specific, this object indicates the maximum power allowed on
         the line for the upstream direction. If the necessary power level
         exceeds the level given by this parameter the modem will re-
         initialize. 
         The aggregate power has a range of -31 dBm to +25.5 dBm in steps of 
         0.1 dB. 
         It is represented as 1/10 * vdslMaxAggregatePowerLevelUpstream .

         ALCATEL NOTE:
             ACCESS:   NA                  USAGE:    OPT
             PERSIST:  YES                 INSRVMOD: YES
             RANGE:    -310..255           DEFVALUE: 255
             UNITS:    dBm / 10            SPARSE:   NA
             DESCR:    NA "
::= {xdslLineSpectrumProfileVdslEntry 8}

vdslPsdShapeDownstream  OBJECT-TYPE
        SYNTAX          VdslPsdDownstreamType
        ACCESS          read-write
        STATUS          mandatory
        DESCRIPTION     
        "VDSL1 specific, this object defines the PSD Shape that must be applied
         for VDSL in the downstream direction.
         vdslCustomPsdDownstream: a custom PSD Shape is defined in
         vdslCustomPsdShapeDownstream.
         A predefined PSD (ANSI or ETSI)can be selected from the following
         list:
           vdslAnsiFttexM1PsdDownstream
           vdslAnsiFttexM2PsdDownstream
           vdslAnsiFttcabM1PsdDownstream
           vdslAnsiFttcabM2PsdDownstream
           vdslEtsiPexP1M1PsdDownstream
           vdslEtsiPexP1M2PsdDownstream
           vdslEtsiPexP2M1PsdDownstream
           vdslEtsiPexP2M2PsdDownstream
           vdslEtsiPcabM1PsdDownstream
           vdslEtsiPcabM2PsdDownstream
           vdslAnsiFttCabM1AdslPsdDownstream
           vdslAnsiFttCabM2AdslPsdDownstream
           vdslAnsiFttCabM1Adsl2PlusPsdDownstream
           vdslAnsiFttCabM2Adsl2PlusPsdDownstream
           vdslEtsiPcabXM1AdslPsdDownstream
           vdslEtsiPcabXM2AdslPsdDownstream
           vdslEtsiPcabM1Adsl2PlusPsdDownstream
           vdslEtsiPcabM2Adsl2PlusPsdDownstream
           vdslEtsiPexM2AdslSample1PsdDownstream
           vdslEtsiPexM2AdslSample2PsdDownstream
           vdslEtsiPexM2AdslSample3PsdDownstream
           vdslEtsiPexM2AdslSample4PsdDownstream

         ALCATEL NOTE:
             ACCESS:   NA                  USAGE:    OPT
             PERSIST:  YES                 INSRVMOD: YES
             RANGE:    NA           
             DEFVALUE: vdslEtsiPcabM1PsdDownstream
             UNITS:    NA                  SPARSE:   NA
             DESCR:    NA  "
::= {xdslLineSpectrumProfileVdslEntry 9}

vdslCustomPsdShapeDownstream           OBJECT-TYPE
        SYNTAX          CustomPsdShapeType 
        ACCESS          read-write
        STATUS          mandatory
        DESCRIPTION     
        "VDSL1 specific, this object specifies PSD points of a custom VDSL PSD
         Shape for the downstream direction in case vdslPsdShapeDownstream =
         vdslCustomPsdDownstream and it will be ignored otherwise.
         A number of 2 to 32 PSD points can be specified.
         The successive PSD points must have increasing (>/=) frequencies.
         It is allowed that for two successive PSD points, different PSD
         levels are defined at a same frequency (brickwall).
         The custom PSD Shape is coded as a variable length octet string
         defined as follows:
         OCTET 0: defines the characteristics (type and scale) of the PSD
         shape.
         OCTET 0- bit 0..1: defines the frequency scale to be used for the
         interpolation of the PSD Shape data (00= linear frequency scale,
         01 = logarithmic frequency scale).
         OCTET 0- bit 2..3: defines the type of the PSD shape (00= PSD mask,
         01= PSD template).
         Octet 1..3: defines PSD point #1
         OCTETS 1..2: INTEGER (0..30000), frequency of PSD point #1,
         expressed in kHz. The value is defined as MSB-LSB (big-endian).
         OCTET 3: INTEGER (0..255), -2*PSD level (in dBm/Hz) of
         PSD point#1.  Only PSD values within the standard range 
         from -95 to 0 dBm/Hz are guaranteed
         OCTETS 4..6: define the frequency and PSD level of PSD point #2.
         ....        up to
         OCTETS 3*N-2..3*N: define the frequency and PSD level of the last PSD
         point #N with N<=32.

         ALCATEL NOTE:
             ACCESS:   NA                  USAGE:    OPT
             PERSIST:  YES                 INSRVMOD: YES
             RANGE:    0..97               DEFVALUE: ''H
             UNITS:    octets              SPARSE:   NA
             DESCR:    NA "
::= {xdslLineSpectrumProfileVdslEntry 10}

vdslPsdShapeUpstream    OBJECT-TYPE
        SYNTAX          VdslPsdUpstreamType
        ACCESS          read-write
        STATUS          mandatory
        DESCRIPTION     
        "VDSL1 specific, this object defines the PSD Shape that must be applied
         for VDSL in the upstream direction.
         vdslCustomPsdUpstream: a custom PSD Shape is defined in
         vdslCustomPsdShapeUpstream.
         A predefined PSD (ANSI or ETSI)can be selected from the following 
         list:
           vdslAnsiFttexM1PsdUpstream
           vdslAnsiFttexM2PsdUpstream
           vdslAnsiFttcabM1PsdUpstream
           vdslAnsiFttcabM2PsdUpstream
           vdslEtsiPM1PsdUpstream
           vdslEtsiPM2PsdUpstream

         ALCATEL NOTE:
             ACCESS:   NA                  USAGE:    OPT
             PERSIST:  YES                 INSRVMOD: YES
             RANGE:    all, except vdslCustomPsdUpstream                  
             DEFVALUE: vdslEtsiPM1PsdUpstream
             UNITS:    NA                  SPARSE:   NA
             DESCR:    NA  "
::= {xdslLineSpectrumProfileVdslEntry 11}

vdslCustomPsdShapeUpstream             OBJECT-TYPE
        SYNTAX         CustomPsdShapeType 
        ACCESS          read-write
        STATUS          mandatory
        DESCRIPTION     
        "VDSL1 specific, this object specifies PSD points of a custom VDSL PSD
         Shape for the upstream direction in case vdslPsdShapeUpstream =
         vdslCustomPsdUpstream and it will be ignored otherwise.
         A number of 2 to 20 points can be specified.
         The successive PSD points must have increasing (>/=) frequencies.
         It is allowed that for two successive PSD points, different PSD
         levels are defined at a same frequency (brickwall).
         The custom PSD Shape is coded as a variable length octet string
         defined as follows:
         OCTET 0: defines the characteristics (type and scale) of the PSD 
         shape.
         OCTET 0- bit 0..1: defines the frequency scale to be used for the
         interpolation of the PSD Shape data (00= linear frequency scale,
         01 = logarithmic frequency scale).
         OCTET 0- bit 2..3: defines the type of the PSD shape (00= PSD mask,
         01= PSD template).
         Octet 1..3: defines PSD point #1
         OCTETS 1..2: INTEGER (0..30000), frequency of PSD point #1,
         expressed in kHz. The value is defined as MSB-LSB (big-endian).
         OCTET 3: INTEGER (0..255), -2*PSD level (in dBm/Hz) of
         PSD point#1.  Only PSD values within the standard range 
         from -95 to 0 dBm/Hz are guaranteed
         OCTETS 4..6: define the frequency and PSD level of PSD point #2.
         ....       up to
         OCTETS 3*N-2..3*N: define the frequency and PSD level of the last PSD
         point #N with N<=20.

         ALCATEL NOTE:
             ACCESS:   NA                  USAGE:    OPT
             PERSIST:  YES                 INSRVMOD: YES
             RANGE:    0                   DEFVALUE: ''H
             UNITS:    octets              SPARSE:   NA
             DESCR:    The object is supported to avoid future database 
                       migration but should not be set.
                       Set requests will be rejected (badvalue) if the value
                       differs from the default value. "
::= {xdslLineSpectrumProfileVdslEntry 12}

vdslPboModeUpstream     OBJECT-TYPE
        SYNTAX          PboModeType
        ACCESS          read-write
        STATUS          mandatory
        DESCRIPTION     
        "Common to VDSL1/VDSL2, this object identifies the upstream PSD power
         backoff mode.
         pboModeOff: upstream PSD power backoff is OFF i.e. the TX PSD is used.
         pboModeOn: upstream PSD power backoff is ON i.e. the PBO RX PSD
         Shape defined in vdslRxPsdShapeUpstream/vdsl2RxPsdShapeUpstream is
         used.
         pboModeOnPolicingShutdown: pbo mode ON and policing mechanism
         shuts down the line in case of non compliancy
         (activation-failure - CPE-Policing and Upbo-Violation alarms
         are raised)
         pboModeOnPolicingUS0Only: pbo mode ON and policing mechanism reduces
         US band usage to US0 only (Upbo-Violation alarm raised) 
         pboModeOnPolicingPassive: pbo mode ON and policing in passive mode 
         (Upbo-Violation raised)
         If VDSL2 pbo policing is enabled but is not supported by the line, 
         configuration should be rejected on the basis of board capabilities.
         If VDSL2 pbo policing is enabled and VDSL1 opmode is selected, then
         modem falls back silently to pboModeOn.

         ALCATEL NOTE:
             ACCESS:   NA                  USAGE:    OPT
             PERSIST:  YES                 INSRVMOD: YES
             RANGE:    NA                  DEFVALUE: pboModeOn
             UNITS:    NA                  SPARSE:   NA
             DESCR:    NA "
::= {xdslLineSpectrumProfileVdslEntry 13}

vdslRxPsdShapeUpstream  OBJECT-TYPE
        SYNTAX          VdslRxPsdUpstreamType
        ACCESS          read-write
        STATUS          mandatory
        DESCRIPTION     
        "VDSL1 specific, this object defines the reference Rx PSD Shape to be
        used for upstream power backoff.
        vdslCustomRxPsdUpstream: a custom reference Rx PSD Shape is defined
        in vdslCustomRxPsdShapeUpstream.
        A predefined standard or custom PSD can be selected from the following
        list:
          vdslAnsiARxPsdUpstream
          vdslAnsiFRxPsdUpstream
          vdslAnsiCustomExRxPsdUpstream
          vdslAnsiCustomCabRxPsdUpstream
          vdslEtsiARxPsdUpstream
          vdslEtsiBRxPsdUpstream
          vdslEtsiCRxPsdUpstream
          vdslEtsiDRxPsdUpstream
          vdslEtsiERxPsdUpstream
          vdslEtsiFRxPsdUpstream
          vdslEtsiCustomExRxPsdUpstream
          vdslEtsiCustomCabRxPsdUpstream
          vdslABParamRxPsdUpstream
        Other PSD are rejected.

         ALCATEL NOTE:
             ACCESS:   NA                  USAGE:    OPT
             PERSIST:  YES                 INSRVMOD: YES
             RANGE:    1..14               DEFVALUE: vdslEtsiARxPsdUpstream
             UNITS:    NA                  SPARSE:   NA
             DESCR:    NA  "
::= {xdslLineSpectrumProfileVdslEntry 14}

vdslCustomRxPsdShapeUpstream           OBJECT-TYPE
        SYNTAX          CustomPsdShapeType 
        ACCESS          read-write
        STATUS          mandatory
        DESCRIPTION     
        "VDSL1 specific, this object specifies PSD points of a custom reference
         receive VDSL PSD Shape for upstream power backoff in case
         vdslRxPsdShapeUpstream = vdslCustomRxPsdUpstream  and it will be 
         ignored otherwise. A number of 2 to 20 PSD points can be specified.
         The successive PSD points must have increasing (>/=) frequencies.
         It is allowed that for two successive PSD points, different PSD
         levels are defined at a same frequency (brickwall).
         The custom PSD Shape is coded as a variable length octet string
         defined as follows:
         OCTET 0: defines the characteristics (type and scale) of the PSD 
         shape.
         OCTET 0- bit 0..1: defines the frequency scale to be used for the
         interpolation of the PSD Shape data (00= linear frequency scale,
         01 = logarithmic frequency scale).
         OCTET 0- bit 2..3: defines the type of the PSD shape (00= PSD mask,
         01= PSD template).
         Octet 1..3: defines PSD point #1
         OCTETS 1..2: INTEGER (0..30000), frequency of PSD point #1,
         expressed in kHz. The value is defined as MSB-LSB (big-endian).
         OCTET 3: INTEGER (255..0), -2*PSD level (in dBm/Hz) of
         PSD point#1.
         OCTETS 4..6: define the frequency and PSD level of PSD point #2.
         ....       up to
         OCTETS 3*N-2..3*N: define the frequency and PSD level of the last PSD
         point #N with N<=20.

         ALCATEL NOTE:
             ACCESS:   NA                  USAGE:    OPT
             PERSIST:  YES                 INSRVMOD: YES
             RANGE:    0..61               DEFVALUE: ''H
             UNITS:    octets              SPARSE:   NA
             DESCR:    NA "
::= {xdslLineSpectrumProfileVdslEntry 15}

vdslOptBandEndFreq      OBJECT-TYPE
        SYNTAX          INTEGER 
        ACCESS          read-write
        STATUS          mandatory
        DESCRIPTION     
        "Common to VDSL1/VDSL2, this object specifies the end frequency of the
         VDSL optional band in case the use of the optional band is allowed
         (vdslOptBandUsage <> optBandOff).
         The end frequency is configurable from 138 kHz to 552 kHz in steps of
         1 kHz.
         The special value 0 (also the default) must be interpreted as 138kHz 
         on POTS boards and as 276kHz on ISDN boards.

         ALCATEL NOTE:
             ACCESS:   NA                  USAGE:    OPT
             PERSIST:  YES                 INSRVMOD: YES
             RANGE:    0,138..552          DEFVALUE: 0
             UNITS:    kHz                 SPARSE:   NA
             DESCR:    NA "
::= {xdslLineSpectrumProfileVdslEntry 16}

vdslAdslBandEndFreq     OBJECT-TYPE
        SYNTAX          INTEGER 
        ACCESS          read-write
        STATUS          mandatory
        DESCRIPTION 
        "Common to VDSL1/VDSL2, this object specifies the end frequency of the
         ADSL band in case the use of the ADSL band by VDSL is not allowed with
         (vdslAdslBandUsage = 3).
         The end frequency is configurable from 276 kHz to 2208 kHz in steps of
         1 kHz.

         ALCATEL NOTE:
             ACCESS:   NA                  USAGE:    OPT
             PERSIST:  YES                 INSRVMOD: YES
             RANGE:    276..2208           DEFVALUE: 1104
             UNITS:    kHz                 SPARSE:   NA
             DESCR:    NA "
::= {xdslLineSpectrumProfileVdslEntry 17}

vdslGhsTonesTxPowerControl             OBJECT-TYPE
        SYNTAX          INTEGER 
        ACCESS          read-write
        STATUS          mandatory
        DESCRIPTION     
        "Common to VDSL1/VDSL2, this object specifies how to control the Tx 
         power of the G.hs tones.
         0: default, the max power as per G994.1 standard definition applies.
         1: auto, the max Tx power level is derived from the
         vdslPsdShapeDownstream.
     2: per tone set. Instead of vdslGhsTonesTxPowerControl,
     use parameters vdslGhsTonesTxPowerControlA43,
     vdslGhsTonesTxPowerControlB43, vdslGhsTonesTxPowerControlA43c, 
     vdslGhsTonesTxPowerControlB43, vdslGhsTonesTxPowerControlA43c, 
     vdslGhsTonesTxPowerControlV43, vdslGhsTonesTxPowerLevelA43,
     vdslGhsTonesTxPowerLevelB43, vdslGhsTonesTxPowerLevelA43c,
     vdslGhsTonesTxPowerLevelV43

         ALCATEL NOTE:
             ACCESS:   NA                  USAGE:    OPT
             PERSIST:  YES                 INSRVMOD: YES
             RANGE:    0..2                DEFVALUE: 0
             UNITS:    NA                  SPARSE:   NA
             DESCR:    NA "
::= {xdslLineSpectrumProfileVdslEntry 18}

vdslGhsTonesTxPowerControlA43          OBJECT-TYPE
        SYNTAX          INTEGER 
        ACCESS          read-write
        STATUS          mandatory
        DESCRIPTION     
        "Common to VDSL1/VDSL2, this object specifies how to control the Tx 
         power of the G.hs tones for DS tones set A43.
         0: default, the max power as per G994.1 standard definition applies.
         1: auto, the max Tx power level is derived from the
           vdslPsdShapeDownstream.
         2: manual, the value set in vdslGhsTonesTxPowerLevelA43 applies.

         ALCATEL NOTE:
             ACCESS:   NA                  USAGE:    OPT
             PERSIST:  YES                 INSRVMOD: YES
             RANGE:    0..2                DEFVALUE: 0
             UNITS:    NA                  SPARSE:   NA
             DESCR:    NA "
::= {xdslLineSpectrumProfileVdslEntry 19}

vdslGhsTonesTxPowerControlB43          OBJECT-TYPE
        SYNTAX          INTEGER 
        ACCESS          read-write
        STATUS          mandatory
        DESCRIPTION     
        "Common to VDSL1/VDSL2, this object specifies how to control the Tx
         power of the G.hs tones for DS tones set B43.
         0: default, the max power as per G994.1 standard definition applies.
         1: auto, the max Tx power level is derived from the
            vdslPsdShapeDownstream.
         2: manual, the value set in vdslGhsTonesTxPowerLevelB43 applies.

         ALCATEL NOTE:
             ACCESS:   NA                  USAGE:    OPT
             PERSIST:  YES                 INSRVMOD: YES
             RANGE:    0..2                DEFVALUE: 0
             UNITS:    NA                  SPARSE:   NA
             DESCR:    NA "
::= {xdslLineSpectrumProfileVdslEntry 20}

vdslGhsTonesTxPowerControlA43c         OBJECT-TYPE
        SYNTAX          INTEGER 
        ACCESS          read-write
        STATUS          mandatory
        DESCRIPTION     
        "Common to VDSL1/VDSL2, this object specifies how to control the Tx
         power of the G.hs tones for DS tones set A43c.
         0: default, the max power as per G994.1 standard definition applies.
         1: auto, the max Tx power level is derived from the
          vdslPsdShapeDownstream.
         2: manual, the value set in vdslGhsTonesTxPowerLevelA43c applies.

         ALCATEL NOTE:
             ACCESS:   NA                  USAGE:    OPT
             PERSIST:  YES                 INSRVMOD: YES
             RANGE:    0..2                DEFVALUE: 0
             UNITS:    NA                  SPARSE:   NA
             DESCR:    NA "
::= {xdslLineSpectrumProfileVdslEntry 21}

vdslGhsTonesTxPowerControlV43          OBJECT-TYPE
        SYNTAX          INTEGER 
        ACCESS          read-write
        STATUS          mandatory
        DESCRIPTION     
        "Common to VDSL1/VDSL2, this object specifies how to control the Tx 
         power of the G.hs tones for DS tones set V43.
         0: default, the max power as per G994.1 standard definition applies.
         1: auto, the max Tx power level is derived from the
           vdslPsdShapeDownstream.
         2: manual, the value set in vdslGhsTonesTxPowerLevelV43 applies.

         ALCATEL NOTE:
             ACCESS:   NA                  USAGE:    OPT
             PERSIST:  YES                 INSRVMOD: YES
             RANGE:    0..2                DEFVALUE: 0
             UNITS:    NA                  SPARSE:   NA
             DESCR:    NA "
::= {xdslLineSpectrumProfileVdslEntry 22}

vdslGhsTonesTxPowerLevelA43            OBJECT-TYPE
        SYNTAX          INTEGER 
        ACCESS          read-write
        STATUS          mandatory
        DESCRIPTION     
        "Common to VDSL1/VDSL2, this object defines the maximum power of DS 
         tones used during G.hs(handshake) sequence when DS tone set A43 is
         used and entry vdslGhsTonesTxPowerControlA43 is set to 2 (manual 
         mode). It is ignored otherwise.
         Value is given in dBm/Hz.  The power of each tone of the set shall
         be equivalent to the given PSD value integrated in a total bandwidth
         of 4.3125 kHz.  Admissible range is between -99 dBm/Hz and
         -40 dBm/Hz with a step of 0.5 dBm/Hz.
         Special value -99 dBm/Hz indicates that the full set
         shall not be used (i.e. no power allowed).

         ALCATEL NOTE:
             ACCESS:   NA                  USAGE:    OPT
             PERSIST:  YES                 INSRVMOD: YES
             RANGE:    -198..-80           DEFVALUE: -80
             UNITS:    dBm/Hz * 1/2        SPARSE:   NA
             DESCR:    NA "
::= {xdslLineSpectrumProfileVdslEntry 23}

vdslGhsTonesTxPowerLevelB43            OBJECT-TYPE
        SYNTAX          INTEGER 
        ACCESS          read-write
        STATUS          mandatory
        DESCRIPTION     
        "Common to VDSL1/VDSL2, this object defines the maximum power of DS
         tones used during G.hs(handshake) sequence when DS tone set B43 is 
         used and entry vdslGhsTonesTxPowerControlB43 is set to 2 (manual
         mode).  It is ignored otherwise. 
         Value is given in dBm/Hz.  The power of each tone of the set shall
         be equivalent to the given PSD value integrated in a total bandwidth
         of 4.3125 kHz.  Admissible range is between -99 dBm/Hz and
         -40 dBm/Hz with a step of 0.5 dBm/Hz.
         Special value -99 dBm/Hz indicates that the full set
         shall not be used (i.e. no power allowed).

         ALCATEL NOTE:
             ACCESS:   NA                  USAGE:    OPT
             PERSIST:  YES                 INSRVMOD: YES
             RANGE:    -198..-80           DEFVALUE: -80
             UNITS:    dBm/Hz * 1/2        SPARSE:   NA
             DESCR:    NA "
::= {xdslLineSpectrumProfileVdslEntry 24}

vdslGhsTonesTxPowerLevelA43c           OBJECT-TYPE
        SYNTAX          INTEGER 
        ACCESS          read-write
        STATUS          mandatory
        DESCRIPTION     
        "Common to VDSL1/VDSL2, this object defines the maximum power of DS
         tones used during G.hs(handshake) sequence when DS tone set A43c is 
         used and entry vdslGhsTonesTxPowerControlA43c is set to 2 (manual
         mode).  It is ignored otherwise.
         Value is given in dBm/Hz.  The power of each tone of the set shall
         be equivalent to the given PSD value integrated in a total bandwidth
         of 4.3125 kHz.  Admissible range is between -99 dBm/Hz and
         -40 dBm/Hz with a step of 0.5 dBm/Hz.
         Special value -99 dBm/Hz indicates that the full set
         shall not be used (i.e. no power allowed).

         ALCATEL NOTE:
             ACCESS:   NA                  USAGE:    OPT
             PERSIST:  YES                 INSRVMOD: YES
             RANGE:    -198..-80           DEFVALUE: -80
             UNITS:    dBm/Hz * 1/2        SPARSE:   NA
             DESCR:    NA "
::= {xdslLineSpectrumProfileVdslEntry 25}

vdslGhsTonesTxPowerLevelV43            OBJECT-TYPE
        SYNTAX          INTEGER 
        ACCESS          read-write
        STATUS          mandatory
        DESCRIPTION     
        "Common to VDSL1/VDSL2, this object defines the maximum power of DS 
         tones used during G.hs(handshake) sequence when DS tone set V43 is
         used and entry vdslGhsTonesTxPowerControlV43 is set to 2 (manual
         mode).  It is ignored otherwise.
         Value is given in dBm/Hz.  The power of each tone of the set shall
         be equivalent to the given PSD value integrated in a total bandwidth
         of 4.3125 kHz.  Admissible range is between -99 dBm/Hz and
         -40 dBm/Hz with a step of 0.5 dBm/Hz.
         Special value -99 dBm/Hz indicates that the full set
         shall not be used (i.e. no power allowed).

         ALCATEL NOTE:
             ACCESS:   NA                  USAGE:    OPT
             PERSIST:  YES                 INSRVMOD: YES
             RANGE:    -198..-80           DEFVALUE: -80
             UNITS:    dBm/Hz * 1/2        SPARSE:   NA
             DESCR:    NA "
::= {xdslLineSpectrumProfileVdslEntry 26}

vdslMaxBandNumber       OBJECT-TYPE
        SYNTAX          INTEGER 
        ACCESS          read-write
        STATUS          mandatory
        DESCRIPTION     
        "Common to VDSL1/VDSL2, this object specifies the maximum number of
         bands to be used from the specified band plan. This number aggregates
         upstream and downstream bands and does not include the optional band,
         which needs to be configured separately.
         Range is 2 to 8, with special value 0 meaning 'unrestricted'

         ALCATEL NOTE:
             ACCESS:   NA                  USAGE:    OPT
             PERSIST:  YES                 INSRVMOD: YES
             RANGE:    0, 2..8             DEFVALUE: 0
             UNITS:    NA                  SPARSE:   NA
             DESCR:    NA "
::= {xdslLineSpectrumProfileVdslEntry 27}

vdslMaxFrequency        OBJECT-TYPE
        SYNTAX          FrequencyType 
        ACCESS          read-write
        STATUS          mandatory
        DESCRIPTION     
        "Common to VDSL1/VDSL2, this object specifies the maximum frequency
         that can be used during showtime in the range 1104 ... 30000 kHz.
         Value 0 means 'unlimited'.

         ALCATEL NOTE:
             ACCESS:   NA                  USAGE:    OPT
             PERSIST:  YES                 INSRVMOD: YES
             RANGE:    0, 1104..30000      DEFVALUE: 0
             UNITS:    kHz                 SPARSE:   NA
             DESCR:    NA "
::= {xdslLineSpectrumProfileVdslEntry 28}

vdslMaxPsdLevelDownstream              OBJECT-TYPE
        SYNTAX          INTEGER
        ACCESS          read-write
        STATUS          mandatory
        DESCRIPTION     
        "VDSL1 specific, this object specifies a maximum PSD level for
         downstream, flat over the passband as an additional restriction to
         the PSD shape.
         Range is -95.5 to 0 dBm/Hz, in steps of 0.1 dB, the maximum 
         value '0' meaning 'no constraint'.
         It is represented as 1/10* vdslMaxPsdLevelDownstream.
         In case the corresponding DSL standard imposes a more stringent value
         for this parameter, the configured value will be ignored and the
         standard value will apply.

         ALCATEL NOTE:
             ACCESS:   NA                  USAGE:    OPT
             PERSIST:  YES                 INSRVMOD: YES
             RANGE:    -955..0             DEFVALUE: 0
             UNITS:    dBm/Hz * 1/10       SPARSE:   NA
             DESCR:    NA "
::= {xdslLineSpectrumProfileVdslEntry 29}

vdslMaxPsdLevelUpstream OBJECT-TYPE
        SYNTAX          INTEGER
        ACCESS          read-write
        STATUS          mandatory
        DESCRIPTION     
        "VDSL1 specific, this object specifies a maximum PSD level for
         upstream, flat over the passband as an additional restriction to the
         PSD shape.
         Range is -95.5 to 0 dBm/Hz, , in steps of 0.1 dB, the maximum 
         value '0' meaning 'no constraint'.
         It is represented as 1/10* vdslMaxPsdLevelUpstream.
         In case the corresponding DSL standard imposes a more stringent value
         for this parameter, the configured value will be ignored and the
         standard value will apply.

         ALCATEL NOTE:
             ACCESS:   NA                  USAGE:    OPT
             PERSIST:  YES                 INSRVMOD: YES
             RANGE:    -955..0             DEFVALUE: 0
             UNITS:    dBm/Hz * 1/10       SPARSE:   NA
             DESCR:    NA "
::= {xdslLineSpectrumProfileVdslEntry 30}

vdslPsdPboParamAUpstream               OBJECT-TYPE
        SYNTAX          PerBandABParamType
        ACCESS          read-write
        STATUS          mandatory
        DESCRIPTION     
        "VDSL1 specific, this object specifies the parameter A value for each
         band (including optional band) for computing the PSD reference for US
         PBO.
         Range of this parameter for each band is 40..80.95 dBm/Hz in steps of
         0.01 dBm/Hz.
         OCTETS (0,1) represent parameter A of band 0, coded as an integer in
         the range 4000..8095 (actual value * 100).
         The value is defined as MSB-LSB (big-endian).
         OCTETS (2*N,2*N+1) represent parameter A of band N, coded as an 
         integer in the range 4000..8095 (actual value * 100)
         Maximum value for N is 4.
         The set of parameter values a = 40 dBm/Hz; b = 0 dBm/Hz is a special
         configuration to disable UPBO in the respective upstream band.
         Default values are defined as follows:
            * US0: a = 40 ; b = 0 
            * US1: a = 47.3 ; b = 19.77 
            * US2: a = 54 ; b = 15.77 
            * US3: a = 54 ; b = 10.77 
            * US4: a = 54 ; b = 9.43 
          Source:
            * US0: No USPBO 
            * US1 & US2: VDSL1 ETSI F 
            * US3 & US4: Copy of US2, considering constant turnover atenuation:
              US1_b assumed at 5 MHz extrapolated at 17 (US3) and 22 (US4) MHz,
              using a k*sqrt(f) = CST rule.
         This parameter is used when vdslRxPsdShapeUp is set to
         vdslABParamRxPsdUp and ignored otherwise.
         It is also ignored in US0 band and should be kept to a=40 b=0 in that
         band.

         ALCATEL NOTE:
             ACCESS:   NA                  USAGE:    OPT
             PERSIST:  YES                 INSRVMOD: YES
             RANGE:    NA                  
             DEFVALUE: '0F A0 12 7A 15 18 15 18 15 18'H
             UNITS:    octets              SPARSE:   NA
             DESCR:    NA "
::= {xdslLineSpectrumProfileVdslEntry 31}

vdslPsdPboParamBUpstream               OBJECT-TYPE
        SYNTAX          PerBandABParamType
        ACCESS          read-write
        STATUS          mandatory
        DESCRIPTION
        "VDSL1 specific, this object specifies the parameter B value for each
         band (including optional band) for computing the PSD reference for US
         PBO.
         Range of this parameter for each band is 0..40.95 dBm/Hz in steps of
         0.01 dBm/Hz.
         OCTETS (0,1) represent parameter B of band 0, coded as an integer in 
         the range 0..4095 (actual value * 100).
         The value is defined as MSB-LSB (big-endian). OCTETS (2*N,2*N+1) represent parameter B of band N, coded as an 
         integer in the range 0..4095 (actual value * 100)
         Maximum value for N is 4.
         The set of parameter values a = 40 dBm/Hz; b = 0 dBm/Hz is a special
         configuration to disable UPBO in the respective upstream band.
         Default values are defined as follows:
            * US0: a = 40 ; b = 0 
            * US1: a = 47.3 ; b = 19.77 
            * US2: a = 54 ; b = 15.77 
            * US3: a = 54 ; b = 10.77 
            * US4: a = 54 ; b = 9.43 
          Source:
            * US0: No USPBO 
            * US1 & US2: VDSL1 ETSI F 
            * US3 & US4: Copy of US2, considering constant turnover atenuation:
              US1_b assumed at 5 MHz extrapolated at 17 (US3) and 22 (US4) MHz,
              using a k*sqrt(f) = CST rule.
         This parameter is used when vdslRxPsdShapeUp is set to 
         vdslABParamRxPsdUp and ignored otherwise.
         It is also ignored in US0 band and should be kept to a=40 b=0 in that
         band.

         ALCATEL NOTE:
             ACCESS:   NA                  USAGE:    OPT
             PERSIST:  YES                 INSRVMOD: YES
             RANGE:    NA
             DEFVALUE: '00 00 07 B9 06 29 04 35 03 AF'H
             UNITS:    octets              SPARSE:   NA
             DESCR:    NA "
::= {xdslLineSpectrumProfileVdslEntry 32}

vdslOptBandStartFreq      OBJECT-TYPE
        SYNTAX          INTEGER 
        ACCESS          read-write
        STATUS          mandatory
        DESCRIPTION     
        "Common to VDSL1/VDSL2, this object specifies the start frequency of the
         VDSL optional band in case the use of the optional band is allowed
         (vdslOptBandUsage <> optBandOff).
         The start frequency is configurable from 1kHz to 138kHz in steps of
         1kHz.
         The special value 0 (also default) has to be interpreted by the modem as 
         25KHz on POTS boards and 120 kHz on ISDN boards.

         ALCATEL NOTE:
             ACCESS:   NA                  USAGE:    OPT
             PERSIST:  YES                 INSRVMOD: YES
             RANGE:    0,1..138            DEFVALUE: 0
             UNITS:    kHz                 SPARSE:   NA
             DESCR:    NA "
::= {xdslLineSpectrumProfileVdslEntry 33}

xdslLineSpectrumProfileMappingTable    OBJECT-TYPE
        SYNTAX          SEQUENCE OF XdslLineSpectrumProfileMappingEntry
        ACCESS          not-accessible
        STATUS          mandatory
        DESCRIPTION
        "The (conceptual) listing the profile name to profile Index
         Mapping.

         ALCATEL NOTE:
             TABLESIZE: 256                    
             DESCR:     NA                           "
::= {xdslLineSpectrumProfile 6}

xdslLineSpectrumProfileMappingEntry    OBJECT-TYPE
      SYNTAX            XdslLineSpectrumProfileMappingEntry
      ACCESS            not-accessible
      STATUS            mandatory
      DESCRIPTION
        "An entry (conceptual row) representing the profile Name to Index
         Mapping.

         Row creation : When an entry is created in the 
                        xdslLineSpectrumProfileTable, an entry is created in
                        this table.
         Row deletion : When an entry is deleted from the
                        xdslLineSpectrumProfileTable, the entry is deleted from
                        this table. "
      INDEX            {xdslLineSpectrumProfileMappingName, 
                        xdslLineSpectrumProfileMappingScope}
::= { xdslLineSpectrumProfileMappingTable 1 }

XdslLineSpectrumProfileMappingEntry ::=
        SEQUENCE {
            xdslLineSpectrumProfileMappingName        AsamProfileName,
            xdslLineSpectrumProfileMappingScope       AsamProfileScope,
            xdslLineSpectrumProfileMappingIndex       AsamProfileIndex
        }

xdslLineSpectrumProfileMappingName     OBJECT-TYPE
        SYNTAX          AsamProfileName
        ACCESS          not-accessible
        STATUS          mandatory
        DESCRIPTION
        "The Spectrum profile name.

         ALCATEL NOTE:
             ACCESS:   NA                  USAGE:    NA
             PERSIST:  NO                  INSRVMOD: NA
             RANGE:    NA                  DEFVALUE: NA
             UNITS:    NA                  SPARSE:   NA
             DESCR:    NA "
::= { xdslLineSpectrumProfileMappingEntry 1 }

xdslLineSpectrumProfileMappingScope    OBJECT-TYPE
        SYNTAX          AsamProfileScope
        ACCESS          not-accessible
        STATUS          mandatory
        DESCRIPTION
        "The Spectrum profile scope.

         ALCATEL NOTE:
             ACCESS:   NA                  USAGE:    NA
             PERSIST:  NO                  INSRVMOD: NA
             RANGE:    NA                  DEFVALUE: NA
             UNITS:    NA                  SPARSE:   NA
             DESCR:    NA "
::= { xdslLineSpectrumProfileMappingEntry 2 }

xdslLineSpectrumProfileMappingIndex    OBJECT-TYPE
        SYNTAX          AsamProfileIndex
        ACCESS          read-only
        STATUS          mandatory
        DESCRIPTION
        "The Index of the corresponding spectrum profile.

         ALCATEL NOTE:
             ACCESS:   NA                  USAGE:    NA
             PERSIST:  NO                  INSRVMOD: NA
             RANGE:    1..256              DEFVALUE: NA
             UNITS:    NA                  SPARSE:   NA
             DESCR:    NA "
::= { xdslLineSpectrumProfileMappingEntry 3 }

xdslLineSpectrumProfileVdsl2Table      OBJECT-TYPE
        SYNTAX          SEQUENCE OF XdslLineSpectrumProfileVdsl2Entry
        ACCESS          not-accessible
        STATUS          mandatory
        DESCRIPTION     
        "This table is part of the line profile. It contains the line
         related parameters of the modem configuration that apply to the VDSL2
         operational mode and use specific values for this mode of operation.
         These parameters are ignored in case another operational mode is used.
         All the common VDSL parameters (i.e. the parameters using the same
         value for VDSL1 and VDSL2) are provided in the
         xdslLineSpectrumProfileVdslTable.  
         The VDSL2 table contains the VDSL2 specific parameters (i.e. not
         common).

         ALCATEL NOTE:
             TABLESIZE: 256                   
             DESCR:     NA                   "
::= {xdslLineSpectrumProfile 7}

xdslLineSpectrumProfileVdsl2Entry      OBJECT-TYPE
        SYNTAX          XdslLineSpectrumProfileVdsl2Entry
        ACCESS          not-accessible
        STATUS          mandatory
        DESCRIPTION     
        "Each entry consists of a list of line related parameters that serve 
         to configure an XDSL modem in case the VDSL2 mode of operation is
         used.

         Row creation : When an entry is created in the 
                        xdslLineSpectrumProfileTable, an entry with the same 
                        xdslLineSpectrumIndex is created in this table.
         Row deletion : When an entry is deleted from the
                        xdslLineSpectrumProfileTable, the entry with the same
                        xdslLineSpectrumIndex is deleted from this table.  "
        INDEX          {xdslLineSpectrumProfileIndex}
::= {xdslLineSpectrumProfileVdsl2Table 1}

XdslLineSpectrumProfileVdsl2Entry ::=
        SEQUENCE {
            vdsl2ModemFeatures                        INTEGER,
            vdsl2MaxAggregatePowerLevelDownstream     INTEGER,
            vdsl2MaxAggregatePowerLevelUpstream       INTEGER,
            vdsl2PsdShapeDownstream                   Vdsl2PsdDownstreamType,
            vdsl2CustomPsdShapeDownstream             CustomPsdShapeType,
            vdsl2PsdShapeUpstream                     Vdsl2PsdUpstreamType,
            vdsl2CustomPsdShapeUpstream               CustomPsdShapeType,
            vdsl2RxPsdShapeUpstream                   VdslRxPsdUpstreamType,
            vdsl2CustomRxPsdShapeUpstream             CustomPsdShapeType,
            vdsl2PsdPboElectrLengthUpstream           INTEGER,
            vdsl2MaxPsdLevelDownstream                INTEGER,
            vdsl2MaxPsdLevelUpstream                  INTEGER,
            vdsl2PsdPboParamAUpstream                 PerBandABParamType,
            vdsl2PsdPboParamBUpstream                 PerBandABParamType,
            vdsl2VirtualNoisePsdDownstream            VirtualNoisePsdDownType,
            vdsl2VirtualNoisePsdUpstream              VirtualNoisePsdUpType,
            vdsl2VirtualNoiseSnrmModeDownstream       SnrmMode,
            vdsl2VirtualNoiseSnrmModeUpstream         SnrmMode,
            vdsl2PsdPboParamEqualFextUpstream         PerBandEqualFextParamType
        }

vdsl2ModemFeatures      OBJECT-TYPE
        SYNTAX          INTEGER (0..4294967295)
        ACCESS          read-write
        STATUS          mandatory 
        DESCRIPTION 
        "This object allows to enable/disable specific features of the modem.
         It is a bitmap represented as a sum and allows multiple features to be
         configured simultaneously. 
         Bitmap values:
          1   Strict compliancy, the modem should turn off all features not
              strictly compliant with the standards.
              The modem is allowed to use proprietary features when
              bit 0 is set to 0.
          Each other bit definition can be found in the modem-TRS.

         ALCATEL NOTE:
             ACCESS:   NA                  USAGE:    OPT
             PERSIST:  YES                 INSRVMOD: YES
             RANGE:    0..4294967295       DEFVALUE: 1
             UNITS:    NA                  SPARSE:   NA
             DESCR:    NA "
::= {xdslLineSpectrumProfileVdsl2Entry 1}
       
vdsl2MaxAggregatePowerLevelDownstream  OBJECT-TYPE
        SYNTAX          INTEGER
        ACCESS          read-write
        STATUS          mandatory
        DESCRIPTION     
        "This parameter indicates the maximum power allowed on 
         the line for the downstream direction. If the necessary power level 
         exceeds the level given by this parameter the modem will re-
         initialize.  
         The aggregate power has a range of -31 dBm to +25.5 dBm in steps of 
         0.1 dB. 
         It is represented as 1/10 * vdsl2MaxAggregatePowerLevelDownstream.

         ALCATEL NOTE:
             ACCESS:   NA                  USAGE:    OPT
             PERSIST:  YES                 INSRVMOD: YES
             RANGE:    -310..255           DEFVALUE: 255
             UNITS:    dBm / 10            SPARSE:   NA
             DESCR:    NA "
::= {xdslLineSpectrumProfileVdsl2Entry 2}

vdsl2MaxAggregatePowerLevelUpstream    OBJECT-TYPE
        SYNTAX          INTEGER
        ACCESS          read-write
        STATUS          mandatory
        DESCRIPTION     
        "This parameter indicates the maximum power allowed on the line for the 
         upstream direction. If the necessary power level exceeds the level 
         given by this parameter the modem will re-initialize. 
         The aggregate power has a range of -31 dBm to +25.5 dBm in steps of 
         0.1 dB. 
         It is represented as 1/10 * vdsl2MaxAggregatePowerLevelUpstream .

         ALCATEL NOTE:
             ACCESS:   NA                  USAGE:    OPT
             PERSIST:  YES                 INSRVMOD: YES
             RANGE:    -310..255           DEFVALUE: 255
             UNITS:    dBm / 10            SPARSE:   NA
             DESCR:    NA "
::= {xdslLineSpectrumProfileVdsl2Entry 3}

vdsl2PsdShapeDownstream                OBJECT-TYPE
        SYNTAX          Vdsl2PsdDownstreamType
        ACCESS          read-write
        STATUS          mandatory
        DESCRIPTION     
        "This parameter defines the PSD Shape that must be applied for VDSL
         in the downstream direction.
         In case a vdsl2PsdShapeDownstream other than vdsl2CustomPsdDownstream
         is defined, vdsl2CustomPsdShapeDownstream may be empty.
         If vdsl2PsdShapeDownstream equals vdsl2CustomPsdDownstream and no
         vdsl2CustomPsdShapeDownstream is defined, the configuration shall be
         rejected.
         If vdsl2PsdShapeDownstream differs from vdsl2CustomPsdDownstream and 
         vdsl2CustomPsdShapeDownstream is defined, the minimum of the two masks
         shall be taken, tone per tone.
         A predefined PSD (ANSI or ETSI)can be selected from the following 
         list:
           vdsl2CustomPsdDownstream (meaning no pre-defined PSD shape is used)
           vdsl2RegionAPsdDownstream
           vdsl2RegionBM1PsdDownstream
           vdsl2RegionBM2PsdDownstream

         ALCATEL NOTE:
             ACCESS:   NA                  USAGE:    OPT
             PERSIST:  YES                 INSRVMOD: YES
             RANGE:    NA                  
             DEFVALUE: vdsl2RegionBM1PsdDownstream
             UNITS:    NA                  SPARSE:   NA
             DESCR:    NA "
::= {xdslLineSpectrumProfileVdsl2Entry 4}

vdsl2CustomPsdShapeDownstream          OBJECT-TYPE
        SYNTAX          CustomPsdShapeType 
        ACCESS          read-write
        STATUS          mandatory
        DESCRIPTION     
        "This object specifies PSD points of a custom VDSL PSD Shape for
         the downstream direction.  It will always be taken into account, 
         whatever the value of vdsl2PsdShapeDownstream.
         In case a vdsl2PsdShapeDownstream other than vdsl2CustomPsdDownstream
         is defined, this object can be empty.
         A number of 2 to 32 PSD points can be specified.
         The successive PSD points must have increasing (>/=) frequencies.
         It is allowed that for two successive PSD points, different PSD
         levels are defined at a same frequency (brickwall).
         The custom PSD Shape is coded as a variable length octet string
         defined as follows:
         OCTET 0: defines the characteristics (type and scale) of the PSD
         shape.
         OCTET 0- bit 0..1: defines the frequency scale to be used for the
         interpolation of the PSD Shape data (00= linear frequency scale,
         01 = logarithmic frequency scale).
         OCTET 0- bit 2..3: defines the type of the PSD shape (00= PSD mask,
         01= PSD template).
         Octet 1..3: defines PSD point #1
         OCTETS 1..2: INTEGER (0..30000), frequency of PSD point #1,
         expressed in kHz. The value is defined as MSB-LSB (big-endian).
         OCTET 3: INTEGER (0..255), -2*PSD level (in dBm/Hz) of
         PSD point#1.  Only PSD values within the standard range 
         from -95 to 0 dBm/Hz are guaranteed
         OCTETS 4..6: define the frequency and PSD level of PSD point #2.
         ....       up to
         OCTETS 3*N-2..3*N: define the frequency and PSD level of the last PSD
         point #N with N<=32.

         ALCATEL NOTE:
             ACCESS:   NA                  USAGE:    OPT
             PERSIST:  YES                 INSRVMOD: YES
             RANGE:    0..97               DEFVALUE: ''H
             UNITS:    octets              SPARSE:   NA
             DESCR:    NA "
::= {xdslLineSpectrumProfileVdsl2Entry 5}

vdsl2PsdShapeUpstream   OBJECT-TYPE
        SYNTAX          Vdsl2PsdUpstreamType
        ACCESS          read-write
        STATUS          mandatory
        DESCRIPTION     
        "This parameter defines the PSD Shape that must be applied for VDSL
         in the upstream direction.
         In case a vdsl2PsdShapeUpstream other than vdsl2CustomPsdUpstream is
         defined, vdsl2CustomPsdShapeUpstream may be empty.
         If vdsl2PsdShapeUpstream equals vdsl2CustomPsdUpstream and no
         vdsl2CustomPsdShapeUpstream is defined, the configuration shall be
         rejected.
         If vdsl2PsdShapeUpstream differs from vdsl2CustomPsdUpstream and 
         vdsl2CustomPsdShapeUpstream is defined, the minimum of the two masks
         shall be taken, tone per tone.
         A predefined PSD (ANSI or ETSI) can be selected from the following 
         list:
           vdsl2CustomPsdUpstream (meaning no pre-defined PSD shape is used)
           vdsl2RegionAPsdUpstream
           vdsl2RegionBM1PsdUpstream
           vdsl2RegionBM2PsdUpstream

         ALCATEL NOTE:
             ACCESS:   NA                  USAGE:    OPT
             PERSIST:  YES                 INSRVMOD: YES
             RANGE:    NA                  DEFVALUE: vdsl2RegionBM1PsdUpstream
             UNITS:    NA                  SPARSE:   NA
             DESCR:    NA "
::= {xdslLineSpectrumProfileVdsl2Entry 6}

vdsl2CustomPsdShapeUpstream            OBJECT-TYPE
        SYNTAX          CustomPsdShapeType 
        ACCESS          read-write
        STATUS          mandatory
        DESCRIPTION     
        "This object specifies PSD points of a custom VDSL PSD Shape for
         the upstream direction.  It will always be taken into account, 
         whatever the value of vdsl2PsdShapeUpstream.
         A number of 2 to 20 points can be specified.
         The successive PSD points must have increasing (>/=) frequencies.
         It is allowed that for two successive PSD points, different PSD
         levels are defined at a same frequency (brickwall).
         The custom PSD Shape is coded as a variable length octet string
         defined as follows:
         OCTET 0: defines the characteristics (type and scale) of the PSD
         shape.
         OCTET 0- bit 0..1: defines the frequency scale to be used for the
         interpolation of the PSD Shape data (00= linear frequency scale,
         01 = logarithmic frequency scale).
         OCTET 0- bit 2..3: defines the type of the PSD shape (00= PSD mask,
         01= PSD template).
         Octet 1..3: defines PSD point #1
         OCTETS 1..2: INTEGER (0..30000), frequency of PSD point #1,
         expressed in kHz. The value is defined as MSB-LSB (big-endian).
         OCTET 3: INTEGER (0..255), -2*PSD level (in dBm/Hz) of
         PSD point#1.  Only PSD values within the standard range 
         from -95 to 0 dBm/Hz are guaranteed
         OCTETS 4..6: define the frequency and PSD level of PSD point #2.
         ....       up to
         OCTETS 3*N-2..3*N: define the frequency and PSD level of the last PSD
         point #N with N<=20.

         ALCATEL NOTE:
             ACCESS:   NA                  USAGE:    OPT
             PERSIST:  YES                 INSRVMOD: YES
             RANGE:    0..61               DEFVALUE: ''H
             UNITS:    octets              SPARSE:   NA
             DESCR:    NA "
::= {xdslLineSpectrumProfileVdsl2Entry 7}

vdsl2RxPsdShapeUpstream                OBJECT-TYPE
        SYNTAX          VdslRxPsdUpstreamType
        ACCESS          read-write
        STATUS          mandatory
        DESCRIPTION     
        "This parameter defines the reference Rx PSD Shape to be used
         for upstream power backoff.
         vdslCustomRxPsdUpstream: a custom reference Rx PSD Shape is defined
         in vdsl2CustomRxPsdShapeUpstream.
         A predefined standard or custom PSD can selected from the following
         list:
          vdslAnsiARxPsdUpstream
          vdslAnsiFRxPsdUpstream
          vdslAnsiCustomExRxPsdUpstream
          vdslAnsiCustomCabRxPsdUpstream
          vdslEtsiARxPsdUpstream
          vdslEtsiBRxPsdUpstream
          vdslEtsiCRxPsdUpstream
          vdslEtsiDRxPsdUpstream
          vdslEtsiERxPsdUpstream
          vdslEtsiFRxPsdUpstream
          vdslEtsiCustomExRxPsdUpstream
          vdslEtsiCustomCabRxPsdUpstream
          vdslABParamRxPsdUpstream
          vdslEqualFextRxPsdUpstream

         ALCATEL NOTE:
             ACCESS:   NA                  USAGE:    OPT
             PERSIST:  YES                 INSRVMOD: YES
             RANGE:    NA                  DEFVALUE: vdslEtsiARxPsdUpstream
             UNITS:    NA                  SPARSE:   NA
             DESCR:    NA "
::= {xdslLineSpectrumProfileVdsl2Entry 8}

vdsl2CustomRxPsdShapeUpstream          OBJECT-TYPE
        SYNTAX          CustomPsdShapeType 
        ACCESS          read-write
        STATUS          mandatory
        DESCRIPTION     
        "This object specifies PSD points of a custom reference receive VDSL
         PSD Shape for upstream power backoff in case
         vdsl2RxPsdShapeUpstream = vdslCustomRxPsdUpstream  and it will be
         ignored otherwise. A number of 2 to 20 PSD points can be specified.
         The successive PSD points must have increasing (>/=) frequencies.
         It is allowed that for two successive PSD points, different PSD
         levels are defined at a same frequency (brickwall).
         The custom PSD Shape is coded as a variable length octet string
         defined as follows:
         OCTET 0: defines the characteristics (type and scale) of the PSD 
         shape.
         OCTET 0- bit 0..1: defines the frequency scale to be used for the
         interpolation of the PSD Shape data (00= linear frequency scale,
         01 = logarithmic frequency scale).
         OCTET 0- bit 2..3: defines the type of the PSD shape (00= PSD mask,
         01= PSD template).
         Octet 1..3: defines PSD point #1
         OCTETS 1..2: INTEGER (0..30000), frequency of PSD point #1,
         expressed in kHz. The value is defined as MSB-LSB (big-endian).
         OCTET 3: INTEGER (0..255), -2*PSD level (in dBm/Hz) of
         PSD point#1.  Only PSD values within the standard range 
         from -95 to 0 dBm/Hz are guaranteed
         OCTETS 4..6: define the frequency and PSD level of PSD point #2.
         ....       up to
         OCTETS 3*N-2..3*N: define the frequency and PSD level of the last PSD
         point #N with N<=20.

         ALCATEL NOTE:
             ACCESS:   NA                  USAGE:    OPT
             PERSIST:  YES                 INSRVMOD: YES
             RANGE:    0..61               DEFVALUE: ''H
             UNITS:    octets              SPARSE:   NA
             DESCR:    NA "
::= {xdslLineSpectrumProfileVdsl2Entry 9}

vdsl2PsdPboElectrLengthUpstream        OBJECT-TYPE
        SYNTAX          INTEGER 
        ACCESS          read-write
        STATUS          mandatory
        DESCRIPTION     
        "This object specifies the electrical length to be used with the AB
         parameters.  It has to be set to the maximal value when the electrical
         length XTU-R estimate should be used.  Range is 0 to 127.5 dB (at 1
         MHz) with a granularity of 0.5 dB.
         Special value 256 means 'electricalLengthEstimated', indicating that
         the US Power Back-off electrical length estimated by the VTU-R is not
         overwritten by any fixed configuration value given either by an 
         operator or by a manager(N.A...).  However, in this case, the VTU-O 
         transceiver is still allowed to automatically overwrite the VTU-R 
         estimated value (which is the normal behaviour).  In other words, this 
         concerns operator overwrite, not VTU-O overwrite.
         Note: the electrical length is positive when the loop gain is negative
         in dB.
         integer range: 0..255 (= actual value * 2) + special value 256

         ALCATEL NOTE:
             ACCESS:   NA                  USAGE:    OPT
             PERSIST:  YES                 INSRVMOD: YES
             RANGE:    0..256              DEFVALUE: 256
             UNITS:    dB / 2              SPARSE:   NA
             DESCR:    NA "
::= {xdslLineSpectrumProfileVdsl2Entry 10}

vdsl2MaxPsdLevelDownstream             OBJECT-TYPE
        SYNTAX          INTEGER
        ACCESS          read-write
        STATUS          mandatory
        DESCRIPTION     
        "This object specifies a maximum PSD level for downstream, flat over
         the passband as an additional restriction to the PSD shape.
         Range is -95.5 to 0 dBm/Hz, in steps of 0.1 dB, the maximum 
         value '0' meaning 'no constraint'.
         It is represented as 1/10* vdsl2MaxPsdLevelDownstream.
         In case the corresponding DSL standard imposes a more stringent value
         for this parameter, the configured value will be ignored and the
         standard value will apply.

         ALCATEL NOTE:
             ACCESS:   NA                  USAGE:    OPT
             PERSIST:  YES                 INSRVMOD: YES
             RANGE:    -955..0             DEFVALUE: 0
             UNITS:    dBm/Hz * 1/10       SPARSE:   NA
             DESCR:    NA "
::= {xdslLineSpectrumProfileVdsl2Entry 11}

vdsl2MaxPsdLevelUpstream               OBJECT-TYPE
        SYNTAX          INTEGER
        ACCESS          read-write
        STATUS          mandatory
        DESCRIPTION     
        "This object specifies a maximum PSD level for upstream, flat over
         the passband as an additional restriction to the PSD shape.
         Range is -95.5 to 0 dBm/Hz, , in steps of 0.1 dB, the maximum 
         value '0'  meaning 'no constraint'.
         It is represented as 1/10* vdsl2MaxPsdLevelUpstream.
         In case the corresponding DSL standard imposes a more stringent value
         for this parameter, the configured value will be ignored and the
         standard value will apply.
         integer range: -955..0

         ALCATEL NOTE:
             ACCESS:   NA                  USAGE:    OPT
             PERSIST:  YES                 INSRVMOD: YES
             RANGE:    -955..0             DEFVALUE: 0
             UNITS:    dBm/Hz * 1/10       SPARSE:   NA
             DESCR:    NA "
::= {xdslLineSpectrumProfileVdsl2Entry 12}

vdsl2PsdPboParamAUpstream              OBJECT-TYPE
        SYNTAX          PerBandABParamType
        ACCESS          read-write
        STATUS          mandatory
        DESCRIPTION     
        "This object specifies the parameter A value for each band (including
         optional band) for computing the PSD reference for US PBO.
         Range of this parameter for each band is 40..80.95 dBm/Hz in steps of
         0.01 dBm/Hz.
         OCTETS (0,1) represent parameter A of band 0, coded as an integer in
         the range 4000..8095 (actual value * 100).
         The value is defined as MSB-LSB (big-endian).
         OCTETS (2*N,2*N+1) represent parameter A of band N, coded as an 
         integer in the range 4000..8095 (actual value * 100).
         Maximum value for N is 4.
         The set of parameter values a = 40 dBm/Hz; b = 0 dBm/Hz is a special
         configuration to disable UPBO in the respective upstream band.
         Default values are defined as follows:
            * US0: a = 40 ; b = 0 
            * US1: a = 47.3 ; b = 19.77 
            * US2: a = 54 ; b = 15.77 
            * US3: a = 54 ; b = 10.77 
            * US4: a = 54 ; b = 9.43 
          Source:
            * US0: No USPBO 
            * US1 & US2: VDSL1 ETSI F 
            * US3 & US4: Copy of US2, considering constant turnover atenuation:
              US1_b assumed at 5 MHz extrapolated at 17 (US3) and 22 (US4) MHz,
              using a k*sqrt(f) = CST rule.
         This parameter is used when vdsl2RxPsdShapeUpstream is set to
         vdslABParamRxPsdUp or vdslEqualFextRxPsdUpstream and ignored otherwise.
         It is also ignored in US0 band and should be kept to a=40 b=0 in that
         band.

         ALCATEL NOTE:
             ACCESS:   NA                  USAGE:    OPT
             PERSIST:  YES                 INSRVMOD: YES
             RANGE:    NA 
             DEFVALUE: '0F A0 12 7A 15 18 15 18 15 18'H
             UNITS:    octets              SPARSE:   NA
             DESCR:    NA "
::= {xdslLineSpectrumProfileVdsl2Entry 13}

vdsl2PsdPboParamBUpstream              OBJECT-TYPE
        SYNTAX          PerBandABParamType
        ACCESS          read-write
        STATUS          mandatory
        DESCRIPTION     
        "This object specifies the parameter B value for each band (including
         optional band) for computing the PSD reference for US PBO.
         Range of this parameter for each band is 0..40.95 dBm/Hz in steps of 
         0.01 dBm/Hz.
         OCTETS (0,1) represent parameter B of band 0, coded as an integer in 
         the range 0..4095 (actual value * 100).
         The value is defined as MSB-LSB (big-endian).
         OCTETS (2*N,2*N+1) represent parameter B of band N, coded as an 
         integer in the range 0..4095 (actual value * 100).
         Maximum value for N is 4.
         The set of parameter values a = 40 dBm/Hz; b = 0 dBm/Hz is a special
         configuration to disable UPBO in the respective upstream band.
         Default values are defined as follows:
            * US0: a = 40 ; b = 0 
            * US1: a = 47.3 ; b = 19.77 
            * US2: a = 54 ; b = 15.77 
            * US3: a = 54 ; b = 10.77 
            * US4: a = 54 ; b = 9.43 
          Source:
            * US0: No USPBO 
            * US1 & US2: VDSL1 ETSI F 
            * US3 & US4: Copy of US2, considering constant turnover atenuation:
              US1_b assumed at 5 MHz extrapolated at 17 (US3) and 22 (US4) MHz,
              using a k*sqrt(f) = CST rule.
         This parameter is used when vdsl2RxPsdShapeUpstream is set to
         vdslABParamRxPsdUp or vdslEqualFextRxPsdUpstream and ignored otherwise.
         It is also ignored in US0 band and should be kept to a=40 b=0 in that
         band.

         ALCATEL NOTE:
             ACCESS:   NA                  USAGE:    OPT
             PERSIST:  YES                 INSRVMOD: YES
             RANGE:    NA 
             DEFVALUE: '00 00 07 B9 06 29 04 35 03 AF'H
             UNITS:    octets              SPARSE:   NA
             DESCR:    NA "
::= {xdslLineSpectrumProfileVdsl2Entry 14}

vdsl2VirtualNoisePsdDownstream         OBJECT-TYPE
        SYNTAX          VirtualNoisePsdDownType
        ACCESS          read-write
        STATUS          mandatory
        DESCRIPTION     
        "This object specifies the transmitter-referred virtual noise level for
         determining the SNR margin in the corresponding downstream bands.
         A number of 2 to 32 Virtual Noise PSD points can be specified downstream.
         An empty sequence means that no virtual noise shall be used.
         The successive PSD points must have increasing (>/=) frequencies.
         It is allowed that for two successive PSD points, different PSD
         levels are defined at a same frequency (brickwall).
         Virtual Noise PSD points are defined in the range -140dBm/Hz..-40 
         dBm/Hz.
         A special value (-167,5 dBm/Hz) states no virtual noise has to be
         applied.
         The custom Virtual Noise PSD Shape is coded as a variable length
         octet string defined as follows:
         Octet 0: reserved 
         Octet 1..3: defines PSD point #1
         OCTETS 1..2: INTEGER (0..30000), frequency of PSD point #1,
         expressed in kHz. The value is defined as MSB-LSB (big-endian).
         OCTET 3: INTEGER (0..200,255), -2*(40 + PSD level) (in dBm/Hz) of
         PSD point#1.
         OCTETS 4..6: define the frequency and PSD level of PSD point #2.
         ....       up to
         OCTETS 3*N-2..3*N: define the frequency and PSD level of the last PSD
         point #N with N<=32.
         This parameter is used when vdsl2virtualNoiseSnrmModeDownstream is set
         to snrmMode2 and ignored otherwise.

         ALCATEL NOTE:
             ACCESS:   NA                  USAGE:    OPT
             PERSIST:  YES                 INSRVMOD: YES
             RANGE:    0..97               DEFVALUE: ''H
             UNITS:    octets              SPARSE:   NA
             DESCR:    NA "
::= {xdslLineSpectrumProfileVdsl2Entry 15}

vdsl2VirtualNoisePsdUpstream           OBJECT-TYPE
        SYNTAX          VirtualNoisePsdUpType
        ACCESS          read-write
        STATUS          mandatory
        DESCRIPTION     
        "This object specifies the transmitter-referred or receiver-referred 
         virtual noise level for determining the SNR margin in the corresponding
         upstream bands.
         A number of 2 to 16 Virtual Noise PSD points can be specified upstream.
         An empty sequence means that no virtual noise shall be used.
         The successive PSD points must have increasing (>/=) frequencies.
         It is allowed that for two successive PSD points, different PSD
         levels are defined at a same frequency (brickwall).
         Virtual Noise PSD points are defined in the range -140dBm/Hz..-40
         dBm/Hz.
         A special value (-167,5 dBm/Hz) states no virtual noise has to be
         applied.
         The custom Virtual Noise PSD Shape is coded as a variable length
         octet string defined as follows:
         Octet 0: reserved 
         Octet 1..3: defines PSD point #1
         OCTETS 1..2: INTEGER (0..30000), frequency of PSD point #1,
         expressed in kHz. The value is defined as MSB-LSB (big-endian).
         OCTET 3: INTEGER (0..200,255), -2*(40 + PSD level) (in dBm/Hz) of
         PSD point#1.
         OCTETS 4..6: define the frequency and PSD level of PSD point #2.
         ....       up to
         OCTETS 3*N-2..3*N: define the frequency and PSD level of the last PSD
         point #N with N<=16.
         This parameter is used when vdsl2virtualNoiseSnrmModeUpstream is set
         to snrmMode2 or snrmMode3 and ignored otherwise.

         ALCATEL NOTE:
             ACCESS:   NA                  USAGE:    OPT
             PERSIST:  YES                 INSRVMOD: YES
             RANGE:    0..49               DEFVALUE: ''H
             UNITS:    NA                  SPARSE:   NA
             DESCR:    NA "
::= {xdslLineSpectrumProfileVdsl2Entry 16}

vdsl2VirtualNoiseSnrmModeDownstream    OBJECT-TYPE
        SYNTAX          SnrmMode
        ACCESS          read-write
        STATUS          mandatory
        DESCRIPTION     
        "This object enables or disables virtual noise in downstream direction.
          snrmmode1: virtual noise is disabled.
          snrmmode2: virtual noise is enabled, using vdsl2VirtualNoisePsdDownstream
                     as the transmitter referred noise
          snrmmode3: not supported, for future use

         ALCATEL NOTE:
             ACCESS:   NA                  USAGE:    OPT
             PERSIST:  YES                 INSRVMOD: YES
             RANGE:    snrmMode1, snrmMode2
             DEFVALUE: snrmMode1
             UNITS:    NA                  SPARSE:   NA
             DESCR:    NA "
::= {xdslLineSpectrumProfileVdsl2Entry 17}

vdsl2VirtualNoiseSnrmModeUpstream      OBJECT-TYPE
        SYNTAX          SnrmMode
        ACCESS          read-write
        STATUS          mandatory
        DESCRIPTION     
        "This object enables or disables virtual noise in upstream direction.
          snrmmode1: virtual noise is disabled.
          snrmmode2: virtual noise is enabled, using vdsl2VirtualNoisePsdUpstream
                     as the transmitter referred noise
          snrmmode3: virtual noise is enabled, using vdsl2VirtualNoisePsdUpstream 
                     as the receiver referred noise 
         ALCATEL NOTE:
             ACCESS:   NA                  USAGE:    OPT
             PERSIST:  YES                 INSRVMOD: YES
             RANGE:    NA                  DEFVALUE: snrmMode1
             UNITS:    NA                  SPARSE:   NA
             DESCR:    NA "
::= {xdslLineSpectrumProfileVdsl2Entry 18}

vdsl2PsdPboParamEqualFextUpstream               OBJECT-TYPE
        SYNTAX          PerBandEqualFextParamType
        ACCESS          read-write
        STATUS          mandatory
        DESCRIPTION     
        "This object specifies the reference electrical length parameter
         value for each band (including optional band) for computing the PSD
         reference for US equal FEXT PBO.
         Range of this parameter for each band is 1.8 dB to 63 dB
         in steps of 0.1 dB.
         The special value 0 dB indicates that the modem has to use dedicated
         mechanism to optimally apply the equal FEXT without providing any
         manual setting for this parameter.
         The value 1.8 dB results in a disabling of equal FEXT in the 
         respective upstream band.
         OCTETS (0,1) represent equal FEXT parameter of band 0, coded as an
         integer in the range 0, 18..630. The value is defined as 10 * the
         actual value in dB as MSB-LSB (big-endian).
         OCTETS (2*N,2*N+1) represent equal FEXT parameter of band N. 
         Maximum value for N is 4.
         This parameter is used when vdsl2RxPsdShapeUpstream is set to
         vdslEqualFextRxPsdUpstream and ignored otherwise.
         It is also ignored in US0 band and should be kept to 0 in that band.

         ALCATEL NOTE:
             ACCESS:   NA                  USAGE:    OPT
             PERSIST:  YES                 INSRVMOD: YES
             RANGE:    NA 
             DEFVALUE: '00 00 00 00 00 00 00 00 00 00'H
             UNITS:    octets              SPARSE:   NA
             DESCR:    NA "
::= {xdslLineSpectrumProfileVdsl2Entry 19}

xdslLineConfTable       OBJECT-TYPE
        SYNTAX          SEQUENCE OF XdslLineConfEntry
        ACCESS          not-accessible
        STATUS          mandatory
        DESCRIPTION     
        "This table contains per line configuration information about the
         modem.

         ALCATEL NOTE:
             TABLESIZE: DEP [number of XDSL lines]                    
             DESCR:     NA                   "
::= {xdslLine 7}

xdslLineConfEntry       OBJECT-TYPE
        SYNTAX          XdslLineConfEntry
        ACCESS          not-accessible
        STATUS          mandatory
        DESCRIPTION     
        "An entry in the xdslLineConfTable contains configuration
         information about the modem related with one physical entry.

         Row creation : Entries for all XDSL lines belonging to a board are 
                        created by the system when the board is planned.
         Row deletion : Entries for all XDSL lines belonging to a board are 
                        deleted by the system when the board is unplanned. "
        INDEX          {ifIndex}
::= {xdslLineConfTable 1}

XdslLineConfEntry ::=
        SEQUENCE {
            xdslLineServiceProfileNbr                 AsamProfilePointer,
            xdslLineSpectrumProfileNbr                AsamProfilePointer,
            xdslLineIsdnSplitterOptimization          SplitterOptimizationType,
            xdslLineOpModeMask                        OpModeType,
            xdslLineOpModeBoardCapability             OpModeType,
            xdslLineCarrierDataMode                   INTEGER,
            xdslLineLoopDiagnosticsMode               INTEGER,
            xdslLineTestModes                         INTEGER,
            xdslLineBondingModeChannel1               BondingModeType,
            xdslLineBondingModeChannel2               BondingModeType,
            xdslLineBondingModeChannel3               BondingModeType,
            xdslLineBondingModeChannel4               BondingModeType,
            xdslLineSeltMode                          INTEGER,
            xdslLineSeltEnable                        INTEGER,
            xdslLineTpsTcMode                         TpsTcModeType,
            xdslLineOpModeAtmCapability               OpModeType,
            xdslLineOpModePtmCapability               OpModeType,
            xdslLineActualConfTpsTcMode               TpsTcModeType,
            xdslLineSeltUncalEchoMeasTime             INTEGER, 
            xdslLineSeltQLNoiseMeasTime               INTEGER, 
            xdslLineDpboProfileNbr                    AsamProfilePointer,
            xdslLineOverruleState                     INTEGER,
            xdslLineInsEnable                         INTEGER,
            xdslLineSeltTxSignPsdType                 SeltTxSignPsdType,
            xdslLineSeltUncalEchoTargetMinSnr         INTEGER,
            xdslLineSeltAGC                           INTEGER,
            xdslLineRtxProfileNbr                     AsamProfilePointer
        }
        
xdslLineServiceProfileNbr              OBJECT-TYPE
        SYNTAX          AsamProfilePointer
        ACCESS          read-write
        STATUS          mandatory
        DESCRIPTION     
        "This object identifies the row of the xdslLineServiceProfileTable
         which defines the valid profile for the interface.

         ALCATEL NOTE:
             ACCESS:   NA                  USAGE:    OPT
             PERSIST:  YES                 INSRVMOD: YES
             RANGE:    0..256              DEFVALUE: 0
             UNITS:    NA                  SPARSE:   NA
             DESCR:    NA "
::= {xdslLineConfEntry 1}

xdslLineSpectrumProfileNbr             OBJECT-TYPE
        SYNTAX          AsamProfilePointer
        ACCESS          read-write
        STATUS          mandatory
        DESCRIPTION     
        "This object identifies the row of the xdslLineSpectrumProfileTable
         which defines the valid profile for the interface.
         ALCATEL NOTE:

             ACCESS:   NA                  USAGE:    OPT
             PERSIST:  YES                 INSRVMOD: YES
             RANGE:    0..256              DEFVALUE: 0
             UNITS:    NA                  SPARSE:   NA
             DESCR:    NA "
::= {xdslLineConfEntry 2}

xdslLineIsdnSplitterOptimization       OBJECT-TYPE  
        SYNTAX          SplitterOptimizationType
        ACCESS          read-write
        STATUS          mandatory
        DESCRIPTION     
        "The  ISDN splitter can be optimized for POTS or for ISDN.

         ALCATEL NOTE:
             ACCESS:   NA                  USAGE:    OPT
             PERSIST:  YES                 INSRVMOD: YES
             RANGE:    isdn                DEFVALUE: isdn
             UNITS:    NA                  SPARSE:   NA
             DESCR:    The object is supported to avoid future database 
                       migration but should not be set.
                       Set requests will be rejected (badvalue) if the value
                       differs from the default value. "
::= {xdslLineConfEntry 3}

xdslLineOpModeMask      OBJECT-TYPE
        SYNTAX          OpModeType
        ACCESS          read-write
        STATUS          mandatory 
        DESCRIPTION 
        "This variable controls the operational modes allowed on the line.
         It can be used to disable an operational mode that is enabled in the
         line spectrum configuration profile (xdslLineOpMode) but is not 
         allowed on the line. 
         The modes which are not supported by the line (i.e. not set in the
         corresponding xdslLineOpModeBoardCapability) must be disabled.
         An operational mode is allowed on the line when it is enabled in
         xdslLineOpMode and in xdslLineOpModeMask.
         It uses the same bitmap coding as defined in xdslLineOpMode.
         '0' is used as special value to indicate that all the modes supported
         by the line are allowed.
         The actual operational mode is reflected by the 
         'xdslLineActualOperationalMode' object.

         ALCATEL NOTE:
             ACCESS:   NA                  USAGE:    OPT 
             PERSIST:  YES                 INSRVMOD: YES
             RANGE:    NA                  
             DEFVALUE: '00 00 00 00 00 00 00 00 
                        00 00 00 00 00 00 00 00'H
             UNITS:    octets              SPARSE:   NA
             DESCR:    NA "
::= {xdslLineConfEntry 4}

xdslLineOpModeBoardCapability          OBJECT-TYPE
        SYNTAX          OpModeType
        ACCESS          read-only
        STATUS          mandatory 
        DESCRIPTION 
        "This variable used to indicate which operational modes are supported 
         by the board for the corresponding line and can therefore be enabled
         in the xdslLineOpModeMask.  Due to the introduction of TpsTcMode, the
         board capability has been further refined to differentiate OpModes 
         supported in Atm and/or Ptm modes, see xdslLineOpModeAtmCapability and
         xdslLineOpModePtmCapability. The object xdslLineOpModeBoardCapability
         has been maintained for backward compatibility reasons and can be used
         to obtain the overall opmode board capabilities independantly of the
         selected TpsTcMode.

         ALCATEL NOTE:
             ACCESS:   NA                  USAGE:    NA
             PERSIST:  NO                  INSRVMOD: NA
             RANGE:    NA                  DEFVALUE: NA
             UNITS:    NA                  SPARSE:   NA
             DESCR:    NA "
::= {xdslLineConfEntry 5}

xdslLineCarrierDataMode OBJECT-TYPE
        SYNTAX          INTEGER {
                            carrierDataModeOff (1),
                            carrierDatamodeOn (2),
                            carrierDatamodeOnInit (3)
                        }
        ACCESS          read-write
        STATUS          mandatory 
        DESCRIPTION 
        "This variable is used to enable or disable the collection during
         normal operation of detailed carrier data measurements for the
         corresponding XDSL line:
         - carrierDataModeOff disables the collection of carrier data
           measurements.
         - carrierDataModeOn enables the collection of carrier data
           measurewments.
           Carrier data measurements which are performed at initialization may
           not be available since the line will not be reinitialized.
         - carrierDataModeOnInit enables the collection of carrier data
           measurements and forces a reinitialization of the line so that the
           carrier data measured during initialization will also be collected.

         ALCATEL NOTE:
             ACCESS:   NA                  USAGE:    OPT 
             PERSIST:  YES                 INSRVMOD: YES
             RANGE:    NA                  DEFVALUE: carrierDataModeOff
             UNITS:    NA                  SPARSE:   NA
             DESCR:    NA "
::= {xdslLineConfEntry 6}

xdslLineLoopDiagnosticsMode            OBJECT-TYPE
        SYNTAX          INTEGER {
                            loopDiagnosticsOff (1),
                            loopDiagnosticsInit (2),
                            loopDiagnosticsCompleted (3),
                            loopDiagnosticsFailed (4)
                        }
        ACCESS          read-write
        STATUS          mandatory 
        DESCRIPTION 
        "This variable is effective for modems with ADSL2 or VDSL2 operational
         modes capabilities only.
         The manager can request the modem to perform a loop diagnostics
         initialisation for this XDSL line where detailed line measurements
         are performed. 
         The system will autonomously overwrite this variable when the loop
         diagnostics initialisation is completed or failed.
         The possible values are:
         - loopDiagnosticsInit (2): set by the manager to put the line in loop
           diagnostics mode and to start a loop diagnostics test.
           Only allowed for modems with ADSL2 or VDSL2 modes capabilities.
         - loopDiagnosticsCompleted (3): set by the system to indicate that
           diagnostics data can be retrieved.
         - loopDiagnosticsFailed (4): set by the system to indicate that the
           loop diagnostics initialization has failed and no diagnostics data
           can be retrieved.
         - loopDiagnosticsOff (1): allows the manager to leave the loop
           diagnostics mode. Loop diagnostics data is not available anymore.

         ALCATEL NOTE:
             ACCESS:   NA                  USAGE:    OPT 
             PERSIST:  NO                  INSRVMOD: YES
             RANGE:    NA                  DEFVALUE: loopDiagnosticsOff
             UNITS:    NA                  SPARSE:   NA
             DESCR:    NA "
::= {xdslLineConfEntry 7}

xdslLineTestModes OBJECT-TYPE
        SYNTAX      INTEGER
        ACCESS      read-write
        STATUS      mandatory 
        DESCRIPTION 
        "This variable allows to enable/disable particular XDSL modem test
         modes.
         It is coded as a bitmap defined as follows:
         - For future use -.
         ALCATEL NOTE:
             ACCESS:   NA                  USAGE:    NA
             PERSIST:  NA                  INSRVMOD: NA
             RANGE:    NA                  DEFVALUE: NA
             UNITS:    NA                  SPARSE:   NA
             DESCR:    This object is not supported. "
::= {xdslLineConfEntry 8}

xdslLineBondingModeChannel1            OBJECT-TYPE   
        SYNTAX          BondingModeType
        ACCESS          read-write
        STATUS          mandatory 
        DESCRIPTION 
        "This variable allows to configure XDSL Channel 1 either in native mode
         or in bonding mode.

         ALCATEL NOTE:
             ACCESS:   NA                  USAGE:    OPT
             PERSIST:  YES                 INSRVMOD: YES
             RANGE:    NA                  DEFVALUE: native
             UNITS:    NA                  SPARSE:   NA
             DESCR:    Set requests on this object are ignored. Updates are done
                       automatically by the system. "
::= {xdslLineConfEntry 9}

xdslLineBondingModeChannel2 OBJECT-TYPE
        SYNTAX      BondingModeType
        ACCESS      read-write
        STATUS      mandatory 
        DESCRIPTION 
        "This variable allows to configure XDSL Channel 2 either in native mode or
         in ATM bonding mode.
         Set requests on this object are ignored. Updates are done automatically by 
         the system.
         ALCATEL NOTE:
             ACCESS:   NA                  USAGE:    NA
             PERSIST:  NA                  INSRVMOD: NA
             RANGE:    NA                  DEFVALUE: native
             UNITS:    NA                  SPARSE:   NA
             DESCR:    This object is not supported. "
::= {xdslLineConfEntry 10}

xdslLineBondingModeChannel3 OBJECT-TYPE
        SYNTAX      BondingModeType
        ACCESS      read-write
        STATUS      mandatory 
        DESCRIPTION 
        "This variable allows to configure XDSL Channel 3 either in native mode or
         in ATM bonding mode.
         Set requests on this object are ignored. Updates are done automatically by 
         the system.
         ALCATEL NOTE:
             ACCESS:   NA                  USAGE:    NA
             PERSIST:  NA                  INSRVMOD: NA
             RANGE:    NA                  DEFVALUE: native
             UNITS:    NA                  SPARSE:   NA
             DESCR:    This object is not supported. "
::= {xdslLineConfEntry 11}

xdslLineBondingModeChannel4 OBJECT-TYPE
        SYNTAX      BondingModeType
        ACCESS      read-write
        STATUS      mandatory 
        DESCRIPTION 
        "This variable allows to configure XDSL Channel 4 either in native mode or
         in ATM bonding mode.
         Set requests on this object are ignored. Updates are done automatically by 
         the system.
         ALCATEL NOTE:
             ACCESS:   NA                  USAGE:    NA
             PERSIST:  NA                  INSRVMOD: NA
             RANGE:    NA                  DEFVALUE: native
             UNITS:    NA                  SPARSE:   NA
             DESCR:    This object is not supported. "
::= {xdslLineConfEntry 12}

xdslLineSeltMode OBJECT-TYPE
        SYNTAX  INTEGER {
                  seltOff (1),
                  seltNoise (2),
                  seltEcho (3),
                  seltCompleted (4),
                  seltFailed (5)
                }
        ACCESS      read-write
        STATUS      mandatory 
        DESCRIPTION 
        "The manager can request the modem to perform a single ended line test
         for this XDSL line. Two types of SELT tests are defined: noise measurement
         and echo response measurement. The test request will be rejected in case
         SELT testing is not supported for this line. The system will autonomously
         overwrite this parameter when the test is completed.

         The possible values are:
         - seltNoise (2): set by the manager to start a noise measurement.
         - seltEcho (3): set by the manager to start an echo response measurement.
         - seltCompleted (4): set by the system to indicate that SELT test data can
           be retrieved.
         - seltFailed (5): set by the system to indicate that the SELT measurement
           has failed and the requested data is not available.
         - seltOff (1): allows the manager to leave the SELT testing mode.
           SELT testing data is not available anymore.
         ALCATEL NOTE:
             ACCESS:   NA                  USAGE:    NA
             PERSIST:  NA                  INSRVMOD: NA
             RANGE:    NA                  DEFVALUE: seltOff
             UNITS:    NA                  SPARSE:   NA
             DESCR:    NA "
::= {xdslLineConfEntry 13}

xdslLineSeltEnable OBJECT-TYPE
        SYNTAX  INTEGER {
                  enabled (1),
                  disabled (2)
                }
        ACCESS      read-write
        STATUS      mandatory
        DESCRIPTION
        "This parameter allows the manager to enable the SELT feature on lines
         supporting SELT testing.  As long as the feature has not been enabled,
         it will not be possible to start a SELT test on this line.
         Once enabled, the feature cannot be disabled anymore.
         ALCATEL NOTE:
             ACCESS:   NA                  USAGE:    NA
             PERSIST:  NA                  INSRVMOD: NA
             RANGE:    NA                  DEFVALUE: disabled
             UNITS:    NA                  SPARSE:   NA
             DESCR:    This object is not supported. "
::= {xdslLineConfEntry 14}

xdslLineTpsTcMode       OBJECT-TYPE
        SYNTAX          TpsTcModeType
        ACCESS          read-write
        STATUS          mandatory
        DESCRIPTION
        "This variable allows to configure the TpsTc Mode of the line.
         atm: the atm transfer mode is selected
         ptm: the ptm transfer mode is selected
         default: the system selects the atm or ptm transfer mode based on the
         opmode board capabilities.
         - if the board supports only ATM TpsTc mode, this TpsTc mode shall
           always be set.  In other words, if xdslLineOpModePtmCapability is
           null PTM mode shall be forbidden.
         - if the board supports only PTM TpsTc mode, this TpsTc mode shall
           always be set.  In other words, if xdslLineOpModeAtmCapability is
           null ATM mode shall be forbidden.
         - if the board supports both TpsTc modes  (both
           xdslLineOpModeAtmCapability and xdslLineOpModePtmCapability contain
           valid opmodes), both atm and ptm are allowed.  When set to default, 
           PTM value shall be selected.
         The actual configured value is given by xdslLineActualConfTpsTcMode.

         ALCATEL NOTE:
             ACCESS:   NA                  USAGE:    OPT 
             PERSIST:  YES                 INSRVMOD: YES
             RANGE:    NA                  DEFVALUE: default
             UNITS:    NA                  SPARSE:   NA
             DESCR:    NA "
::= {xdslLineConfEntry 15}

xdslLineOpModeAtmCapability            OBJECT-TYPE
        SYNTAX          OpModeType
        ACCESS          read-only
        STATUS          mandatory
        DESCRIPTION
        "This variable indicates which operational modes are supported by
         the board for the corresponding line in ATM TpsTc mode.

         ALCATEL NOTE:
             ACCESS:   NA                  USAGE:    NA
             PERSIST:  NO                  INSRVMOD: NA
             RANGE:    NA                  DEFVALUE: NA 
             UNITS:    NA                  SPARSE:   NA
             DESCR:    NA "
::= {xdslLineConfEntry 16}

xdslLineOpModePtmCapability            OBJECT-TYPE
        SYNTAX          OpModeType
        ACCESS          read-only
        STATUS          mandatory
        DESCRIPTION
        "This variable indicates which operational modes are supported by
         the board for the corresponding line in PTM TpsTc mode.

         ALCATEL NOTE:
             ACCESS:   NA                  USAGE:    NA
             PERSIST:  NO                  INSRVMOD: NA
             RANGE:    NA                  DEFVALUE: NA 
             UNITS:    NA                  SPARSE:   NA
             DESCR:    NA "
::= {xdslLineConfEntry 17}

xdslLineActualConfTpsTcMode OBJECT-TYPE
        SYNTAX      TpsTcModeType
        ACCESS      read-only
        STATUS      mandatory
        DESCRIPTION
        "This variable indicates which TpsTc Mode is configured on the line:
         atm: the atm transfer mode is configured
         ptm: the ptm transfer mode is configured.
         ALCATEL NOTE:
             ACCESS:   NA                  USAGE:    NA
             PERSIST:  NO                  INSRVMOD: NA
             RANGE:    atm, ptm            DEFVALUE: NA
             UNITS:    NA                  SPARSE:   NA
             DESCR:    NA "
::= {xdslLineConfEntry 18}

xdslLineSeltUncalEchoMeasTime OBJECT-TYPE 
        SYNTAX          INTEGER
        ACCESS          read-write
        STATUS          mandatory
        DESCRIPTION
        "This object defines the maximum SELT measurement time to be used by 
         the modems to perform an Uncalibrated Echo (Variance) measurement.
         Valid range : 5..240 in steps of 1, units in seconds.
         ALCATEL NOTE:
             ACCESS:   NA                  USAGE:    OPT
             PERSIST:  NO                  INSRVMOD: NA
             RANGE:    5..240              DEFVALUE: 240
             UNITS:    seconds             SPARSE:   NA
             DESCR:    
             Note that the default value does not reflect the default value 
             used by the modem subsystem. The default value of the SELT 
             measurement time is only used when a retrieve is performed on 
             this OID before a set was done. 
             If this measurement time is not set, the proxy will take its own 
             implemented default value (this proxy implemented default can 
             differ for each proxy). "
::= {xdslLineConfEntry 19} 

xdslLineSeltQLNoiseMeasTime OBJECT-TYPE 
        SYNTAX          INTEGER
        ACCESS          read-write
        STATUS          mandatory
        DESCRIPTION
        "This object defines the maximum SELT measurement time to be used by 
         the modems to perform an Quiet Line Noise measurement
         Valid range : 5..240 in steps of 1, units in seconds.
         ALCATEL NOTE:
             ACCESS:   NA                  USAGE:    OPT
             PERSIST:  NO                  INSRVMOD: NA
             RANGE:    5..240              DEFVALUE: 5
             UNITS:    seconds             SPARSE:   NA
             DESCR:    
             Note that the default value does not reflect the default value 
             used by the modem subsystem. The default value of the SELT 
             measurement time is only used when a retrieve is performed on 
             this OID before a set was done. 
             If this measurement time is not set, the proxy will take its own 
             implemented default value (this proxy implemented default can 
             differ for each proxy). "
::= {xdslLineConfEntry 20}

xdslLineDpboProfileNbr              OBJECT-TYPE
        SYNTAX          AsamProfilePointer
        ACCESS          read-write
        STATUS          mandatory
        DESCRIPTION     
        "This object identifies the row of the xdslDpboProfileTable
         which defines the valid profile for the interface.

         ALCATEL NOTE:
             ACCESS:   NA                  USAGE:    OPT
             PERSIST:  YES                 INSRVMOD: YES
             RANGE:    0..50               DEFVALUE: 0
             UNITS:    NA                  SPARSE:   NA
             DESCR:    NA "
::= {xdslLineConfEntry 21}

xdslLineOverruleState              OBJECT-TYPE
        SYNTAX          INTEGER {
                             notCreated (1),
                             createdNoOverrules (2),
                             createdOverrules (3)
                        }
        ACCESS          read-only
        STATUS          mandatory
        DESCRIPTION     
        "This object identifies if the corresponding Overrule-record is created
         and if at least one parameter overrules the profile parameters.

         ALCATEL NOTE:
             ACCESS:   NA                  USAGE:    NA
             PERSIST:  NO                  INSRVMOD: NA
             RANGE:    1..3                DEFVALUE: NA
             UNITS:    NA                  SPARSE:   NA
             DESCR:    NA "
::= {xdslLineConfEntry 22}

xdslLineInsEnable OBJECT-TYPE
        SYNTAX  INTEGER {
                  enabled (1),
                  disabled (2)
                }
        ACCESS      read-write
        STATUS      mandatory
        DESCRIPTION
        "This parameter allows the manager to enable the INS feature on lines
         supporting INS.  As long as the feature has not been enabled,
         it will not be possible to start INS on this line.
         Once enabled, the feature cannot be disabled anymore.
         ALCATEL NOTE:
             ACCESS:   NA                  USAGE:    NA
             PERSIST:  YES                 INSRVMOD: NA
             RANGE:    NA                  DEFVALUE: disabled
             UNITS:    NA                  SPARSE:   NA
             DESCR:    NA "
::= {xdslLineConfEntry 23}

xdslLineSeltTxSignPsdType OBJECT-TYPE
        SYNTAX                  SeltTxSignPsdType  
        ACCESS                  read-write 
        STATUS                  mandatory  
        DESCRIPTION             
         "Defines the Tx signal Psd type to be used as limit for the 
          SELT echo response measurement excitation signal.
          The possible values are:
            - txSignPsdTypeDefault (1): Select the board dependant
              default Tx signal Psd Type.                 
            - txSignPsdTypeFromConfig (2): Derive PSD from the modem 
              line configuration data. The actual used Tx Signal Psd type can
              be retrieved via the xdslSeltSelectedPsdTypeUsed object.
            - txSignPsdTypeFromConfigVdsl2 (3): Derive PSD from the VDSL2
              modem line configuration data.
            - txSignPsdTypeFromConfigVdsl1 (4): Derive PSD from the VDSL1
              modem line configuration data.
            - txSignPsdTypeFromConfigAdsl1or2 (5): Derive PSD from the ADSL2 or
              ADSL1 modem line configuration data. 
            - txSignPsdTypeFromConfigAdsl2Plus (6): Derive PSD from the ADSL2+
              modem line configuration data. 
            - txSignPsdTypePreDefVdsl2 (7): Derive PSD from the 
              predefined, hard-coded VDSL2 profile. 
              (The modem line configuration data is to be ignored).
            - txSignPsdTypePreDefVdsl1 (8): Derive PSD from the 
              predefined, hard-coded VDSL1 profile. 
              (The modem line configuration data is to be ignored).
            - txSignPsdTypePreDefAllBandsVdsl2 (9): Derive PSD from the
              predefined, hard-coded all bands VDSL2 profile. 
              (The modem line configuration data is to be ignored).
            - txSignPsdTypePreDefAllBandsAdsl1 (10): Derive PSD from the
              predefined, hard-coded all bands ADSL1 profile. 
              (The modem line configuration data is to be ignored).
            - txSignPsdTypePreDefAllBandsAdsl2Plus (11): Derive PSD from the
              predefined, hard-coded all bands ADSL2+ profile. 
              (The modem line configuration data is to be ignored).
            - txSignPsdTypePreDefVdsl2RegionA (12): Derive PSD from the 
              predefined, hard-coded VDSL2 profile consistent with Annex A
              of G.993.2 
              (The modem line configuration data is to be ignored).
            - txSignPsdTypeFrom8dConfig (13): Derive PSD from the modem line 
              configuration data except for the VDSL2 profile that is fixed to 
              8d for SELT.  It can also be that ADSL configuration is selected 
              when the line is configured in ADSLx. The actual used Tx Signal
              Psd type can be retrieved via the xdslSeltSelectedPsdTypeUsed
              object.
            - txSignPsdTypeFrom8dConfigVdsl2 (14): Derive PSD from the VDSL2 
              modem line configuration data except for the VDSL2 profile that 
              is fixed to 8d for SELT.  It should give an error when the board 
              is configured in ADSL mode. The actual used Tx Signal Psd type 
              can be retrieved via the xdslSeltSelectedPsdTypeUsed object.

           Default value is txSignPsdTypeDefault.
         ALCATEL NOTE:
             ACCESS:   NA                  USAGE:    OPT
             PERSIST:  NO                  INSRVMOD: NA
             RANGE:    NA                  DEFVALUE: txSignPsdTypeDefault
             UNITS:    NA                  SPARSE:   NA
             DESCR:    NA "
::= {xdslLineConfEntry 24}

xdslLineSeltUncalEchoTargetMinSnr OBJECT-TYPE
        SYNTAX                  INTEGER  
        ACCESS                  read-write 
        STATUS                  mandatory  
        DESCRIPTION             
         "Defines the uncalibrated echo response measurement SNR minimal
          target to be used for the SELT Echo measurement. If the target
          minimal SNR cannot be achieved, the actual achieved minimal SNR
          can be retrieved via xdslSeltUncalEchoMinSnrUsed.
          INTEGER(+0,+120), in steps of 1, unit is dB.
          The special value -1000 indicates that no uncalibrated echo 
          response measurement SNR target is configured. The best SNR shall 
          be achieved within the configured echo measurement time 
          (See isamSELTUncalEchoMeasurementTime).
          Default value is -1000.
          The isamSELTUncalEchoTargetMinSnr value should be set for 
          each measurement
             ACCESS:   NA                  USAGE:    OPT
             PERSIST:  NO                  INSRVMOD: NA
             RANGE:    -1000,0..120        DEFVALUE: -1000
             UNITS:    NA                  SPARSE:   NA
             DESCR:    NA "
::= {xdslLineConfEntry 25}

xdslLineSeltAGC                OBJECT-TYPE
        SYNTAX                  INTEGER  
        ACCESS                  read-write 
        STATUS                  mandatory  
        DESCRIPTION             
         "Defines the AGC to be used for the SELT Echo measurement.
          INTEGER(-100,+100), in dB
          The special value -1000 requests to use Automatic GC.
          Default is to use Automatic GC.
          This value should be set for each measurement. 
             ACCESS:   NA                  USAGE:    OPT
             PERSIST:  NO                  INSRVMOD: NA
             RANGE:    -1000,-100..100     DEFVALUE: -1000
             UNITS:    NA                  SPARSE:   NA
             DESCR:    NA "
::= {xdslLineConfEntry 26}

xdslLineRtxProfileNbr              OBJECT-TYPE
        SYNTAX          AsamProfilePointer
        ACCESS          read-write
        STATUS          mandatory
        DESCRIPTION     
        "This object identifies the row of the xdslRtxProfileTable
         which defines the valid profile for the interface.

         ALCATEL NOTE:
             ACCESS:   NA                  USAGE:    OPT
             PERSIST:  YES                 INSRVMOD: YES
             RANGE:    0..128              DEFVALUE: 0
             UNITS:    NA                  SPARSE:   NA
             DESCR:    NA "
::= {xdslLineConfEntry 27}

xdslLineOperDataTable   OBJECT-TYPE
        SYNTAX          SEQUENCE OF XdslLineOperDataEntry
        ACCESS          not-accessible
        STATUS          mandatory
        DESCRIPTION     
        "The xdsl line operational data table.

         ALCATEL NOTE:
             TABLESIZE: DEP [number of XDSL lines]                   
             DESCR:     NA                   "
::= {xdslLineCurrent 1}

xdslLineOperDataEntry   OBJECT-TYPE
        SYNTAX          XdslLineOperDataEntry                   
        ACCESS          not-accessible
        STATUS          mandatory
        DESCRIPTION     
        "An entry in the xdsl line operational data table.

         Row creation : Entries for all XDSL lines belonging to a board are 
                        created when the board becomes operational.
         Row deletion : Entries for all XDSL lines belonging to a board are 
                        deleted when the board becomes unavailable. "
        INDEX          {ifIndex}
::= {xdslLineOperDataTable 1}

XdslLineOperDataEntry ::=
        SEQUENCE {
            xdslLineRelCapacityOccupationUpstream     INTEGER,
            xdslLineNoiseMarginUpstream               INTEGER,
            xdslLineOutputPowerDownstream             INTEGER,
            xdslLineSignalAttenuationUpstream         INTEGER,
            xdslLineLoopAttenuationUpstream           INTEGER,
            xdslLineActualOpMode                      OpModeType, 
            xdslLineXtucOpModeCapabilities            OpModeType,
            xdslLineLastTxStateDownstream             INTEGER,
            xdslLineActualPsdDownstream               INTEGER,
            xdslLinePowerMgtState                     INTEGER,
            xdslLinePerBandLoopAttenuationUpstream    PerBandOperDataType,
            xdslLinePerBandSignalAttenuationUpstream  PerBandOperDataType,
            xdslLinePerBandNoiseMarginUpstream        PerBandOperDataType,
            xdslLineHighestFrequencyUpstream          INTEGER,
            xdslLineElectricalLengthUsed              INTEGER,
            xdslLineTimingAdvanceCorrected            INTEGER,
            xdslLineActualTpsTcMode                   TpsTcModeType,
            xdslLineActualRaModeUpstream              XdslActualRAModeType,
            xdslLineActualRtxModeUpstream             ActualRtxMode
}

xdslLineRelCapacityOccupationUpstream  OBJECT-TYPE
        SYNTAX          INTEGER
        ACCESS          read-only
        STATUS          mandatory
        DESCRIPTION     
        "This parameter represents the ratio of the actual line bitrate over
         the maximum attainable line bitrate in the upstream direction. The
         line rate is equal to the net data rate rate plus all overhead
         information (framing overhead, Reed Solomon overhead, Trellis 
         overhead).
         When the modem is not in showtime, then the value measured in
         preceeding showtime session is returned. The value is fixed to 100%
         in case of activation failure when for that particular direction a
         bitrate higher than the attainable bitrate has been requested.
         When no data is available (e.g. before first showtime) value 0
         is used.
         Range is 0 to 100% with a granularity of 1 %.

         ALCATEL NOTE:
             ACCESS:   NA                  USAGE:    NA
             PERSIST:  NO                  INSRVMOD: NA
             RANGE:    0..100              DEFVALUE: 0
             UNITS:    percent             SPARSE:   NA
             DESCR:    NA "
::= {xdslLineOperDataEntry 1}

xdslLineNoiseMarginUpstream            OBJECT-TYPE
        SYNTAX          INTEGER
        ACCESS          read-only
        STATUS          mandatory
        DESCRIPTION     
        "This parameter indicates the current noise margin for the upstream
         direction. When the modem is not in showtime this 
         object will have the previously measured value. 
         When no data is available (e.g. before first showtime) value 0
         is used.
         Range is -64 to 63 dB with a granularity of 0,1 dB.
         It is represented as 1/10 * xdslLineNoiseMarginUpstream.

         ALCATEL NOTE:
             ACCESS:   NA                  USAGE:    NA
             PERSIST:  NO                  INSRVMOD: NA
             RANGE:    -640..630           DEFVALUE: 0
             UNITS:    dB / 10             SPARSE:   NA
             DESCR:    NA "
::= {xdslLineOperDataEntry 2}

xdslLineOutputPowerDownstream          OBJECT-TYPE
        SYNTAX          INTEGER
        ACCESS          read-only
        STATUS          mandatory
        DESCRIPTION     
        "This object gives the actual aggregate output power for the downstream 
         carriers. When the modem is not in showtime this object will have the
         previously measured value.
         When no data is available (e.g. before first showtime) value 0
         is used.
         Range is -31 to 31 dBm with a granularity of 0,1 dB.
         It is expressed as 1/10 * xdslLineOutputPowerDownstream .

         ALCATEL NOTE:
             ACCESS:   NA                  USAGE:    NA
             PERSIST:  NO                  INSRVMOD: NA
             RANGE:    -310..310           DEFVALUE: 0
             UNITS:    dBm / 10            SPARSE:   NA
             DESCR:    NA "
::= {xdslLineOperDataEntry 3}

xdslLineSignalAttenuationUpstream      OBJECT-TYPE
        SYNTAX          INTEGER
        ACCESS          read-only
        STATUS          mandatory
        DESCRIPTION     
        "This object gives the difference in dB between the power measured at
         the near-end receiver and that transmitted from the far-end. The
         signal attenuation is measured over all data carriers and is updated
         during showtime.
         When the modem is not in showtime this object will have the value
         measured during the previous showtime session.
         When no data is available (e.g. before first showtime) value 0
         is used.
         It is represented as 1/10 * xdslLineSignalAttenuationUpstream, with
         a range of (0..127dB) and a granularity of 0.1 dB.

         ALCATEL NOTE:
             ACCESS:   NA                  USAGE:    NA
             PERSIST:  NO                  INSRVMOD: NA
             RANGE:    0..1270             DEFVALUE: 0
             UNITS:    dB / 10             SPARSE:   NA
             DESCR:    NA "
::= {xdslLineOperDataEntry 4}

xdslLineLoopAttenuationUpstream        OBJECT-TYPE
        SYNTAX          INTEGER
        ACCESS          read-only
        STATUS          mandatory
        DESCRIPTION     
        "This object gives the difference in dB between the power 
         measured at the near-end receiver and that transmitted from the
         far-end over all sub-carriers. The loop attenuation is measured at
         initialization and is not updated during showtime.
         When the modem is not in showtime this object will have the value
         measured during the previous showtime session.
         When no data is available (e.g. before first showtime) value 0
         is used.
         It is represented as 1/10 * xdslLineLoopAttenuationUpstream, with
         a range of (0..127dB) and a granularity of 0.1 dB.

         ALCATEL NOTE:
             ACCESS:   NA                  USAGE:    NA
             PERSIST:  NO                  INSRVMOD: NA
             RANGE:    0..1270             DEFVALUE: 0
             UNITS:    dB / 10             SPARSE:   NA
             DESCR:    NA "
::= {xdslLineOperDataEntry 5}

xdslLineActualOpMode    OBJECT-TYPE
        SYNTAX          OpModeType
        ACCESS          read-only
        STATUS          mandatory
        DESCRIPTION 
        "This variable consists of a bitmap which represents the operational 
         mode of the ATU-C. In case the modem is not operational this object 
         represents the operational mode of the most recent initialization 
         procedure.
         If the modem has not been initialized yet, this object will have the
         value 0. It uses the same coding as defined in xdslLineOpMode.

         ALCATEL NOTE:
             ACCESS:   NA                  USAGE:    NA
             PERSIST:  NO                  INSRVMOD: NA
             RANGE:    NA
             DEFVALUE: '00 00 00 00 00 00 00 00 
                        00 00 00 00 00 00 00 00'H
             UNITS:    octets              SPARSE:   NA
             DESCR:    NA "
::= {xdslLineOperDataEntry 6}

xdslLineXtucOpModeCapabilities         OBJECT-TYPE
        SYNTAX          OpModeType
        ACCESS          read-only
        STATUS          mandatory
        DESCRIPTION 
        "This variable consists of a bitmap which represents the operational
         modes enabled at the XTU-C. It uses the same coding as defined in
         xdslLineOpMode.

         ALCATEL NOTE:
             ACCESS:   NA                  USAGE:    NA
             PERSIST:  NO                  INSRVMOD: NA
             RANGE:    NA 
             DEFVALUE: '00 00 00 00 00 00 00 00 
                        00 00 00 00 00 00 00 00'H
             UNITS:    octets              SPARSE:   NA
             DESCR:    NA "
::= {xdslLineOperDataEntry 7}

xdslLineLastTxStateDownstream     OBJECT-TYPE
        SYNTAX          INTEGER
        ACCESS          read-only
        STATUS          mandatory
        DESCRIPTION     
        "This object gives the last successful transmitted initialisation state
         as defined in G.997.1. It is reported for ADSL2 modes in Loop
         Diagnostics State only.
         ALCATEL NOTE:
             ACCESS:   NA                  USAGE:    NA
             PERSIST:  NO                  INSRVMOD: NA
             RANGE:    NA                  DEFVALUE: NA
             UNITS:    NA                  SPARSE:   NA
             DESCR:    This object is not supported. "
::= {xdslLineOperDataEntry 8}

xdslLineActualPsdDownstream            OBJECT-TYPE
        SYNTAX          INTEGER
        ACCESS          read-only
        STATUS          mandatory
        DESCRIPTION     
        "This object gives the average transmit power spectrum density over the
         used carriers in the downstream direction as measured at the U-C
         reference point.
         When the modem is not in showtime this object will have the value
         measured during the previous showtime session.
         When no data is available (e.g. before first showtime) value 0
         is used.
         Range is -95.5 dBm/Hz to 0 dBm/Hz with 0,1 dB steps. The actual PSD is
         represented as 1/10 * xdslLineActualPsdDownstream.

         ALCATEL NOTE:
             ACCESS:   NA                  USAGE:    NA
             PERSIST:  NO                  INSRVMOD: NA
             RANGE:    -955..0             DEFVALUE: 0
             UNITS:    dBm/Hz * 1/10       SPARSE:   NA
             DESCR:    NA "
::= {xdslLineOperDataEntry 9}

xdslLinePowerMgtState   OBJECT-TYPE
        SYNTAX          INTEGER {
                            l0 (1),
                            l1 (2),
                            l2 (3),
                            l3 (4)
                        }
        ACCESS          read-only
        STATUS          mandatory
        DESCRIPTION     
        "This object indicates the actual power management state of the line:
         - l0 (Synchronized): full transmission (i.e. showtime)
         - l1 (Low power): there is transmission on the line but the downstream
           net data rate is reduced. This state is NOT supported (replaced by
           L2 in standards).
         - l2 (Low power): there is transmission on the line but the downstream
           net data rate is reduced
         - l3 (No power): there is no transmission on the line

         ALCATEL NOTE:
             ACCESS:   NA                  USAGE:    NA
             PERSIST:  NO                  INSRVMOD: NA
             RANGE:    NA                  DEFVALUE: l3
             UNITS:    NA                  SPARSE:   NA
             DESCR:    NA "
::= {xdslLineOperDataEntry 10}

xdslLinePerBandLoopAttenuationUpstream           OBJECT-TYPE
        SYNTAX          PerBandOperDataType
        ACCESS          read-only
        STATUS          mandatory
        DESCRIPTION
        "This object indicates loop attenuation for each upstream band 
         (including optional band) in case of VDSL2.
         It is represented as 1/10 * xdslLinePerBandLoopAttenuationUpstream,
         for each band with a range of (0..127dB) and a granularity of 0.1 dB.
         Max value is used to indicate that no Opdata is available for the
         corresponding band.
         OCTETS (0,1) represent value for band 0, coded as an integer in the
         range 0.. 1270. The value is defined as MSB-LSB (big-endian).
         OCTETS (2*N,2*N+1) represent value for band N, coded as an integer in
         the range 0.. 1270. The value is defined as MSB-LSB (big-endian).
         Maximum value for N is 4.

         ALCATEL NOTE:
             ACCESS:   NA                  USAGE:    NA
             PERSIST:  NO                  INSRVMOD: NA
             RANGE:    NA
             DEFVALUE: '00 00 00 00 00 00 00 00 00 00'H
             UNITS:    octets              SPARSE:   NA
             DESCR:    NA "
::= {xdslLineOperDataEntry 11}

xdslLinePerBandSignalAttenuationUpstream         OBJECT-TYPE
        SYNTAX          PerBandOperDataType
        ACCESS          read-only
        STATUS          mandatory
        DESCRIPTION
        "This object indicates signal attenuation for each upstream band 
         (including optional band) in case of VDSL2.
         It is represented as 1/10 * xdslLinePerBandSignalAttenuationUpstream,
         for each band with a range of (0..127dB) and a granularity of 0.1 dB.
         Max value is used to indicate that no Opdata is available for the
         corresponding band.
         OCTETS (0,1) represent value for band 0, coded as an integer in the
         range 0.. 1270. The value is defined as MSB-LSB (big-endian).
         OCTETS (2*N,2*N+1) represent value for band N, coded as an integer in
         the range 0.. 1270. The value is defined as MSB-LSB (big-endian).
         Maximum value for N is 4.

         ALCATEL NOTE:
             ACCESS:   NA                  USAGE:    NA
             PERSIST:  NO                  INSRVMOD: NA
             RANGE:    NA
             DEFVALUE: '00 00 00 00 00 00 00 00 00 00'H
             UNITS:    octets              SPARSE:   NA
             DESCR:    NA "
::= {xdslLineOperDataEntry 12}

xdslLinePerBandNoiseMarginUpstream     OBJECT-TYPE
        SYNTAX          PerBandOperDataType
        ACCESS          read-only
        STATUS          mandatory
        DESCRIPTION
        "This object indicates noise margin for each upstream band (including 
         optional band in case of VDSL2.
         It is represented as 1/10 * xdslLinePerBandNoiseMarginUpstream,
         for each band with a range of (-64..63dB) and a granularity of 0.1 dB.
         Max value is used to indicate that no Opdata is available for the
         corresponding band.
         OCTETS (0,1) represent value for band 0, coded as an integer in the
         range -640.. 630. The value is defined as MSB-LSB (big-endian).
         OCTETS (2*N,2*N+1) represent value for band N, coded as an integer in 
         the range -640.. 630. The value is defined as MSB-LSB (big-endian).
         Maximum value for N is 4.

         ALCATEL NOTE:
             ACCESS:   NA                  USAGE:    NA
             PERSIST:  NO                  INSRVMOD: NA
             RANGE:    NA
             DEFVALUE: '00 00 00 00 00 00 00 00 00 00'H
             UNITS:    octets              SPARSE:   NA
             DESCR:    NA "
::= {xdslLineOperDataEntry 13}

xdslLineHighestFrequencyUpstream       OBJECT-TYPE
        SYNTAX          INTEGER
        ACCESS          read-only
        STATUS          mandatory
        DESCRIPTION
        "This object indicates the highest carrier frequency used
         in the upstream direction in case of VDSL2.

         ALCATEL NOTE:
             ACCESS:   NA                  USAGE:    NA
             PERSIST:  NO                  INSRVMOD: NA
             RANGE:    0..30000            DEFVALUE: 0
             UNITS:    kHz                 SPARSE:   NA
             DESCR:    NA "
::= {xdslLineOperDataEntry 14}

xdslLineElectricalLengthUsed           OBJECT-TYPE
        SYNTAX          INTEGER
        ACCESS          read-only
        STATUS          mandatory
        DESCRIPTION
        "This object indicates the Line Electrical Length actually used
         by XTU-C when mode is VDSL2.
         Range: 0 to 127.5 dB @ 1MHz , with 0.5 dB steps.
         Integer range: 0..255, actual value * 2.

         ALCATEL NOTE:
             ACCESS:   NA                  USAGE:    NA
             PERSIST:  NO                  INSRVMOD: NA
             RANGE:    0..255              DEFVALUE: 0
             UNITS:    dB/2 @ 1Mhz         SPARSE:   NA
             DESCR:    NA "
::= {xdslLineOperDataEntry 15}

xdslLineTimingAdvanceCorrected         OBJECT-TYPE
        SYNTAX          INTEGER
        ACCESS          read-only
        STATUS          mandatory
        DESCRIPTION
        "This object defines the timing advance of transmitted symbol with 
         respect to the received symbol when mode is VDSL-2.  Near end value
         corresponds to the value corrected by XTU-C.
         Range: -250000..250000 ns in steps of 10 ns.
         Integer range: -25000..25000 (actual value / 10)

         ALCATEL NOTE:
             ACCESS:   NA                  USAGE:    NA
             PERSIST:  NO                  INSRVMOD: NA
             RANGE:    -25000..25000       DEFVALUE: 0
             UNITS:    ns * 10             SPARSE:   NA
             DESCR:    NA "
::= {xdslLineOperDataEntry 16}

xdslLineActualTpsTcMode                OBJECT-TYPE
        SYNTAX          TpsTcModeType
        ACCESS          read-only
        STATUS          mandatory
        DESCRIPTION
        "This object indicates the TpsTcMode that is actually used.

         ALCATEL NOTE:
             ACCESS:   NA                  USAGE:    NA
             PERSIST:  NO                  INSRVMOD: NA
             RANGE:    atm,ptm             DEFVALUE: ptm
             UNITS:    NA                  SPARSE:   NA
             DESCR:    NA "
::= {xdslLineOperDataEntry 17}

xdslLineActualRaModeUpstream             OBJECT-TYPE
        SYNTAX          XdslActualRAModeType
        ACCESS          read-only
        STATUS          mandatory
        DESCRIPTION
        "This object indicates the Rate Adaptive mode in the upstream direction 
         that is actually used.

         ALCATEL NOTE:
             ACCESS:   NA                  USAGE:    NA
             PERSIST:  NO                  INSRVMOD: NA
             RANGE:    1,2,3,255           DEFVALUE: UnknownNotSupported
             UNITS:    NA                  SPARSE:   NA
             DESCR:    NA "
::= {xdslLineOperDataEntry 18}

xdslLineActualRtxModeUpstream             OBJECT-TYPE
        SYNTAX          ActualRtxMode
        ACCESS          read-only
        STATUS          mandatory
        DESCRIPTION
        "This object indicates if the RTX is used in the upstream direction .

         ALCATEL NOTE:
             ACCESS:   NA                  USAGE:    NA
             PERSIST:  NO                  INSRVMOD: NA
             RANGE:    1..6,255            DEFVALUE: UnknownNotSupported
             UNITS:    NA                  SPARSE:   NA
             DESCR:    NA "
::= {xdslLineOperDataEntry 19}

xdslLineCarrierDataTable               OBJECT-TYPE
        SYNTAX          SEQUENCE OF XdslLineCarrierDataEntry
        ACCESS          not-accessible
        STATUS          mandatory
        DESCRIPTION     
        "The xdsl line carrier data table.

         ALCATEL NOTE:
             TABLESIZE: DEP [number of XDSL lines]                    
             DESCR:     NA                   "
::= {xdslLineCurrent 2}

xdslLineCarrierDataEntry               OBJECT-TYPE
        SYNTAX          XdslLineCarrierDataEntry                   
        ACCESS          not-accessible
        STATUS          mandatory
        DESCRIPTION     
        "An entry in the xdsl line carrier data table.

         Row creation : Entries for all XDSL lines belonging to a board are 
                        created when the board becomes operational.
         Row deletion : Entries for all XDSL lines belonging to a board are 
                        deleted when the board becomes unavailable. "
        INDEX          {ifIndex}
::= {xdslLineCarrierDataTable 1}

XdslLineCarrierDataEntry ::=
        SEQUENCE {
            xdslLineCarrierLoadDownstream             OCTET STRING,
            xdslLineCarrierGainDownstream             OCTET STRING,
            xdslLineCarrierTssDownstream              OCTET STRING,
            xdslLineCarrierSnrUpstream                OCTET STRING,
            xdslLineCarrierQlnUpstream                OCTET STRING,
            xdslLineCarrierHlinUpstream               OCTET STRING,
            xdslLineCarrierHlogUpstream               OCTET STRING,
            xdslLineCarrierSpacingDownstream          CarrierSpacingType,
            xdslLineCarrierTxPsdDownstream            OCTET STRING,
            xdslLineCarrierGroupTxPsd                 SubCarrierGroupSizeType,
            xdslLineCarrierGroupLoad                  SubCarrierGroupSizeType,
            xdslLineCarrierGroupGain                  SubCarrierGroupSizeType,
            xdslLineCarrierGroupTss                  SubCarrierGroupSizeType,
            xdslLineCarrierGroupSnr                   SubCarrierGroupSizeType,
            xdslLineCarrierGroupQln                   SubCarrierGroupSizeType,
            xdslLineCarrierGroupHLin                  SubCarrierGroupSizeType,
            xdslLineCarrierGroupHLog                  SubCarrierGroupSizeType
         }

xdslLineCarrierLoadDownstream          OBJECT-TYPE
        SYNTAX          OCTET STRING
        ACCESS          read-only
        STATUS          mandatory
        DESCRIPTION     
        "This object represents the bit load distribution i.e. the number of
         bits per carrier group over the downstream passband.
         When the modem is not in showtime this object will have the previously
         measured value.
         When the data are not available because the measurement is not
         completed, not enabled or not supported, an empty string will be
         returned.
         The XDSL downstream passband is composed of one or more bands (maximum
         5,including VDSL optional band). Each carrier can carry up to 15 bits.
         The carrier load is coded as a bitmap defined as follows:
         OCTETS 0,1: INTEGER (0..4096), index of the start carrier group of the
         first downstream band. The value is defined as MSB-LSB (big-endian).
         OCTETS 2,3: INTEGER (0..4096), index of the stop carrier group of the
         first downstream band. The value is defined as MSB-LSB (big-endian).
         OCTET 4: contains the bit load of the first two carrier groups of the
         band.
         The load of the first carrier group uses the most significant 4 bits
         nibble.
         Range is 0-15 bits per carrier group, with a granularity of 1
         bit/carrier group.
         OCTETS 5..L: and so on, up to the last carrier group of the first
         downstream band. The last nibble of OCTET L is set to 0x0 if not used.
         OCTETS L+1..M: contain the start/stop carrier groups and the carrier
         load of the second downstream band when available.
         OCTETS M+1..N: contain the start/stop carrier groups and the carrier
         load of the third downstream band when available.
         OCTETS N+1..P: contain the start/stop carrier groups and the carrier
         load of the fourth downstream band when available.
         OCTETS P+1..Q: contain the start/stop carrier groups and the carrier
         load of the fifth downstream band when available.

         ALCATEL NOTE:
             ACCESS:   NA                  USAGE:    NA
             PERSIST:  NO                  INSRVMOD: NA
             RANGE:    0..4117             DEFVALUE: ''H
             UNITS:    octets              SPARSE:   NA
             DESCR:    NA "
::= {xdslLineCarrierDataEntry 1}

xdslLineCarrierGainDownstream          OBJECT-TYPE
        SYNTAX          OCTET STRING
        ACCESS          read-only
        STATUS          mandatory
        DESCRIPTION     
        "This object provides the gain allocation (i.e. gi) per carrier group 
         over the downstream passband.
         When the modem is not in showtime this object will have the previously
         measured value.
         When the data are not available because the measurement is not
         completed, not enabled or not supported, an empty string will be
         returned.
         The XDSL downstream passband is composed of one or more bands (maximum
         5, including VDSL optional band). The gain has a range of 
         approximately 0 - 8, in steps of 1/512.
         The gain value is represented as gi/512 on a linear scale with gi
         a 12 bits unsigned integer in the 0 to 4095 range given by the 12 LSB
         bits of a 2 bytes integer.
         The carrier gain allocation is coded as a bitmap defined as
         follows:
         OCTETS 0,1: INTEGER (0..4096), index of the start carrier group of the
         first downstream band. The value is defined as MSB-LSB (big-endian).
         OCTETS 2,3: INTEGER (0..4096), index of the stop carrier group of the
         first downstream band. The value is defined as MSB-LSB (big-endian).
         OCTETS 4,5: INTEGER, contains the gain of the first carrier group of
         the band (start carrier group).
         OCTETS 6..L: and so on until the last carrier group of the first
         downstream band (stop carrier group).
         OCTETS L+1..M: contain the start/stop carrier groups and the carrier
         gain of the second downstream band when available.
         OCTETS M+1..N: contain the start/stop carrier groups and the carrier
         gain of the third downstream band when available.
         OCTETS N+1..P: contain the start/stop carrier groups and the carrier
         gain of the fourth downstream band when available.
         OCTETS P+1..Q: contain the start/stop carrier groups and the carrier
         gain of the fifth downstream band when available.

         ALCATEL NOTE:
             ACCESS:   NA                  USAGE:    NA
             PERSIST:  NO                  INSRVMOD: NA
             RANGE:    0..8214             DEFVALUE: ''H
             UNITS:    octets              SPARSE:   NA
             DESCR:    NA "
::= {xdslLineCarrierDataEntry 2}

xdslLineCarrierTssDownstream     OBJECT-TYPE
        SYNTAX                    OCTET STRING
        ACCESS                    read-only
        STATUS                    mandatory
        DESCRIPTION     
         "This object provides the Transmit Spectrum Shaping parameters
         (i.e. tssi) for the downstream direction.
         Its definition is for further study.
         ALCATEL NOTE:
             ACCESS:   NA                  USAGE:    NA
             PERSIST:  NA                  INSRVMOD: NA
             RANGE:    NA                  DEFVALUE: NA
             UNITS:    NA                  SPARSE:   NA
             DESCR:    This object is not supported. "
::= {xdslLineCarrierDataEntry 3}

xdslLineCarrierSnrUpstream             OBJECT-TYPE
        SYNTAX          OCTET STRING
        ACCESS          read-only
        STATUS          mandatory
        DESCRIPTION     
        "This object provides the Signal to Noise Ratio per carrier group over
         the upstream passband.
         When the modem is not in showtime this object will have the previously
         measured value.
         When the data are not available because the measurement is not
         completed, not enabled or not supported, an empty string will be
         returned.
         The XDSL upstream passband is composed of one or more bands (maximum
         5, including VDSL optional band). The SNR has a range from -32 to 95
         dB in steps of 0.5 dB.
         It is represented as SNRi = -32 + snri/2, with snri an 8 bit
         unsigned integer in the range 0 to 254.
         The special value 255 indicates that no measurement is available for
         the carrier or that the measurement is out of range.
         The carrier snrs are coded as a bitmap defined as follows:
         OCTETS 0,1: INTEGER, contains the number of symbols used to
         measure the data. The value is defined as MSB-LSB (big-endian).
         OCTETS 2,3: INTEGER (0..4096), index of the start carrier group of the
         first upstream band. The value is defined as MSB-LSB (big-endian).
         OCTETS 4,5: INTEGER (0..4096), index of the stop carrier group of the
         first upstream band. The value is defined as MSB-LSB (big-endian).
         OCTETS 6: INTEGER, contains the snr of the first carrier group of the
         band (start carrier group).
         OCTETS 7..L: and so on until the last carrier group of the first
         upstream band (stop carrier group).
         OCTETS L+1..M: contain the start/stop carrier groups and the carrier
         snr of the second upstream band when available.
         OCTETS M+1..N: contain the start/stop carrier groups and the carrier
         snr of the third upstream band when available.
         OCTETS N+1..P: contain the start/stop carrier groups and the carrier
         snr of the fourth upstream band when available.
         OCTETS P+1..Q: contain the start/stop carrier groups and the carrier
         snr of the fifth upstream band when available.

         ALCATEL NOTE:
             ACCESS:   NA                  USAGE:    NA
             PERSIST:  NO                  INSRVMOD: NA
             RANGE:    0..4119             DEFVALUE: ''H
             UNITS:    octets              SPARSE:   NA
             DESCR:    NA "
::= {xdslLineCarrierDataEntry 4}

xdslLineCarrierQlnUpstream             OBJECT-TYPE
        SYNTAX          OCTET STRING
        ACCESS          read-only
        STATUS          mandatory
        DESCRIPTION     
        "This object provides the Quiet Line Noise measurement (QLN) per
         carrier group over the upstream passband.
         When the data are not available because the measurement is not
         completed, not enabled or not supported, an empty string will be
         returned.
         The XDSL upstream passband is composed of one or more bands (maximum
         5, including VDSL optional band). The QLN has a range from -150 dBm/Hz
         to -23 dBm/Hz in steps
         of 0.5 dB. It is represented as QLNi = -23 - qlni/2, with qlni an
         8 bit unsigned integer in the range 0 to 254.
         The special value 255 indicates that no measurement is available for
         the carrier or that the measurement is out of range.
         The carrier qlns are coded as a bitmap defined as follows:
         OCTETS 0,1: INTEGER, contains the number of symbols used to
         measure the data. The value is defined as MSB-LSB (big-endian).
         OCTETS 2,3: INTEGER (0..4096), index of the start carrier group of the
         first upstream band. The value is defined as MSB-LSB (big-endian).
         OCTETS 4,5: INTEGER (0..4096), index of the stop carrier group of the
         first upstream band. The value is defined as MSB-LSB (big-endian).
         OCTETS 6: INTEGER, contains the qln of the first carrier group of the
         band (start carrier group).
         OCTETS 7..L: and so on until the last carrier group of the first
         upstream band (stop carrier group).
         OCTETS L+1..M: contain the start/stop carrier groups and the carrier
         qln of the second downstream band when available.
         OCTETS M+1..N: contain the start/stop carrier groups and the carrier
         qln of the third upstream band when available.
         OCTETS N+1..P: contain the start/stop carrier groups and the carrier
         qln of the fourth upstream band when available.
         OCTETS P+1..Q: contain the start/stop carrier groups and the carrier
         qln of the fifth upstream band when available.

         ALCATEL NOTE:
             ACCESS:   NA                  USAGE:    NA
             PERSIST:  NO                  INSRVMOD: NA
             RANGE:    0..4119             DEFVALUE: ''H
             UNITS:    octets              SPARSE:   NA
             DESCR:    NA "
::= {xdslLineCarrierDataEntry 5}

xdslLineCarrierHlinUpstream            OBJECT-TYPE
        SYNTAX          OCTET STRING
        ACCESS          read-only
        STATUS          mandatory
        DESCRIPTION      
        "This object provides the channel characteristics function complex
         values in linear scale for each carrier group over the upstream
         passband.
         When the data are not available because the measurement is not
         completed, not enabled or not supported, an empty string will be
         returned.
         The XDSL upstream passband is composed of one or more bands (maximum
         5, including VDSL optional band ).
         HLIN has a range of approximately +6 dB to -90 dB, with a granularity
         of 2^-15. The Hlin is represented as
         HLINi = (scale/2^15)*((ai+j*bi)/2^15),
         with ai and bi 2 bytes signed integers in the range -32767 to 32767.
         The special value -32768 indicates that no measurement is available
         for the carrier or that the measurement is out of range.
         The scale factor is a 2 bytes unsigned integer. The scale factor
         must be chosen such that:
         max(|Ai|,|Bi|) over all i is equal to 2^15-1, i.e. over all carriers
         of the XDSL band(s) of the corresponding direction.

         The carrier HLINs are coded as a bitmap defined as follows:
         OCTETS 0,1: INTEGER, contains the number of symbols used to
         measure the data. The value is defined as MSB-LSB (big-endian).
         OCTETS 2,3: INTEGER(0..65535), contains the scale factor to apply to
         the hlin values, over the upstream band(s).
         The value is defined as MSB-LSB (big-endian).
         OCTETS 4,5: INTEGER (0..4096), index of the start carrier group of the
         first upstream band. The value is defined as MSB-LSB (big-endian).
         OCTETS 6,7: INTEGER (0..4096), index of the stop carrier group of the
         first upstream band. The value is defined as MSB-LSB (big-endian).
         OCTETS 8,9: SIGNED INTEGER , contains the ai for the first carrier
         group of the band (start carrier group).
         The value is defined as MSB-LSB (big-endian).
         OCTETS 10,11: SIGNED INTEGER , contains the bi for the first carrier
         group of the band (start carrier group). 
         The value is defined as MSB-LSB (big-endian).
         OCTETS 12..L: ai and bi for the next carrier group and so on until the 
         last carrier group of the first upstream band (stop carrier group).
         OCTETS L+1..M: contain the start/stop carrier groups and the HLIN ai
         and bi of the second upstream band when available.
         OCTETS M+1..N: contain the start/stop carrier groups and the HLIN ai
         and bi of the third upstream band when available.
         OCTETS N+1..P: contain the start/stop carrier groups and the HLIN ai
         and bi of the fourth upstream band when available.
         OCTETS P+1..Q: contain the start/stop carrier groups and the HLIN ai
         and bi of the fifth upstream band when available.

         ALCATEL NOTE:
             ACCESS:   NA                  USAGE:    NA
             PERSIST:  NO                  INSRVMOD: NA
             RANGE:    0..8218             DEFVALUE: ''H
             UNITS:    octets              SPARSE:   NA
             DESCR:    NA "
::= {xdslLineCarrierDataEntry 6}

xdslLineCarrierHlogUpstream            OBJECT-TYPE
        SYNTAX          OCTET STRING
        ACCESS          read-only
        STATUS          mandatory
        DESCRIPTION     
        "This object provides the channel characteristics function real values
         in dB for each carrier group over the upstream passband.
         When the data are not available because the measurement is not
         completed, not enabled or not supported, an empty string will be
         returned.
         The XDSL upstream passband is composed of one or more bands (maximum
         5, including VDSL optional band).
         Hlog has a range of approximately +6 dB to -96 dB in steps of
         0.1 dB. The Hlog is represented as HLOGi = 6 - mi/10,
         with mi a 10 bits unsigned integer in the range 0 to 1022.
         The special value 1023 indicates that no measurement is available for
         the carrier or that the measurement is out of range.

         The carrier HLOGs are coded as a bitmap defined as follows:
         OCTETS 0,1: INTEGER, contains the number of symbols used to
         measure the data. The value is defined as MSB-LSB (big-endian).
         OCTETS 2,3: INTEGER (0..4096), index of the start carrier group of the
         first upstream band. The value is defined as MSB-LSB (big-endian).
         OCTETS 4,5: INTEGER (0..4096), index of the stop carrier group of the
         first upstream band. The value is defined as MSB-LSB (big-endian).
         OCTETS 6,7: INTEGER (0..1023), contains the HLOG mi of the first
         carrier group of the band (start carrier group).
         The value is defined as MSB-LSB (big-endian).
         OCTETS 8..L: mi for the next carrier group and so on until the last
         carrier group of the first upstream band (stop carrier group).
         OCTETS L+1..M: contain the start/stop carrier groups and the HLOG mi
         of the second upstream band when available.
         OCTETS M+1..N: contain the start/stop carrier groups and the HLOG mi
         of the third upstream band when available.
         OCTETS N+1..P: contain the start/stop carrier groups and the HLOG mi
         of the fourth upstream band when available.
         OCTETS P+1..Q: contain the start/stop carrier groups and the HLOG mi
         of the fifth upstream band when available.

         ALCATEL NOTE:
             ACCESS:   NA                  USAGE:    NA
             PERSIST:  NO                  INSRVMOD: NA
             RANGE:    0..8216             DEFVALUE: ''H
             UNITS:    octets              SPARSE:   NA
             DESCR:    NA "
::= {xdslLineCarrierDataEntry 7}

xdslLineCarrierSpacingDownstream       OBJECT-TYPE
        SYNTAX          CarrierSpacingType
        ACCESS          read-only
        STATUS          mandatory
        DESCRIPTION     
        "This object provides the actual carrier spacing used on the XDSL line 
         in the downstream direction:
          singleCarrierSpacing:  4.3125 kHz 
          doubleCarrierSpacing:  8.6250 kHz 
          halfCarrierSpacing:    2.15625 kHz 
          quarterCarrierSpacing: 1.078125 kHz

         ALCATEL NOTE:
             ACCESS:   NA                  USAGE:    NA
             PERSIST:  NO                  INSRVMOD: NA
             RANGE:    NA                  DEFVALUE: NA
             UNITS:    NA                  SPARSE:   NA
             DESCR:    NA "
::= {xdslLineCarrierDataEntry 8}

xdslLineCarrierTxPsdDownstream         OBJECT-TYPE
        SYNTAX          OCTET STRING
        ACCESS          read-only
        STATUS          mandatory
        DESCRIPTION
        "Provides the actual transmit PSD per carrier group over the
         downstream passband.
         When the modem is not in showtime this object will have the previously
         measured value.
         When the data are not available because the measurement is not
         completed, not enabled or not supported, an empty string will be
         returned.
         The XDSL downstream passband is composed of one or more bands (maximum
         5, including VDSL optional band). 
         The PSD has a range from -127 dBm/Hz to 0 dBm/Hz in steps of 0.5 dB.
         It is represented as PSDi = - psdi/2, with psdi an 8 bit
         unsigned integer in the range 0 to 254.
         The special value 255 indicates that no measurement is available for
         the carrier, the carrier is not loaded, or that the measurement is out
         of range.
         The carrier Tx PSD is coded as a bitmap defined as follows:
         OCTETS 0,1: INTEGER (0..4096), index of the start carrier group of the
         downstream band. The value is defined as MSB-LSB (big-endian).
         OCTETS 2,3: INTEGER (0..4096), index of the stop carrier group of the
         downstream band. The value is defined as MSB-LSB (big-endian).
         OCTET 4: INTEGER(0..255), PSD of the first carrier group of the band
         (start carrier group).
         OCTETS 5..L: and so on until the last carrier group of the first
         downstream band (stop carrier group).
         OCTETS L+1..M: contain the start/stop carrier groups and the carrier
         PSD of the second downstream band when available.
         OCTETS M+1..N: contain the start/stop carrier groups and the carrier
         PSD of the third downstream band when available.
         OCTETS N+1..P: contain the start/stop carrier groups and the carrier
         PSD of the fourth downstream band when available.
         OCTETS P+1..Q: contain the start/stop carrier groups and the carrier
         PSD of the fifth downstream band when available.

         ALCATEL NOTE:
             ACCESS:   NA                  USAGE:    NA
             PERSIST:  NO                  INSRVMOD: NA
             RANGE:    0..4117             DEFVALUE: ''H
             UNITS:    octets              SPARSE:   NA
             DESCR:    NA "
::= {xdslLineCarrierDataEntry 9}

xdslLineCarrierGroupTxPsd              OBJECT-TYPE
        SYNTAX          SubCarrierGroupSizeType
        ACCESS          read-only
        STATUS          mandatory
        DESCRIPTION
        "Provides the grouping factor for Actual Tx Power Spectrum Density
         carrier data octet-string.  The grouping factor represents the number
         of carriers that have been grouped together in view to reduce data 
         size.

         ALCATEL NOTE:
             ACCESS:   NA                  USAGE:    NA
             PERSIST:  NO                  INSRVMOD: NA
             RANGE:    1, 2, 4, 8          DEFVALUE: 1
             UNITS:    NA                  SPARSE:   NA
             DESCR:    NA "
::= {xdslLineCarrierDataEntry 10}

xdslLineCarrierGroupLoad               OBJECT-TYPE
        SYNTAX          SubCarrierGroupSizeType
        ACCESS          read-only
        STATUS          mandatory
        DESCRIPTION
        "Provides the grouping factor for carrier load data octet-
         string.  The grouping factor represents the number of carriers that
         have been grouped together in view to reduce data size.

         ALCATEL NOTE:
             ACCESS:   NA                  USAGE:    NA
             PERSIST:  NO                  INSRVMOD: NA
             RANGE:    1, 2, 4, 8          DEFVALUE: 1
             UNITS:    NA                  SPARSE:   NA
             DESCR:    NA "
::= {xdslLineCarrierDataEntry 11}

xdslLineCarrierGroupGain               OBJECT-TYPE
        SYNTAX          SubCarrierGroupSizeType
        ACCESS          read-only
        STATUS          mandatory
        DESCRIPTION
        "Provides the grouping factor for carrier gain allocation data octet-
         string.  The grouping factor represents the number of carriers that
         have been grouped together in view to reduce data size.

         ALCATEL NOTE:
             ACCESS:   NA                  USAGE:    NA
             PERSIST:  NO                  INSRVMOD: NA
             RANGE:    1, 2, 4, 8          DEFVALUE: 1
             UNITS:    NA                  SPARSE:   NA
             DESCR:    NA "
::= {xdslLineCarrierDataEntry 12}

xdslLineCarrierGroupTss                         OBJECT-TYPE
                SYNTAX                                  SubCarrierGroupSizeType
                ACCESS                                  read-only
                STATUS                                  mandatory
                DESCRIPTION
                "Provides the grouping factor for Transmit Spectrum Shaping carrier data
                 octet-string.  The grouping factor represents the number of carriers that
                 have been grouped together in view to reduce data size.
         ALCATEL NOTE:
             ACCESS:   NA                  USAGE:    NA
             PERSIST:  NA                  INSRVMOD: NA
             RANGE:    NA                  DEFVALUE: NA
             UNITS:    NA                  SPARSE:   NA
             DESCR:    This object is not supported. "
::= {xdslLineCarrierDataEntry 13}

xdslLineCarrierGroupSnr OBJECT-TYPE
        SYNTAX          SubCarrierGroupSizeType
        ACCESS          read-only
        STATUS          mandatory
        DESCRIPTION
        "Provides the grouping factor for Signal to Noise Ratio per carrier 
         data octet-string.  The grouping factor represents the number of 
         carriers that have been grouped together in view to reduce data size.

         ALCATEL NOTE:
             ACCESS:   NA                  USAGE:    NA
             PERSIST:  NO                  INSRVMOD: NA
             RANGE:    1, 2, 4, 8          DEFVALUE: 1
             UNITS:    NA                  SPARSE:   NA
             DESCR:    NA "
::= {xdslLineCarrierDataEntry 14}

xdslLineCarrierGroupQln OBJECT-TYPE
        SYNTAX          SubCarrierGroupSizeType
        ACCESS          read-only
        STATUS          mandatory
        DESCRIPTION
        "Provides the grouping factor for Quiet Line Noise data octet-
         string.  The grouping factor represents the number of carriers that
         have been grouped together in view to reduce data size.

         ALCATEL NOTE:
             ACCESS:   NA                  USAGE:    NA
             PERSIST:  NO                  INSRVMOD: NA
             RANGE:    1, 2, 4, 8          DEFVALUE: 1
             UNITS:    NA                  SPARSE:   NA
             DESCR:    NA "
::= {xdslLineCarrierDataEntry 15}

xdslLineCarrierGroupHLin               OBJECT-TYPE
        SYNTAX          SubCarrierGroupSizeType
        ACCESS          read-only
        STATUS          mandatory
        DESCRIPTION
        "Provides the grouping factor for Complex Channel Characteristics data
         in linear scale.  The grouping factor represents the number of 
         carriers that have been grouped together in view to reduce data size.

         ALCATEL NOTE:
             ACCESS:   NA                  USAGE:    NA
             PERSIST:  NO                  INSRVMOD: NA
             RANGE:    1, 2, 4, 8          DEFVALUE: 1
             UNITS:    NA                  SPARSE:   NA
             DESCR:    NA "
::= {xdslLineCarrierDataEntry 16}

xdslLineCarrierGroupHLog               OBJECT-TYPE
        SYNTAX          SubCarrierGroupSizeType
        ACCESS          read-only
        STATUS          mandatory
        DESCRIPTION
        "Provides the grouping factor for Channel Characteristics data in dB.
         The grouping factor represents the number of carriers that
         have been grouped together in view to reduce data size.

         ALCATEL NOTE:
             ACCESS:   NA                  USAGE:    NA
             PERSIST:  NO                  INSRVMOD: NA
             RANGE:    1, 2, 4, 8          DEFVALUE: 1
             UNITS:    NA                  SPARSE:   NA
             DESCR:    NA "
::= {xdslLineCarrierDataEntry 17}

xdslLineFailureStatusTable             OBJECT-TYPE
        SYNTAX          SEQUENCE OF XdslLineFailureStatusEntry
        ACCESS          not-accessible
        STATUS          mandatory
        DESCRIPTION     
        "The xdsl line near end failure status table.

         ALCATEL NOTE:
             TABLESIZE: DEP [number of XDSL lines]                    
             DESCR:     NA                   "
::= {xdslLineCurrent 3}
        
xdslLineFailureStatusEntry             OBJECT-TYPE
        SYNTAX          XdslLineFailureStatusEntry                      
        ACCESS          not-accessible
        STATUS          mandatory
        DESCRIPTION     
        "An entry in the xdsl line near end failure status table.

         Row creation : Entries for all XDSL lines belonging to a board are 
                        created when the board becomes operational.
         Row deletion : Entries for all XDSL lines belonging to a board are 
                        deleted when the board becomes unavailable. "
        INDEX          {ifIndex}
::= {xdslLineFailureStatusTable 1}
        
XdslLineFailureStatusEntry ::=
        SEQUENCE {
                xdslLineFailureStatus           INTEGER,
                xdslLineActivationFailureErrorCode  INTEGER
        }

xdslLineFailureStatus   OBJECT-TYPE
        SYNTAX          INTEGER (1..65535)  
        ACCESS          read-only
        STATUS          mandatory
        DESCRIPTION 
        "This variable indicates the status of the near end interface. It is a 
         bitmap represented as a sum, therefore, it can represent multiple 
         failure simultaneuosly. The xdslLineNoDefect should be set if and only 
         if no other  flag is set. The various bit positions are:
           1     xdslLineNoDefect
           2     xdslLineLOS (loss of signal) in the upstream direction
           4     xdslLineLOF (loss of frame) in the upstream direction 
           8     xdslLineLOM (loss of margin) in the upstream direction
          16     xdslLineLPR (loss of power) of the ATU-C
          64     xdslLineESE (Excessive Severe Errors) in the upstream
                 direction
         128     xdslLineActivationFailure due to configuration error
         256     xdslLineActivationFailure due to configuration not feasible
         512..2048 reserved
         4096    xdslLineBitrateThreshold for the upstream direction.
         8192    xdslLineTpsTc Mismatch
        16384    xdslLine Forced Rtx InitFailure

         ALCATEL NOTE:
             ACCESS:   NA                  USAGE:    NA
             PERSIST:  NO                  INSRVMOD: NA
             RANGE:    NA                  DEFVALUE: 1
             UNITS:    NA                  SPARSE:   NA
             DESCR:    NA "
::= {xdslLineFailureStatusEntry 1}

xdslLineActivationFailureErrorCode   OBJECT-TYPE
        SYNTAX          INTEGER  
        ACCESS          read-only
        STATUS          mandatory
        DESCRIPTION 
        "In case xdslLineFailureStatus entry reports activation failure due to
         configuration error or activation failure due to configuration not
         feasible, this variable indicates the failure cause with the most
         detailed error code possible. In case of failure with multiple causes
         the first applicable error code shall be reported.
         In case xdslLineFailureStatus does not report an activation failure or 
         the failure cause is unknown, this parameter shall be 0.

         ALCATEL NOTE:
             ACCESS:   NA                  USAGE:    NA
             PERSIST:  NO                  INSRVMOD: NA
             RANGE:    NA                  DEFVALUE: NA
             UNITS:    NA                  SPARSE:   NA
             DESCR:    NA "
::= {xdslLineFailureStatusEntry 2}

xdslLineCurrentIntervalTable           OBJECT-TYPE
        SYNTAX          SEQUENCE OF XdslLineCurrentIntervalEntry
        ACCESS          not-accessible
        STATUS          mandatory
        DESCRIPTION     
        "The xdsl line near end current interval table.

         ALCATEL NOTE:
             TABLESIZE: DEP [number of XDSL lines]                    
             DESCR:     NA                   "
::= {xdslLineCurrent 4}
        
xdslLineCurrentIntervalEntry           OBJECT-TYPE
        SYNTAX          XdslLineCurrentIntervalEntry                    
        ACCESS          not-accessible
        STATUS          mandatory
        DESCRIPTION     
        "An entry in the xdsl line near end current interval table.

         Row creation : Entries for all XDSL lines belonging to a board are 
                        created when the board becomes operational.
         Row deletion : Entries for all XDSL lines belonging to a board are 
                        deleted when the board becomes unavailable. "
        INDEX          {ifIndex}
::= {xdslLineCurrentIntervalTable 1}

XdslLineCurrentIntervalEntry ::=
        SEQUENCE {
            xdslLineCurrentIntervalLOSCounter         Counter,
            xdslLineCurrentIntervalLOFCounter         Counter,
            xdslLineCurrentIntervalLOMCounter         Counter,
            xdslLineCurrentIntervalLPRCounter         Counter,
            xdslLineCurrentIntervalESECounter         Counter,
            xdslLineCurrentIntervalESCounter          Counter,
            xdslLineCurrentIntervalSESCounter         Counter,
            xdslLineCurrentIntervalUASCounter         Counter,
            xdslLineCurrentIntervalReInitCounter      Counter,
            xdslLineCurrentIntervalFailedInitCounter  Counter,
            xdslLineCurrentIntervalMeasuredTime       INTEGER,
            xdslLineCurrentIntervalInvalidDataFlag    INTEGER,
            xdslLineCurrentIntervalRAUCounter         Counter,
            xdslLineCurrentIntervalRADCounter         Counter,
            xdslLineCurrentIntervalLEFTRSCounter      Counter,
            xdslLineCurrentIntervalErrFreeBitsCounter Counter,
            xdslLineCurrentIntervalMinEFTRValue       INTEGER
        }

xdslLineCurrentIntervalLOSCounter      OBJECT-TYPE
        SYNTAX          Counter
        ACCESS          read-only
        STATUS          mandatory
        DESCRIPTION     
        "This object represents for the current 15 minute interval the LOS 
         failure count, which is the number of occurences of an LOS failure 
         event, where a failure event occurs when the failure is declared and 
         ends when the failure clears.

         ALCATEL NOTE:
             ACCESS:   NA                  USAGE:    NA
             PERSIST:  NO                  INSRVMOD: NA
             RANGE:    NA                  DEFVALUE: 0
             UNITS:    NA                  SPARSE:   NA
             DESCR:    NA "
::= {xdslLineCurrentIntervalEntry 1}

xdslLineCurrentIntervalLOFCounter      OBJECT-TYPE
        SYNTAX          Counter
        ACCESS          read-only
        STATUS          mandatory
        DESCRIPTION     
        "This object represents for the current 15 minute interval the LOF 
         failure count, which is the number of occurences of an LOF failure 
         event, where a failure event occurs when the failure is declared and 
         ends when the failure clears.

         ALCATEL NOTE:
             ACCESS:   NA                  USAGE:    NA
             PERSIST:  NO                  INSRVMOD: NA
             RANGE:    NA                  DEFVALUE: 0
             UNITS:    NA                  SPARSE:   NA
             DESCR:    NA "
::= {xdslLineCurrentIntervalEntry 2}

xdslLineCurrentIntervalLOMCounter      OBJECT-TYPE
        SYNTAX          Counter
        ACCESS          read-only
        STATUS          mandatory
        DESCRIPTION     
        "This object represents for the current 15 minute interval the LOM
         failure count, which is the number of occurences of a LOM failure 
         event, where a failure event occurs when the failure is declared and 
         ends when the failure clears.

         ALCATEL NOTE:
             ACCESS:   NA                  USAGE:    NA
             PERSIST:  NO                  INSRVMOD: NA
             RANGE:    NA                  DEFVALUE: 0
             UNITS:    NA                  SPARSE:   NA
             DESCR:    NA "
::= {xdslLineCurrentIntervalEntry 3}

xdslLineCurrentIntervalLPRCounter       OBJECT-TYPE
        SYNTAX          Counter
        ACCESS          read-only
        STATUS          mandatory
        DESCRIPTION     
        "This object represents for the current 15 minute interval the LPR 
         failure count, which is the number of occurences of an LPR failure 
         event, where a failure event occurs when the failure is declared and 
         ends when the failure clears.
         ALCATEL NOTE:
             ACCESS:   NA                  USAGE:    NA
             PERSIST:  NA                  INSRVMOD: NA
             RANGE:    NA                  DEFVALUE: NA
             UNITS:    NA                  SPARSE:   NA
             DESCR:    This object is not supported. "
::= {xdslLineCurrentIntervalEntry 4}

xdslLineCurrentIntervalESECounter      OBJECT-TYPE
        SYNTAX          Counter
        ACCESS          read-only
        STATUS          mandatory
        DESCRIPTION     
        "This object represents for the current 15 minute interval the ESE 
         failure count, which is the number of occurences of an ESE failure 
         event, where a failure event occurs when the failure is declared and 
         ends when the failure clears.

         ALCATEL NOTE:
             ACCESS:   NA                  USAGE:    NA
             PERSIST:  NO                  INSRVMOD: NA
             RANGE:    NA                  DEFVALUE: 0
             UNITS:    NA                  SPARSE:   NA
             DESCR:    NA "
::= {xdslLineCurrentIntervalEntry 5}

xdslLineCurrentIntervalESCounter       OBJECT-TYPE
        SYNTAX          Counter
        ACCESS          read-only
        STATUS          mandatory
        DESCRIPTION     
        "The counter associated with the number of Errored Seconds encountered 
         by the line in the current 15 minute interval.

         ALCATEL NOTE:
             ACCESS:   NA                  USAGE:    NA
             PERSIST:  NO                  INSRVMOD: NA
             RANGE:    NA                  DEFVALUE: 0
             UNITS:    NA                  SPARSE:   NA
             DESCR:    NA "
::= {xdslLineCurrentIntervalEntry 6}

xdslLineCurrentIntervalSESCounter      OBJECT-TYPE
        SYNTAX          Counter
        ACCESS          read-only
        STATUS          mandatory
        DESCRIPTION     
        "The counter associated with the number of Severely Errored Seconds
         encountered by the line in the current 15 minute interval.

         ALCATEL NOTE:
             ACCESS:   NA                  USAGE:    NA
             PERSIST:  NO                  INSRVMOD: NA
             RANGE:    NA                  DEFVALUE: 0
             UNITS:    NA                  SPARSE:   NA
             DESCR:    NA "
::= {xdslLineCurrentIntervalEntry 7}

xdslLineCurrentIntervalUASCounter      OBJECT-TYPE
        SYNTAX          Counter
        ACCESS          read-only
        STATUS          mandatory
        DESCRIPTION     
        "The counter associated with the number of Unavailable Seconds
         encountered by the line in the current 15 minute interval.

         ALCATEL NOTE:
             ACCESS:   NA                  USAGE:    NA
             PERSIST:  NO                  INSRVMOD: NA
             RANGE:    NA                  DEFVALUE: 0
             UNITS:    NA                  SPARSE:   NA
             DESCR:    NA "
::= {xdslLineCurrentIntervalEntry 8}

xdslLineCurrentIntervalReInitCounter   OBJECT-TYPE
        SYNTAX          Counter
        ACCESS          read-only
        STATUS          mandatory
        DESCRIPTION     
        "This object represents for the current 15 minute interval the number
         of times the modem left showtime and tried to re-initialize the line
         because of detection of a persistent defect.

         ALCATEL NOTE:
             ACCESS:   NA                  USAGE:    NA
             PERSIST:  NO                  INSRVMOD: NA
             RANGE:    NA                  DEFVALUE: 0
             UNITS:    NA                  SPARSE:   NA
             DESCR:    NA "
::= {xdslLineCurrentIntervalEntry 9}

xdslLineCurrentIntervalFailedInitCounter         OBJECT-TYPE
        SYNTAX          Counter
        ACCESS          read-only
        STATUS          mandatory
        DESCRIPTION     
        "This object represents for the current 15 minute interval the number
         of times the modem tries to initialize the line but fails.

         ALCATEL NOTE:
             ACCESS:   NA                  USAGE:    NA
             PERSIST:  NO                  INSRVMOD: NA
             RANGE:    NA                  DEFVALUE: 0
             UNITS:    NA                  SPARSE:   NA
             DESCR:    NA "
::= {xdslLineCurrentIntervalEntry 10}

xdslLineCurrentIntervalMeasuredTime    OBJECT-TYPE
        SYNTAX          INTEGER(0..900)
        ACCESS          read-only
        STATUS          mandatory
        DESCRIPTION     
        "The amount of time, measured in seconds, that statistics for this
         entry have been counted.

         ALCATEL NOTE:
             ACCESS:   NA                  USAGE:    NA
             PERSIST:  NO                  INSRVMOD: NA
             RANGE:    NA                  DEFVALUE: 0
             UNITS:    seconds             SPARSE:   NA
             DESCR:    NA "
::= {xdslLineCurrentIntervalEntry 11}

xdslLineCurrentIntervalInvalidDataFlag OBJECT-TYPE
        SYNTAX          INTEGER
        ACCESS          read-only
        STATUS          mandatory
        DESCRIPTION     
        "This object indicates the validity of the corresponding PM data.
         It is set to 1 when the PM data is incomplete or invalid and set to 0
         when the PM data is complete and valid.

         ALCATEL NOTE:
             ACCESS:   NA                  USAGE:    NA
             PERSIST:  NO                  INSRVMOD: NA
             RANGE:    0..1                DEFVALUE: 1
             UNITS:    NA                  SPARSE:   NA
             DESCR:    NA "
::= {xdslLineCurrentIntervalEntry 12}

xdslLineCurrentIntervalRAUCounter      OBJECT-TYPE
        SYNTAX          Counter
        ACCESS          read-only
        STATUS          mandatory
        DESCRIPTION     
        "This object represents for the current 15 minute interval the RAU 
         anomaly count, which is the number of occurences of an Upshift Rate
         Adaptation.

         ALCATEL NOTE:
             ACCESS:   NA                  USAGE:    NA
             PERSIST:  NO                  INSRVMOD: NA
             RANGE:    NA                  DEFVALUE: 0
             UNITS:    NA                  SPARSE:   NA
             DESCR:    NA "
::= {xdslLineCurrentIntervalEntry 13}

xdslLineCurrentIntervalRADCounter      OBJECT-TYPE
        SYNTAX          Counter
        ACCESS          read-only
        STATUS          mandatory
        DESCRIPTION     
        "This object represents for the current 15 minute interval the RAD 
         anomaly count, which is the number of occurences of a Downshift Rate
         Adaptation.

         ALCATEL NOTE:
             ACCESS:   NA                  USAGE:    NA
             PERSIST:  NO                  INSRVMOD: NA
             RANGE:    NA                  DEFVALUE: 0
             UNITS:    NA                  SPARSE:   NA
             DESCR:    NA "
::= {xdslLineCurrentIntervalEntry 14}

xdslLineCurrentIntervalLEFTRSCounter      OBJECT-TYPE
        SYNTAX          Counter
        ACCESS          read-only
        STATUS          mandatory
        DESCRIPTION     
        "When RTX is in use then this counter associates with the number of
         LEFTR seconds encountered by the line in the current 15 minute interval.
         Otherwise the default value will be returned.

         ALCATEL NOTE:
             ACCESS:   NA                  USAGE:    NA
             PERSIST:  NO                  INSRVMOD: NA
             RANGE:    NA                  DEFVALUE: 0
             UNITS:    NA                  SPARSE:   NA
             DESCR:    NA "
::= {xdslLineCurrentIntervalEntry 15}

xdslLineCurrentIntervalErrFreeBitsCounter      OBJECT-TYPE
        SYNTAX          Counter
        ACCESS          read-only
        STATUS          mandatory
        DESCRIPTION     
        "When RTX is in use then this counter represents for the current 
         15 minute interval the count of the number of error-free bits divided 
         by 2^16.
         Otherwise the default value will be returned.

         ALCATEL NOTE:
             ACCESS:   NA                  USAGE:    NA
             PERSIST:  NO                  INSRVMOD: NA
             RANGE:    NA                  DEFVALUE: 0
             UNITS:    NA                  SPARSE:   NA
             DESCR:    NA "
::= {xdslLineCurrentIntervalEntry 16}

xdslLineCurrentIntervalMinEFTRValue      OBJECT-TYPE
        SYNTAX          INTEGER
        ACCESS          read-only
        STATUS          mandatory
        DESCRIPTION     
        "When RTX is in use then this parameter reports for the current 
         15 minute interval the Minimum EFTR observed during this interval.
         Otherwise the default value will be returned.

         ALCATEL NOTE:
             ACCESS:   NA                  USAGE:    NA
             PERSIST:  NO                  INSRVMOD: NA
             RANGE:    NA                  DEFVALUE: 0
             UNITS:    NA                  SPARSE:   NA
             DESCR:    NA "
::= {xdslLineCurrentIntervalEntry 17}

xdslLineCurrent1DayTable               OBJECT-TYPE
        SYNTAX          SEQUENCE OF XdslLineCurrent1DayEntry
        ACCESS          not-accessible
        STATUS          mandatory
        DESCRIPTION     
        "The xdsl line near end current 1 day table.

         ALCATEL NOTE:
             TABLESIZE: DEP [number of XDSL lines]                    
             DESCR:     NA                   "
::= {xdslLineCurrent 5}
        
xdslLineCurrent1DayEntry               OBJECT-TYPE
        SYNTAX          XdslLineCurrent1DayEntry                        
        ACCESS          not-accessible
        STATUS          mandatory
        DESCRIPTION     
        "An entry in the xdsl line near end current 1 day table.

         Row creation : Entries for all XDSL lines belonging to a board are 
                        created when the board becomes operational.
         Row deletion : Entries for all XDSL lines belonging to a board are 
                        deleted when the board becomes unavailable. "
        INDEX          {ifIndex}
::= {xdslLineCurrent1DayTable 1}

XdslLineCurrent1DayEntry ::=
        SEQUENCE {
            xdslLineCurrent1DayLOSCounter             Counter,
            xdslLineCurrent1DayLOFCounter             Counter,
            xdslLineCurrent1DayLOMCounter             Counter,
            xdslLineCurrent1DayLPRCounter             Counter,
            xdslLineCurrent1DayESECounter             Counter,
            xdslLineCurrent1DayESCounter              Counter,
            xdslLineCurrent1DaySESCounter             Counter,
            xdslLineCurrent1DayUASCounter             Counter,
            xdslLineCurrent1DayReInitCounter          Counter,
            xdslLineCurrent1DayFailedInitCounter      Counter,
            xdslLineCurrent1DayMeasuredTime           INTEGER,
            xdslLineCurrent1DayInvalidDataFlag        INTEGER,
            xdslLineCurrent1DayRAUCounter             Counter,
            xdslLineCurrent1DayRADCounter             Counter,
            xdslLineCurrent1DayLEFTRSCounter          Counter,
            xdslLineCurrent1DayErrFreeBitsCounter     Counter,
            xdslLineCurrent1DayMinEFTRValue           INTEGER
        }

xdslLineCurrent1DayLOSCounter          OBJECT-TYPE
        SYNTAX          Counter
        ACCESS          read-only
        STATUS          mandatory
        DESCRIPTION     
        "This object represents for the current 1 day interval the LOS failure 
         count, which is the number of occurences of an LOS failure event,
         where a failure event occurs when the failure is declared and ends
         when the failure clears.

         ALCATEL NOTE:
             ACCESS:   NA                  USAGE:    NA
             PERSIST:  NO                  INSRVMOD: NA
             RANGE:    NA                  DEFVALUE: 0
             UNITS:    NA                  SPARSE:   NA
             DESCR:    NA "
::= {xdslLineCurrent1DayEntry 1}

xdslLineCurrent1DayLOFCounter          OBJECT-TYPE
        SYNTAX          Counter
        ACCESS          read-only
        STATUS          mandatory
        DESCRIPTION     
        "This object represents for the current 1 day interval 
         the LOF failure count, which is the number of occurences of an LOF 
         failure event, where a failure event occurs when the failure is 
         declared and ends when the failure clears.

         ALCATEL NOTE:
             ACCESS:   NA                  USAGE:    NA
             PERSIST:  NO                  INSRVMOD: NA
             RANGE:    NA                  DEFVALUE: 0
             UNITS:    NA                  SPARSE:   NA
             DESCR:    NA "
::= {xdslLineCurrent1DayEntry 2}

xdslLineCurrent1DayLOMCounter          OBJECT-TYPE
        SYNTAX          Counter
        ACCESS          read-only
        STATUS          mandatory
        DESCRIPTION     
        "This object represents for the current 1 day interval 
         the LOM failure count, which is the number of occurences of a LOM
         failure event, where a failure event occurs when the failure is 
         declared and ends when the failure clears.

         ALCATEL NOTE:
             ACCESS:   NA                  USAGE:    NA
             PERSIST:  NO                  INSRVMOD: NA
             RANGE:    NA                  DEFVALUE: 0
             UNITS:    NA                  SPARSE:   NA
             DESCR:    NA "
::= {xdslLineCurrent1DayEntry 3}

xdslLineCurrent1DayLPRCounter   OBJECT-TYPE
        SYNTAX          Counter
        ACCESS          read-only
        STATUS          mandatory
        DESCRIPTION     
        "This object represents for the current 1 day interval the LPR failure
         count, which is the number of occurences of an LPR failure event,
         where a failure event occurs when the failure is declared and ends
         when the failure clears.
         ALCATEL NOTE:
             ACCESS:   NA                  USAGE:    NA
             PERSIST:  NA                  INSRVMOD: NA
             RANGE:    NA                  DEFVALUE: NA
             UNITS:    NA                  SPARSE:   NA
             DESCR:    This object is not supported. "
::= {xdslLineCurrent1DayEntry 4}

xdslLineCurrent1DayESECounter          OBJECT-TYPE
        SYNTAX          Counter
        ACCESS          read-only
        STATUS          mandatory
        DESCRIPTION     
        "This object represents for the current 1 day interval the ESE 
         failure count, which is the number of occurences of an ESE failure 
         event, where a failure event occurs when the failure is declared and 
         ends when the failure clears.

         ALCATEL NOTE:
             ACCESS:   NA                  USAGE:    NA
             PERSIST:  NO                  INSRVMOD: NA
             RANGE:    NA                  DEFVALUE: 0
             UNITS:    NA                  SPARSE:   NA
             DESCR:    NA "
::= {xdslLineCurrent1DayEntry 5}

xdslLineCurrent1DayESCounter           OBJECT-TYPE
        SYNTAX          Counter
        ACCESS          read-only
        STATUS          mandatory
        DESCRIPTION     
        "The counter associated with the number of Errored Seconds encountered 
         by the line in the current 1 day interval.

         ALCATEL NOTE:
             ACCESS:   NA                  USAGE:    NA
             PERSIST:  NO                  INSRVMOD: NA
             RANGE:    NA                  DEFVALUE: 0
             UNITS:    NA                  SPARSE:   NA
             DESCR:    NA "
::= {xdslLineCurrent1DayEntry 6}

xdslLineCurrent1DaySESCounter          OBJECT-TYPE
        SYNTAX          Counter
        ACCESS          read-only
        STATUS          mandatory
        DESCRIPTION     
        "The counter associated with the number of Severely Errored Seconds
         encountered by the line in the current 1 day interval.

         ALCATEL NOTE:
             ACCESS:   NA                  USAGE:    NA
             PERSIST:  NO                  INSRVMOD: NA
             RANGE:    NA                  DEFVALUE: 0
             UNITS:    NA                  SPARSE:   NA
             DESCR:    NA "
::= {xdslLineCurrent1DayEntry 7}

xdslLineCurrent1DayUASCounter          OBJECT-TYPE
        SYNTAX          Counter
        ACCESS          read-only
        STATUS          mandatory
        DESCRIPTION     
        "The counter associated with the number of Unavailable Seconds
         encountered by the line in the current 1 Day interval.

         ALCATEL NOTE:
             ACCESS:   NA                  USAGE:    NA
             PERSIST:  NO                  INSRVMOD: NA
             RANGE:    NA                  DEFVALUE: 0
             UNITS:    NA                  SPARSE:   NA
             DESCR:    NA "
::= {xdslLineCurrent1DayEntry 8}

xdslLineCurrent1DayReInitCounter       OBJECT-TYPE
        SYNTAX          Counter
        ACCESS          read-only
        STATUS          mandatory
        DESCRIPTION     
        "This object represents for the current 1 day interval the number of
         times the modem left showtime and tried to re-initialize the line
         because of detection of a persistent defect.

         ALCATEL NOTE:
             ACCESS:   NA                  USAGE:    NA
             PERSIST:  NO                  INSRVMOD: NA
             RANGE:    NA                  DEFVALUE: 0
             UNITS:    NA                  SPARSE:   NA
             DESCR:    NA "
::= {xdslLineCurrent1DayEntry 9}

xdslLineCurrent1DayFailedInitCounter   OBJECT-TYPE
        SYNTAX          Counter
        ACCESS          read-only
        STATUS          mandatory
        DESCRIPTION     
        "This object represents for the current 1 day interval the number of
         times the modem tries to initialize the line but fails.

         ALCATEL NOTE:
             ACCESS:   NA                  USAGE:    NA
             PERSIST:  NO                  INSRVMOD: NA
             RANGE:    NA                  DEFVALUE: 0
             UNITS:    NA                  SPARSE:   NA
             DESCR:    NA "
::= {xdslLineCurrent1DayEntry 10}

xdslLineCurrent1DayMeasuredTime        OBJECT-TYPE
        SYNTAX          INTEGER(0..86400)
        ACCESS          read-only
        STATUS          mandatory
        DESCRIPTION     
        "The amount of time, measured in seconds, that statistics for this 
         entry have been counted.

         ALCATEL NOTE:
             ACCESS:   NA                  USAGE:    NA
             PERSIST:  NO                  INSRVMOD: NA
             RANGE:    NA                  DEFVALUE: 0
             UNITS:    seconds             SPARSE:   NA
             DESCR:    NA "
::= {xdslLineCurrent1DayEntry 11}

xdslLineCurrent1DayInvalidDataFlag     OBJECT-TYPE
        SYNTAX          INTEGER
        ACCESS          read-only
        STATUS          mandatory
        DESCRIPTION     
        "This object indicates the validity of the corresponding PM data.
         It is set to 1 when the PM data is incomplete or invalid and set to 0
         when the PM data is complete and valid.

         ALCATEL NOTE:
             ACCESS:   NA                  USAGE:    NA
             PERSIST:  NO                  INSRVMOD: NA
             RANGE:    0..1                DEFVALUE: 1
             UNITS:    NA                  SPARSE:   NA
             DESCR:    NA "
::= {xdslLineCurrent1DayEntry 12}

xdslLineCurrent1DayRAUCounter          OBJECT-TYPE
        SYNTAX          Counter
        ACCESS          read-only
        STATUS          mandatory
        DESCRIPTION     
        "This object represents for the current 1 day interval the RAU anomaly 
         count, which is the number of occurences of an Upshift Rate 
         Adaptation.

         ALCATEL NOTE:
             ACCESS:   NA                  USAGE:    NA
             PERSIST:  NO                  INSRVMOD: NA
             RANGE:    NA                  DEFVALUE: 0
             UNITS:    NA                  SPARSE:   NA
             DESCR:    NA "
::= {xdslLineCurrent1DayEntry 13}

xdslLineCurrent1DayRADCounter          OBJECT-TYPE
        SYNTAX          Counter
        ACCESS          read-only
        STATUS          mandatory
        DESCRIPTION     
        "This object represents for the current 1 day interval the RAD anomaly 
         count, which is the number of occurences of a Downshift Rate 
         Adaptation.

         ALCATEL NOTE:
             ACCESS:   NA                  USAGE:    NA
             PERSIST:  NO                  INSRVMOD: NA
             RANGE:    NA                  DEFVALUE: 0
             UNITS:    NA                  SPARSE:   NA
             DESCR:    NA "
::= {xdslLineCurrent1DayEntry 14}

xdslLineCurrent1DayLEFTRSCounter      OBJECT-TYPE
        SYNTAX          Counter
        ACCESS          read-only
        STATUS          mandatory
        DESCRIPTION     
        "When RTX is in use then this counter associates with the number of
         LEFTR seconds encountered by the line in the current 1 day interval.
         Otherwise the default value will be returned.

         ALCATEL NOTE:
             ACCESS:   NA                  USAGE:    NA
             PERSIST:  NO                  INSRVMOD: NA
             RANGE:    NA                  DEFVALUE: 0
             UNITS:    NA                  SPARSE:   NA
             DESCR:    NA "
::= { xdslLineCurrent1DayEntry 15}

xdslLineCurrent1DayErrFreeBitsCounter      OBJECT-TYPE
        SYNTAX          Counter
        ACCESS          read-only
        STATUS          mandatory
        DESCRIPTION     
        "When RTX is in use then this counter represents for the current 
         1 day interval the count of the number of error-free bits divided 
         by 2^16.
         Otherwise the default value will be returned.

         ALCATEL NOTE:
             ACCESS:   NA                  USAGE:    NA
             PERSIST:  NO                  INSRVMOD: NA
             RANGE:    NA                  DEFVALUE: 0
             UNITS:    NA                  SPARSE:   NA
             DESCR:    NA "
::= { xdslLineCurrent1DayEntry 16}

xdslLineCurrent1DayMinEFTRValue      OBJECT-TYPE
        SYNTAX          INTEGER
        ACCESS          read-only
        STATUS          mandatory
        DESCRIPTION     
        " When RTX is in use then this counter represents for the current 
         1 day interval the count of the Minimum of the EFTR observed
         during this interval.
         Otherwise the default value will be returned.

         ALCATEL NOTE:
             ACCESS:   NA                  USAGE:    NA
             PERSIST:  NO                  INSRVMOD: NA
             RANGE:    NA                  DEFVALUE: 0
             UNITS:    NA                  SPARSE:   NA
             DESCR:    NA "
::= { xdslLineCurrent1DayEntry 17}

xdslLineInsOperDataTable       OBJECT-TYPE
        SYNTAX          SEQUENCE OF XdslLineInsOperDataEntry
        ACCESS          not-accessible
        STATUS          mandatory
        DESCRIPTION     
        " The xdsl line impulse noise sensor operational data table.

         ALCATEL NOTE:
             TABLESIZE: DEP [number of XDSL lines]                    
             DESCR:     NA                   "
::= {xdslLineCurrent 6}

xdslLineInsOperDataEntry       OBJECT-TYPE
        SYNTAX          XdslLineInsOperDataEntry
        ACCESS          not-accessible
        STATUS          mandatory
        DESCRIPTION     
        " An entry in the xdsl line impulse noise sensor operational data table
        
         Row creation : Entries for all XDSL lines belonging to a board are 
                        created by the system when the board is planned.
         Row deletion : Entries for all XDSL lines belonging to a board are 
                        deleted by the system when the board is unplanned. "
        INDEX          {ifIndex}
::= {xdslLineInsOperDataTable 1}

XdslLineInsOperDataEntry ::=
        SEQUENCE {
            xdslLineInsActualSensitivity                  INTEGER,
            xdslLineInmActualEquivInpMode                 INTEGER
        }
        
xdslLineInsActualSensitivity              OBJECT-TYPE
        SYNTAX          INTEGER
        ACCESS          read-only
        STATUS          mandatory
        DESCRIPTION     
        "This object represents the Impulse Noise Sensor sensitivity actually
         applied by the modem. The value can be different from the configured
         Impulse Noise Sensitivity depending on the current noise conditions on
         the line and modem capability.
         Range: -12.8 dB to 12.7 dB with 0.1 dB steps.
         The Actual Sensitivity is represented as
         1/10 * xdslLineInsActualSensitivity.

         ALCATEL NOTE:
             ACCESS:   NA                  USAGE:    NA
             PERSIST:  NO                  INSRVMOD: NA
             RANGE:    -128 .. 127         DEFVALUE: 0
             UNITS:    dB / 10             SPARSE:   NA
             DESCR:    NA "
::= {xdslLineInsOperDataEntry 1}

xdslLineInmActualEquivInpMode                   OBJECT-TYPE
        SYNTAX          INTEGER
        ACCESS          read-only
        STATUS          mandatory
        DESCRIPTION     
        "This object represents the actual Impulse Noise Monitoring Equivalent
         INP Mode applied by the modem. The value will be different from the
         configured INM Equivalent INP Mode if the modem is using a fallback
         mode because the configured mode is not supported, or if INM is not
         supported.
         Range: 0 to 3 plus special value 255.
         Special value 255 indicates that INM is not supported.

         ALCATEL NOTE:
             ACCESS:   NA                  USAGE:    NA
             PERSIST:  NO                  INSRVMOD: NA
             RANGE:    0..3, 255           DEFVALUE: 0
             UNITS:    NA                  SPARSE:   NA
             DESCR:    NA "
::= {xdslLineInsOperDataEntry 2}

xdslLineInmCurrentIntervalTable       OBJECT-TYPE
        SYNTAX          SEQUENCE OF XdslLineInmCurrentIntervalEntry
        ACCESS          not-accessible
        STATUS          mandatory
        DESCRIPTION     
        " The xdsl line Impulse noise Monitoring near end current 15 minute
         interval table.

         ALCATEL NOTE:
             TABLESIZE: DEP [number of XDSL lines]                    
             DESCR:     NA                   "
::= {xdslLineCurrent 7}

xdslLineInmCurrentIntervalEntry       OBJECT-TYPE
        SYNTAX          XdslLineInmCurrentIntervalEntry
        ACCESS          not-accessible
        STATUS          mandatory
        DESCRIPTION     
        "An entry in the xdsl line Impulse Noise Monitoring current 15 minute
         interval table.

         Row creation : Entries for all XDSL lines belonging to a board are 
                        created by the system when the board is planned.
         Row deletion : Entries for all XDSL lines belonging to a board are 
                        deleted by the system when the board is unplanned. "
        INDEX          {ifIndex}
::= {xdslLineInmCurrentIntervalTable 1}

XdslLineInmCurrentIntervalEntry ::=
        SEQUENCE {
            xdslLineInmCurrentIntervalIatHistogram            IatHistogramType,
            xdslLineInmCurrentIntervalEquivInpHistogram       EquivInpHistogramType,
            xdslLineInmCurrentIntervalTotalDataSymbolCounter  Counter
        }
        
xdslLineInmCurrentIntervalIatHistogram              OBJECT-TYPE
        SYNTAX          IatHistogramType
        ACCESS          read-only
        STATUS          mandatory
        DESCRIPTION     
        "This object represents the Impulse Noise Monitoring Inter-Arrival Time
         histogram for the current 15 minute interval. The histogram consists
         of eight saturating counters representing the different class
         intervals configured.
         The Inter-Arrival Time is defined as the time between the start of two
         consecutive impulses, expressed as an number of data symbols.
         The class intervals width and offset are defined by
         xdslLineInmInterArrivalTimeStep and xdslLineInmInterArrivalTimeOffset.
         The Inter-Arrival Time histogram is coded as a fixed length
         octet string defined as follows:
         OCTETS 0..1: INTEGER (0..65535), value of the first class interval.
         The value is defined as MSB-LSB (big-endian).
         OCTETS 2..3: define the value of class interval 2.
         ....        up to
         OCTETS 14..15: define the last class interval 8.

         ALCATEL NOTE:
             ACCESS:   NA                  USAGE:    NA
             PERSIST:  NO                  INSRVMOD: NA
             RANGE:    NA                  DEFVALUE: '00000000000000000000000000000000'H
             UNITS:    octets              SPARSE:   NA
             DESCR:    NA "
::= {xdslLineInmCurrentIntervalEntry 1}

xdslLineInmCurrentIntervalEquivInpHistogram              OBJECT-TYPE
        SYNTAX          EquivInpHistogramType
        ACCESS          read-only
        STATUS          mandatory
        DESCRIPTION     
        "This object represents the Impulse Noise Monitoring Equivalent INP
         histogram for the current 15 minute interval. The histogram consists
         of seventeen saturating counters representing the different class
         intervals.
         Class intervals 1 to 16 contain the number of impulse noise events
         detected per equivalent level of INP as defined by
         xdslLineEquivInpMode. Class interval 17 contains the number of impulse
         noise events detected with equivalent level of INP greater than 16.
         The equivalent INP histogram is coded as a fixed length
         octet string defined as follows:
         OCTETS 0..1: INTEGER (0..65535), value of the first class interval.
         The value is defined as MSB-LSB (big-endian).
         OCTETS 2..3: define the value of class interval 2.
         ....        up to
         OCTETS 32..33: define the last class interval 17.

         ALCATEL NOTE:
             ACCESS:   NA                  USAGE:    NA
             PERSIST:  NO                  INSRVMOD: NA
             RANGE:    NA                  DEFVALUE: '00000000000000000000000000000000000000000000000000000000000000000000'H
             UNITS:    octets              SPARSE:   NA
             DESCR:    NA "
::= {xdslLineInmCurrentIntervalEntry 2}

xdslLineInmCurrentIntervalTotalDataSymbolCounter   OBJECT-TYPE
        SYNTAX          Counter
        ACCESS          read-only
        STATUS          mandatory
        DESCRIPTION     
        " This object represents the total number of data symbols that have
         been monitored to construct the Impulse Noise Monitoring histograms of
         Impulse Length and Inter-Arrival Time for the current 15 minute
         interval.

         ALCATEL NOTE:
             ACCESS:   NA                  USAGE:    NA
             PERSIST:  NO                  INSRVMOD: NA
             RANGE:    NA                  DEFVALUE: 0
             UNITS:    NA                  SPARSE:   NA
             DESCR:    NA "
::= {xdslLineInmCurrentIntervalEntry 3}

xdslLineInmCurrent1DayTable       OBJECT-TYPE
        SYNTAX          SEQUENCE OF XdslLineInmCurrent1DayEntry
        ACCESS          not-accessible
        STATUS          mandatory
        DESCRIPTION     
        " The xdsl line Impulse noise Monitoring near end current 1 day interval
         table.

         ALCATEL NOTE:
             TABLESIZE: DEP [number of XDSL lines]                    
             DESCR:     NA                   "
::= {xdslLineCurrent 8}

xdslLineInmCurrent1DayEntry       OBJECT-TYPE
        SYNTAX          XdslLineInmCurrent1DayEntry
        ACCESS          not-accessible
        STATUS          mandatory
        DESCRIPTION     
        " An entry in the xdsl line Impulse Noise Monitoring current 1 day
         interval table.

         Row creation : Entries for all XDSL lines belonging to a board are 
                        created by the system when the board is planned.
         Row deletion : Entries for all XDSL lines belonging to a board are 
                        deleted by the system when the board is unplanned. "
        INDEX          {ifIndex}
::= {xdslLineInmCurrent1DayTable 1}

XdslLineInmCurrent1DayEntry ::=
        SEQUENCE {
            xdslLineInmCurrent1DayIatHistogram            IatHistogramType,
            xdslLineInmCurrent1DayEquivInpHistogram       EquivInpHistogramType,
            xdslLineInmCurrent1DayTotalDataSymbolCounter  Counter
        }
        
xdslLineInmCurrent1DayIatHistogram              OBJECT-TYPE
        SYNTAX          IatHistogramType
        ACCESS          read-only
        STATUS          mandatory
        DESCRIPTION     
        " This object represents the Impulse Noise Monitoring Inter-Arrival Time
         histogram for the current 1 day interval. The histogram consists
         of eight saturating counters representing the different class
         intervals configured.
         The Inter-Arrival Time is defined as the time between the start of two
         consecutive impulses, expressed as an number of data symbols.
         The class intervals width and offset are defined by
         xdslLineInmInterArrivalTimeStep and xdslLineInmInterArrivalTimeOffset.
         The Inter-Arrival Time histogram is coded as a fixed length
         octet string defined as follows:
         OCTETS 0..1: INTEGER (0..65535), value of the first class interval.
         The value is defined as MSB-LSB (big-endian).
         OCTETS 2..3: define the value of class interval 2.
         ....        up to
         OCTETS 14..15: define the last class interval 8.

         ALCATEL NOTE:
             ACCESS:   NA                  USAGE:    NA
             PERSIST:  NO                  INSRVMOD: NA
             RANGE:    NA                  DEFVALUE: '00000000000000000000000000000000'H
             UNITS:    octets              SPARSE:   NA
             DESCR:    NA "
::= {xdslLineInmCurrent1DayEntry 1}

xdslLineInmCurrent1DayEquivInpHistogram              OBJECT-TYPE
        SYNTAX          EquivInpHistogramType
        ACCESS          read-only
        STATUS          mandatory
        DESCRIPTION     
        "This object represents the Impulse Noise Monitoring Equivalent INP
         histogram for the current 1 day interval. The histogram consists
         of seventeen saturating counters representing the different class
         intervals.
         Class intervals 1 to 16 contain the number of impulse noise events
         detected per equivalent level of INP as defined by
         xdslLineEquivInpMode. Class interval 17 contains the number of impulse
         noise events detected with equivalent level of INP greater than 16.
         The equivalent INP histogram is coded as a fixed length
         octet string defined as follows:
         OCTETS 0..1: INTEGER (0..65535), value of the first class interval.
         The value is defined as MSB-LSB (big-endian).
         OCTETS 2..3: define the value of class interval 2.
         ....        up to
         OCTETS 32..33: define the last class interval 17.

         ALCATEL NOTE:
             ACCESS:   NA                  USAGE:    NA
             PERSIST:  NO                  INSRVMOD: NA
             RANGE:    NA                  DEFVALUE: '00000000000000000000000000000000000000000000000000000000000000000000'H
             UNITS:    octets              SPARSE:   NA
             DESCR:    NA "
::= {xdslLineInmCurrent1DayEntry 2}

xdslLineInmCurrent1DayTotalDataSymbolCounter   OBJECT-TYPE
        SYNTAX          Counter
        ACCESS          read-only
        STATUS          mandatory
        DESCRIPTION     
        " This object represents the total number of data symbols that have
         been monitored to construct the Impulse Noise Monitoring histograms of
         Impulse Length and Inter-Arrival Time for the current 1 day interval.

         ALCATEL NOTE:
             ACCESS:   NA                  USAGE:    NA
             PERSIST:  NO                  INSRVMOD: NA
             RANGE:    NA                  DEFVALUE: 0
             UNITS:    NA                  SPARSE:   NA
             DESCR:    NA "
::= {xdslLineInmCurrent1DayEntry 3}

xdslLineEventTraceTable       OBJECT-TYPE
        SYNTAX          SEQUENCE OF XdslLineEventTraceEntry
        ACCESS          not-accessible
        STATUS          mandatory
        DESCRIPTION     
        " The xdsl line event trace table.

         ALCATEL NOTE:
             TABLESIZE: DEP [number of XDSL lines]                    
             DESCR:     NA                   "
::= {xdslLineCurrent 9}

xdslLineEventTraceEntry       OBJECT-TYPE
        SYNTAX          XdslLineEventTraceEntry
        ACCESS          not-accessible
        STATUS          mandatory
        DESCRIPTION     
        " An entry in the xdsl line event trace table.

         Row creation : Entries for all XDSL lines belonging to a board are 
                        created by the system when the board is planned.
         Row deletion : Entries for all XDSL lines belonging to a board are 
                        deleted by the system when the board is unplanned. "
        INDEX          {ifIndex}
::= {xdslLineEventTraceTable 1}

XdslLineEventTraceEntry ::=
        SEQUENCE {
            xdslLineEventTrace                  EventTraceType
        }
        
xdslLineEventTrace              OBJECT-TYPE
        SYNTAX          EventTraceType
        ACCESS          read-only
        STATUS          mandatory
        DESCRIPTION     
        "This object represent a logging of the events that occurred on the 
         line.
         It is coded as a variable length octet string of up to 25 records,
         with 6 octets per record. 
         Encoding per record: 
          OCTETS 0..3: INTEGER (0..4294967295), representing the timestamp 
           (NetworkTimeInSeconds). The value is defined as MSB-LSB (big-endian)
          OCTET 4: INTEGER(0..255), representing the event type 
          OCTET 5: INTEGER(0..255), representing the event data
         This event trace is intended to be only used by the Alcatel-Lucent
         NA5530 Network Analyzer.

         ALCATEL NOTE:
             ACCESS:   NA                  USAGE:    NA
             PERSIST:  NO                  INSRVMOD: NA
             RANGE:    0..150              DEFVALUE: ''H
             UNITS:    octets              SPARSE:   NA
             DESCR:    NA "
::= {xdslLineEventTraceEntry 1}

xdslLinePreviousIntervalTable          OBJECT-TYPE
        SYNTAX          SEQUENCE OF XdslLinePreviousIntervalEntry
        ACCESS          not-accessible
        STATUS          mandatory
        DESCRIPTION     
        "The xdsl line near end previous interval table.

         ALCATEL NOTE:
             TABLESIZE: DEP [number of XDSL lines * 192]                    
             DESCR:     NA                   "
::= {xdslLinePrevious 1}
        
xdslLinePreviousIntervalEntry          OBJECT-TYPE
        SYNTAX          XdslLinePreviousIntervalEntry                   
        ACCESS          not-accessible
        STATUS          mandatory
        DESCRIPTION     
        "An entry in the xdsl line near end previous interval table.

         Row creation : Entries for all XDSL lines belonging to a board are 
                        created when the board becomes operational.
         Row deletion : Entries for all XDSL lines belonging to a board are 
                        deleted when the board becomes unavailable. "
        INDEX          {ifIndex, 
                        xdslLinePreviousIntervalNumber}
::= {xdslLinePreviousIntervalTable 1}

XdslLinePreviousIntervalEntry ::=
        SEQUENCE {
            xdslLinePreviousIntervalNumber            INTEGER,
            xdslLinePreviousIntervalLOSCounter        Counter,
            xdslLinePreviousIntervalLOFCounter        Counter,
            xdslLinePreviousIntervalLOMCounter        Counter,
            xdslLinePreviousIntervalLPRCounter        Counter,
            xdslLinePreviousIntervalESECounter        Counter,
            xdslLinePreviousIntervalESCounter         Counter,
            xdslLinePreviousIntervalSESCounter        Counter,
            xdslLinePreviousIntervalUASCounter        Counter,
            xdslLinePreviousIntervalReInitCounter     Counter,
            xdslLinePreviousIntervalFailedInitCounter Counter,
            xdslLinePreviousIntervalMeasuredTime      INTEGER,
            xdslLinePreviousIntervalInvalidDataFlag   INTEGER,
            xdslLinePreviousIntervalRAUCounter        Counter,
            xdslLinePreviousIntervalRADCounter        Counter,
            xdslLinePreviousIntervalLEFTRSCounter     Counter,
            xdslLinePreviousIntervalErrFreeBitsCounter Counter,
            xdslLinePreviousIntervalMinEFTRValue       INTEGER
        }
        
xdslLinePreviousIntervalNumber         OBJECT-TYPE
        SYNTAX          INTEGER(1..192)
        ACCESS          read-only
        STATUS          mandatory
        DESCRIPTION     
        "A number between 1 and 192, which identifies the interval for which 
         the set of statistics is available. The interval identified by 1 is 
         the most recently completed 15 minute interval, and the interval
         identified by N is the interval immediately preceding the one
         identified by N-1.

         ALCATEL NOTE:
             ACCESS:   NA                  USAGE:    NA
             PERSIST:  NO                  INSRVMOD: NA
             RANGE:    NA                  DEFVALUE: NA
             UNITS:    NA                  SPARSE:   NA
             DESCR:    NA "
::= {xdslLinePreviousIntervalEntry 1}

xdslLinePreviousIntervalLOSCounter     OBJECT-TYPE
        SYNTAX          Counter
        ACCESS          read-only
        STATUS          mandatory
        DESCRIPTION     
        "This object represents for a particular 15 minute interval the LOS 
         failure count, which is the number of occurences of an LOS failure 
         event, where a failure event occurs when the failure is declared and 
         ends when the failure clears.

         ALCATEL NOTE:
             ACCESS:   NA                  USAGE:    NA
             PERSIST:  NO                  INSRVMOD: NA
             RANGE:    NA                  DEFVALUE: 0
             UNITS:    NA                  SPARSE:   NA
             DESCR:    NA "
::= {xdslLinePreviousIntervalEntry 2}

xdslLinePreviousIntervalLOFCounter     OBJECT-TYPE
        SYNTAX          Counter
        ACCESS          read-only
        STATUS          mandatory
        DESCRIPTION     
        "This object represents for a particular 15 minute interval the LOF 
         failure count, which is the number of occurences of an LOF failure 
         event, where a failure event occurs when the failure is declared and 
         ends when the failure clears.

         ALCATEL NOTE:
             ACCESS:   NA                  USAGE:    NA
             PERSIST:  NO                  INSRVMOD: NA
             RANGE:    NA                  DEFVALUE: 0
             UNITS:    NA                  SPARSE:   NA
             DESCR:    NA "
::= {xdslLinePreviousIntervalEntry 3}

xdslLinePreviousIntervalLOMCounter     OBJECT-TYPE
        SYNTAX          Counter
        ACCESS          read-only
        STATUS          mandatory
        DESCRIPTION     
        "This object represents for a particular 15 minute interval the LOM 
         failure count, which is the number of occurences of a LOM failure 
         event, where a failure event occurs when the failure is declared and 
         ends when the failure clears.

         ALCATEL NOTE:
             ACCESS:   NA                  USAGE:    NA
             PERSIST:  NO                  INSRVMOD: NA
             RANGE:    NA                  DEFVALUE: 0
             UNITS:    NA                  SPARSE:   NA
             DESCR:    NA "
::= {xdslLinePreviousIntervalEntry 4}

xdslLinePreviousIntervalLPRCounter      OBJECT-TYPE
        SYNTAX          Counter
        ACCESS          read-only
        STATUS          mandatory
        DESCRIPTION
        "This object represents for a particular 15 minute interval the LPR 
         failure count, which is the number of occurences of an LPR failure 
         event, where a failure event occurs when the failure is declared and 
         ends when the failure clears.
         ALCATEL NOTE:
             ACCESS:   NA                  USAGE:    NA
             PERSIST:  NA                  INSRVMOD: NA
             RANGE:    NA                  DEFVALUE: NA
             UNITS:    NA                  SPARSE:   NA
             DESCR:    This object is not supported. "
::= {xdslLinePreviousIntervalEntry 5}

xdslLinePreviousIntervalESECounter     OBJECT-TYPE
        SYNTAX          Counter
        ACCESS          read-only
        STATUS          mandatory
        DESCRIPTION     
        "This object represents for a particular 15 minute interval the ESE 
         failure count, which is the number of occurences of an ESE failure 
         event, where a failure event occurs when the failure is declared and 
         ends when the failure clears.

         ALCATEL NOTE:
             ACCESS:   NA                  USAGE:    NA
             PERSIST:  NO                  INSRVMOD: NA
             RANGE:    NA                  DEFVALUE: 0
             UNITS:    NA                  SPARSE:   NA
             DESCR:    NA "
   ::= {xdslLinePreviousIntervalEntry 6}

xdslLinePreviousIntervalESCounter      OBJECT-TYPE
        SYNTAX          Counter
        ACCESS          read-only
        STATUS          mandatory
        DESCRIPTION  
        "The counter associated with the number of Errored Seconds encountered 
         by the line in a particular 15 minute interval.

         ALCATEL NOTE:
             ACCESS:   NA                  USAGE:    NA
             PERSIST:  NO                  INSRVMOD: NA
             RANGE:    NA                  DEFVALUE: 0
             UNITS:    NA                  SPARSE:   NA
             DESCR:    NA "
   ::= {xdslLinePreviousIntervalEntry 7}

xdslLinePreviousIntervalSESCounter     OBJECT-TYPE
        SYNTAX          Counter
        ACCESS          read-only
        STATUS          mandatory
        DESCRIPTION  
        "The counter associated with the number of Severely Errored Seconds
         encountered by the line in a particular 15 minute interval.

         ALCATEL NOTE:
             ACCESS:   NA                  USAGE:    NA
             PERSIST:  NO                  INSRVMOD: NA
             RANGE:    NA                  DEFVALUE: 0
             UNITS:    NA                  SPARSE:   NA
             DESCR:    NA "
   ::= {xdslLinePreviousIntervalEntry 8}

xdslLinePreviousIntervalUASCounter     OBJECT-TYPE
        SYNTAX          Counter
        ACCESS          read-only
        STATUS          mandatory
        DESCRIPTION  
        "The counter associated with the number of Unavailable Seconds
         encountered by the line in a particular 15 minute interval.

         ALCATEL NOTE:
             ACCESS:   NA                  USAGE:    NA
             PERSIST:  NO                  INSRVMOD: NA
             RANGE:    NA                  DEFVALUE: 0
             UNITS:    NA                  SPARSE:   NA
             DESCR:    NA "
   ::= {xdslLinePreviousIntervalEntry 9}

xdslLinePreviousIntervalReInitCounter  OBJECT-TYPE
        SYNTAX          Counter
        ACCESS          read-only
        STATUS          mandatory
        DESCRIPTION     
        "This object represents for a particular 15 minute interval the number
         of times the modem left showtime and tried to re-initialize the line
         because of detection of a persistent defect.

         ALCATEL NOTE:
             ACCESS:   NA                  USAGE:    NA
             PERSIST:  NO                  INSRVMOD: NA
             RANGE:    NA                  DEFVALUE: 0
             UNITS:    NA                  SPARSE:   NA
             DESCR:    NA "
::= {xdslLinePreviousIntervalEntry 10}

xdslLinePreviousIntervalFailedInitCounter        OBJECT-TYPE
        SYNTAX          Counter
        ACCESS          read-only
        STATUS          mandatory
        DESCRIPTION     
        "This object represents for a particular 15 minute interval the number
         of times the modem tries to initialize the line but fails.

         ALCATEL NOTE:
             ACCESS:   NA                  USAGE:    NA
             PERSIST:  NO                  INSRVMOD: NA
             RANGE:    NA                  DEFVALUE: 0
             UNITS:    NA                  SPARSE:   NA
             DESCR:    NA "
::= {xdslLinePreviousIntervalEntry 11}

xdslLinePreviousIntervalMeasuredTime   OBJECT-TYPE
        SYNTAX          INTEGER(0..900)
        ACCESS          read-only
        STATUS          mandatory
        DESCRIPTION     
        "The amount of time, measured in seconds, that statistics for this
         entry have been counted.

         ALCATEL NOTE:
             ACCESS:   NA                  USAGE:    NA
             PERSIST:  NO                  INSRVMOD: NA
             RANGE:    NA                  DEFVALUE: 0
             UNITS:    seconds             SPARSE:   NA
             DESCR:    NA "
::= {xdslLinePreviousIntervalEntry 12}

xdslLinePreviousIntervalInvalidDataFlag          OBJECT-TYPE
        SYNTAX          INTEGER
        ACCESS          read-only
        STATUS          mandatory
        DESCRIPTION     
        "This object indicates the validity of the corresponding PM data.
         It is set to 1 when the PM data is incomplete or invalid and set to 0
         when the PM data is complete and valid.

         ALCATEL NOTE:
             ACCESS:   NA                  USAGE:    NA
             PERSIST:  NO                  INSRVMOD: NA
             RANGE:    0..1                DEFVALUE: 1
             UNITS:    NA                  SPARSE:   NA
             DESCR:    NA "
::= {xdslLinePreviousIntervalEntry 13}

xdslLinePreviousIntervalRAUCounter     OBJECT-TYPE
        SYNTAX          Counter
        ACCESS          read-only
        STATUS          mandatory
        DESCRIPTION     
        "This object represents for a particular 15 minute interval the RAU 
         anomaly count, which is the number of occurences of an Upshift Rate
         Adaptation.

         ALCATEL NOTE:
             ACCESS:   NA                  USAGE:    NA
             PERSIST:  NO                  INSRVMOD: NA
             RANGE:    NA                  DEFVALUE: 0
             UNITS:    NA                  SPARSE:   NA
             DESCR:    NA "
::= {xdslLinePreviousIntervalEntry 14}

xdslLinePreviousIntervalRADCounter     OBJECT-TYPE
        SYNTAX          Counter
        ACCESS          read-only
        STATUS          mandatory
        DESCRIPTION     
        "This object represents for a particular 15 minute interval the RAD 
         anomaly count, which is the number of occurences of a Downshift Rate 
         Adaptation.

         ALCATEL NOTE:
             ACCESS:   NA                  USAGE:    NA
             PERSIST:  NO                  INSRVMOD: NA
             RANGE:    NA                  DEFVALUE: 0
             UNITS:    NA                  SPARSE:   NA
             DESCR:    NA "
::= {xdslLinePreviousIntervalEntry 15}

xdslLinePreviousIntervalLEFTRSCounter      OBJECT-TYPE
        SYNTAX          Counter
        ACCESS          read-only
        STATUS          mandatory
        DESCRIPTION     
        "When RTX is in use then this counter associates with the number of
         LEFTR seconds encountered by the line in the previous 15 minute interval.
         Otherwise the default value will be returned.

         ALCATEL NOTE:
             ACCESS:   NA                  USAGE:    NA
             PERSIST:  NO                  INSRVMOD: NA
             RANGE:    NA                  DEFVALUE: 0
             UNITS:    NA                  SPARSE:   NA
             DESCR:    NA "
::= { xdslLinePreviousIntervalEntry 16}

xdslLinePreviousIntervalErrFreeBitsCounter      OBJECT-TYPE
        SYNTAX          Counter
        ACCESS          read-only
        STATUS          mandatory
        DESCRIPTION     
        "When RTX is in use then this counter represents for the previous 
         15 minute interval the count of the number of error-free bits divided 
         by 2^16.
         Otherwise the default value will be returned.

         ALCATEL NOTE:
             ACCESS:   NA                  USAGE:    NA
             PERSIST:  NO                  INSRVMOD: NA
             RANGE:    NA                  DEFVALUE: 0
             UNITS:    NA                  SPARSE:   NA
             DESCR:    NA "
::= { xdslLinePreviousIntervalEntry 17}

xdslLinePreviousIntervalMinEFTRValue      OBJECT-TYPE
        SYNTAX          INTEGER
        ACCESS          read-only
        STATUS          mandatory
        DESCRIPTION     
        "When RTX is in use then this counter represents for the previous 
         15 minute interval the count of the Minimum of the EFTR observed
         during this interval.
         Otherwise the default value will be returned.

         ALCATEL NOTE:
             ACCESS:   NA                  USAGE:    NA
             PERSIST:  NO                  INSRVMOD: NA
             RANGE:    NA                  DEFVALUE: 0
             UNITS:    NA                  SPARSE:   NA
             DESCR:    NA "
::= { xdslLinePreviousIntervalEntry 18}

xdslLinePrevious1DayTable              OBJECT-TYPE
        SYNTAX          SEQUENCE OF XdslLinePrevious1DayEntry
        ACCESS          not-accessible
        STATUS          mandatory
        DESCRIPTION     
        "The xdsl line near end previous 1 day table.

         ALCATEL NOTE:
             TABLESIZE: DEP [number of XDSL lines * number of days (1)]                  
             DESCR:     NA                   "
::= {xdslLinePrevious 2}
        
xdslLinePrevious1DayEntry              OBJECT-TYPE
        SYNTAX          XdslLinePrevious1DayEntry                       
        ACCESS          not-accessible
        STATUS          mandatory
        DESCRIPTION     
        "An entry in the xdsl line near end previous 1 day table.

         Row creation : Entries for all XDSL lines belonging to a board are 
                        created when the board becomes operational.
         Row deletion : Entries for all XDSL lines belonging to a board are 
                        deleted when the board becomes unavailable. "
        INDEX          {ifIndex, 
                        xdslLinePrevious1DayNumber}
::= {xdslLinePrevious1DayTable 1}

XdslLinePrevious1DayEntry ::=
        SEQUENCE {
            xdslLinePrevious1DayNumber                INTEGER,
            xdslLinePrevious1DayLOSCounter            Counter,
            xdslLinePrevious1DayLOFCounter            Counter,
            xdslLinePrevious1DayLOMCounter            Counter,
            xdslLinePrevious1DayLPRCounter            Counter,
            xdslLinePrevious1DayESECounter            Counter,
            xdslLinePrevious1DayESCounter             Counter,
            xdslLinePrevious1DaySESCounter            Counter,
            xdslLinePrevious1DayUASCounter            Counter,
            xdslLinePrevious1DayReInitCounter         Counter,
            xdslLinePrevious1DayFailedInitCounter     Counter,
            xdslLinePrevious1DayMeasuredTime          INTEGER,
            xdslLinePrevious1DayInvalidDataFlag       INTEGER,
            xdslLinePrevious1DayRAUCounter            Counter,
            xdslLinePrevious1DayRADCounter            Counter,
            xdslLinePrevious1DayLEFTRSCounter         Counter,
            xdslLinePrevious1DayErrFreeBitsCounter    Counter,     
            xdslLinePrevious1DayMinEFTRValue          INTEGER
        }

xdslLinePrevious1DayNumber             OBJECT-TYPE
        SYNTAX          INTEGER(1..7)
        ACCESS          read-only
        STATUS          mandatory
        DESCRIPTION     
        "A number between 1 and 7, which identifies the day for which the 
         set of statistics is available. The day identified by 1 is the 
         most recently completed 1Day, and the day identified 
         by N is the day immediately preceding the one identified by N-1.

         ALCATEL NOTE:
             ACCESS:   NA                  USAGE:    NA
             PERSIST:  NO                  INSRVMOD: NA
             RANGE:    1                   DEFVALUE: NA
             UNITS:    NA                  SPARSE:   NA
             DESCR:    Only statistics for one previous day is kept. "
::= {xdslLinePrevious1DayEntry 1}

xdslLinePrevious1DayLOSCounter         OBJECT-TYPE
        SYNTAX          Counter
        ACCESS          read-only
        STATUS          mandatory
        DESCRIPTION     
        "This object represents for the previous 1 day interval the LOS failure 
         count, which is the number of occurences of an LOS failure event,
         where a failure event occurs when the failure is declared and ends
         when the failure clears.

         ALCATEL NOTE:
             ACCESS:   NA                  USAGE:    NA
             PERSIST:  NO                  INSRVMOD: NA
             RANGE:    NA                  DEFVALUE: 0
             UNITS:    NA                  SPARSE:   NA
             DESCR:    NA "
::= {xdslLinePrevious1DayEntry 2}

xdslLinePrevious1DayLOFCounter         OBJECT-TYPE
        SYNTAX          Counter
        ACCESS          read-only
        STATUS          mandatory
        DESCRIPTION     
        "This object represents for the previous 1 day interval the LOF failure 
         count, which is the number of occurences of an LOF failure event, 
         where a failure event occurs when the failure is declared and ends
         when the failure clears.

         ALCATEL NOTE:
             ACCESS:   NA                  USAGE:    NA
             PERSIST:  NO                  INSRVMOD: NA
             RANGE:    NA                  DEFVALUE: 0
             UNITS:    NA                  SPARSE:   NA
             DESCR:    NA "
::= {xdslLinePrevious1DayEntry 3}

xdslLinePrevious1DayLOMCounter         OBJECT-TYPE
        SYNTAX          Counter
        ACCESS          read-only
        STATUS          mandatory
        DESCRIPTION     
        "This object represents for the previous 1 day interval the LOM failure 
         count, which is the number of occurences of a LOM failure event, where 
         a failure event occurs when the failure is declared and ends when the 
         failure clears.

         ALCATEL NOTE:
             ACCESS:   NA                  USAGE:    NA
             PERSIST:  NO                  INSRVMOD: NA
             RANGE:    NA                  DEFVALUE: 0
             UNITS:    NA                  SPARSE:   NA
             DESCR:    NA "
::= {xdslLinePrevious1DayEntry 4}

xdslLinePrevious1DayLPRCounter  OBJECT-TYPE
        SYNTAX  Counter
        ACCESS  read-only
        STATUS  mandatory
        DESCRIPTION     
        "This object represents for the previous 1 day interval the LPR failure 
         count, which is the number of occurences of an LPR failure event,
         where a failure event occurs when the failure is declared and ends
         when the failure clears.
         ALCATEL NOTE:
             ACCESS:   NA                  USAGE:    NA
             PERSIST:  NA                  INSRVMOD: NA
             RANGE:    NA                  DEFVALUE: NA
             UNITS:    NA                  SPARSE:   NA
             DESCR:    This object is not supported. "
::= {xdslLinePrevious1DayEntry 5}

xdslLinePrevious1DayESECounter         OBJECT-TYPE
        SYNTAX          Counter
        ACCESS          read-only
        STATUS          mandatory
        DESCRIPTION     
        "This object represents for the previous 1 day interval the ESE 
         failure count, which is the number of occurences of an ESE failure 
         event, where a failure event occurs when the failure is declared and 
         ends when the failure clears.

         ALCATEL NOTE:
             ACCESS:   NA                  USAGE:    NA
             PERSIST:  NO                  INSRVMOD: NA
             RANGE:    NA                  DEFVALUE: 0
             UNITS:    NA                  SPARSE:   NA
             DESCR:    NA "
::= {xdslLinePrevious1DayEntry 6}

xdslLinePrevious1DayESCounter          OBJECT-TYPE
        SYNTAX          Counter
        ACCESS          read-only
        STATUS          mandatory
        DESCRIPTION     
        "The counter associated with the number of Errored Seconds encountered 
         by the line in the previous 1 day interval.

         ALCATEL NOTE:
             ACCESS:   NA                  USAGE:    NA
             PERSIST:  NO                  INSRVMOD: NA
             RANGE:    NA                  DEFVALUE: 0
             UNITS:    NA                  SPARSE:   NA
             DESCR:    NA "
::= {xdslLinePrevious1DayEntry 7}

xdslLinePrevious1DaySESCounter         OBJECT-TYPE
        SYNTAX          Counter
        ACCESS          read-only
        STATUS          mandatory
        DESCRIPTION     
        "The counter associated with the number of Severely Errored Seconds
         encountered by the line in the previous 1 day interval.

         ALCATEL NOTE:
             ACCESS:   NA                  USAGE:    NA
             PERSIST:  NO                  INSRVMOD: NA
             RANGE:    NA                  DEFVALUE: 0
             UNITS:    NA                  SPARSE:   NA
             DESCR:    NA "
::= {xdslLinePrevious1DayEntry 8}

xdslLinePrevious1DayUASCounter         OBJECT-TYPE
        SYNTAX          Counter
        ACCESS          read-only
        STATUS          mandatory
        DESCRIPTION     
        "The counter associated with the number of Unavailable Seconds
         encountered by the line in the previous 1 day interval.

         ALCATEL NOTE:
             ACCESS:   NA                  USAGE:    NA
             PERSIST:  NO                  INSRVMOD: NA
             RANGE:    NA                  DEFVALUE: 0
             UNITS:    NA                  SPARSE:   NA
             DESCR:    NA "
::= {xdslLinePrevious1DayEntry 9}

xdslLinePrevious1DayReInitCounter      OBJECT-TYPE
        SYNTAX          Counter
        ACCESS          read-only
        STATUS          mandatory
        DESCRIPTION     
        "This object represents for the previous 1 day interval the number of
         times the modem left showtime and tried to re-initialize the line
         because of detection of a persistent defect.

         ALCATEL NOTE:
             ACCESS:   NA                  USAGE:    NA
             PERSIST:  NO                  INSRVMOD: NA
             RANGE:    NA                  DEFVALUE: 0
             UNITS:    NA                  SPARSE:   NA
             DESCR:    NA "
::= {xdslLinePrevious1DayEntry 10}

xdslLinePrevious1DayFailedInitCounter  OBJECT-TYPE
        SYNTAX          Counter
        ACCESS          read-only
        STATUS          mandatory
        DESCRIPTION     
        "This object represents for the previous 1 day interval the number of
         times the modem tries to initialize the line but fails.

         ALCATEL NOTE:
             ACCESS:   NA                  USAGE:    NA
             PERSIST:  NO                  INSRVMOD: NA
             RANGE:    NA                  DEFVALUE: 0
             UNITS:    NA                  SPARSE:   NA
             DESCR:    NA "
::= {xdslLinePrevious1DayEntry 11}

xdslLinePrevious1DayMeasuredTime       OBJECT-TYPE
        SYNTAX          INTEGER(0..86400)
        ACCESS          read-only
        STATUS          mandatory
        DESCRIPTION     
        "The amount of time, measured in seconds, that statistics for this
         entry have been counted.

         ALCATEL NOTE:
             ACCESS:   NA                  USAGE:    NA
             PERSIST:  NO                  INSRVMOD: NA
             RANGE:    NA                  DEFVALUE: 0
             UNITS:    seconds             SPARSE:   NA
             DESCR:    NA "
::= {xdslLinePrevious1DayEntry 12}

xdslLinePrevious1DayInvalidDataFlag    OBJECT-TYPE
        SYNTAX          INTEGER
        ACCESS          read-only
        STATUS          mandatory
        DESCRIPTION     
        "This object indicates the validity of the corresponding PM data.
         It is set to 1 when the PM data is incomplete or invalid and set to 0
         when the PM data is complete and valid.

         ALCATEL NOTE:
             ACCESS:   NA                  USAGE:    NA
             PERSIST:  NO                  INSRVMOD: NA
             RANGE:    0..1                DEFVALUE: 1
             UNITS:    NA                  SPARSE:   NA
             DESCR:    NA "
::= {xdslLinePrevious1DayEntry 13}

xdslLinePrevious1DayRAUCounter         OBJECT-TYPE
        SYNTAX          Counter
        ACCESS          read-only
        STATUS          mandatory
        DESCRIPTION     
        "This object represents for the previous 1 day interval the RAU anomaly 
         count, which is the number of occurences of an Upshift Rate 
         Adaptation.

         ALCATEL NOTE:
             ACCESS:   NA                  USAGE:    NA
             PERSIST:  NO                  INSRVMOD: NA
             RANGE:    NA                  DEFVALUE: 0
             UNITS:    NA                  SPARSE:   NA
             DESCR:    NA "
::= {xdslLinePrevious1DayEntry 14}

xdslLinePrevious1DayRADCounter         OBJECT-TYPE
        SYNTAX          Counter
        ACCESS          read-only
        STATUS          mandatory
        DESCRIPTION     
        "This object represents for the previous 1 day interval the RAD anomaly 
         count, which is the number of occurences of a Downshift Rate 
         Adaptation.

         ALCATEL NOTE:
             ACCESS:   NA                  USAGE:    NA
             PERSIST:  NO                  INSRVMOD: NA
             RANGE:    NA                  DEFVALUE: 0
             UNITS:    NA                  SPARSE:   NA
             DESCR:    NA "
::= {xdslLinePrevious1DayEntry 15}

xdslLinePrevious1DayLEFTRSCounter      OBJECT-TYPE
        SYNTAX          Counter
        ACCESS          read-only
        STATUS          mandatory
        DESCRIPTION     
        "When RTX is in use then this counter associates with the number of
         LEFTR seconds encountered by the line in the previous 1 day interval.
         Otherwise the default value will be returned.

         ALCATEL NOTE:
             ACCESS:   NA                  USAGE:    NA
             PERSIST:  NO                  INSRVMOD: NA
             RANGE:    NA                  DEFVALUE: 0
             UNITS:    NA                  SPARSE:   NA
             DESCR:    NA "
::= { xdslLinePrevious1DayEntry 16}

xdslLinePrevious1DayErrFreeBitsCounter      OBJECT-TYPE
        SYNTAX          Counter
        ACCESS          read-only
        STATUS          mandatory
        DESCRIPTION     
        "When RTX is in use then this counter represents for the previous 
         1 day interval the count of the number of error-free bits divided 
         by 2^16.
         Otherwise the default value will be returned.

         ALCATEL NOTE:
             ACCESS:   NA                  USAGE:    NA
             PERSIST:  NO                  INSRVMOD: NA
             RANGE:    NA                  DEFVALUE: 0
             UNITS:    NA                  SPARSE:   NA
             DESCR:    NA "
::= { xdslLinePrevious1DayEntry 17}

xdslLinePrevious1DayMinEFTRValue      OBJECT-TYPE
        SYNTAX          INTEGER
        ACCESS          read-only
        STATUS          mandatory
        DESCRIPTION     
        "When RTX is in use then this counter represents for the previous 
         1 day interval the count of the Minimum of the EFTR observed
         during this interval.
         Otherwise the default value will be returned.

         ALCATEL NOTE:
             ACCESS:   NA                  USAGE:    NA
             PERSIST:  NO                  INSRVMOD: NA
             RANGE:    NA                  DEFVALUE: 0
             UNITS:    NA                  SPARSE:   NA
             DESCR:    NA "
::= { xdslLinePrevious1DayEntry 18}

xdslLineInmPreviousIntervalTable       OBJECT-TYPE
        SYNTAX          SEQUENCE OF XdslLineInmPreviousIntervalEntry
        ACCESS          not-accessible
        STATUS          mandatory
        DESCRIPTION     
        " The xdsl line Impulse noise Monitoring near end previous 15 minute
         interval table.

         ALCATEL NOTE:
             TABLESIZE: DEP [number of XDSL lines]                    
             DESCR:     NA                   "
::= {xdslLinePrevious 7}

xdslLineInmPreviousIntervalEntry       OBJECT-TYPE
        SYNTAX          XdslLineInmPreviousIntervalEntry
        ACCESS          not-accessible
        STATUS          mandatory
        DESCRIPTION     
        " An entry in the xdsl line Impulse Noise Monitoring previous 15 minute
         interval table.

         Row creation : Entries for all XDSL lines belonging to a board are 
                        created by the system when the board is planned.
         Row deletion : Entries for all XDSL lines belonging to a board are 
                        deleted by the system when the board is unplanned. "
        INDEX          {ifIndex}
::= {xdslLineInmPreviousIntervalTable 1}

XdslLineInmPreviousIntervalEntry ::=
        SEQUENCE {
            xdslLineInmPreviousIntervalIatHistogram            IatHistogramType,
            xdslLineInmPreviousIntervalEquivInpHistogram       EquivInpHistogramType,
            xdslLineInmPreviousIntervalTotalDataSymbolCounter  Counter
        }
        
xdslLineInmPreviousIntervalIatHistogram              OBJECT-TYPE
        SYNTAX          IatHistogramType
        ACCESS          read-only
        STATUS          mandatory
        DESCRIPTION     
        " This object represents the Impulse Noise Monitoring Inter-Arrival Time
         histogram for the previous 15 minute interval. The histogram consists
         of eight saturating counters representing the different class
         intervals configured.
         The Inter-Arrival Time is defined as the time between the start of two
         consecutive impulses, expressed as an number of data symbols.
         The class intervals width and offset are defined by
         xdslLineInmInterArrivalTimeStep and xdslLineInmInterArrivalTimeOffset.
         The Inter-Arrival Time histogram is coded as a fixed length
         octet string defined as follows:
         OCTETS 0..1: INTEGER (0..65535), value of the first class interval.
         The value is defined as MSB-LSB (big-endian).
         OCTETS 2..3: define the value of class interval 2.
         ....        up to
         OCTETS 14..15: define the last class interval 8.

         ALCATEL NOTE:
             ACCESS:   NA                  USAGE:    NA
             PERSIST:  NO                  INSRVMOD: NA
             RANGE:    NA                  DEFVALUE: '00000000000000000000000000000000'H
             UNITS:    octets              SPARSE:   NA
             DESCR:    NA "
::= {xdslLineInmPreviousIntervalEntry 1}

xdslLineInmPreviousIntervalEquivInpHistogram              OBJECT-TYPE
        SYNTAX          EquivInpHistogramType
        ACCESS          read-only
        STATUS          mandatory
        DESCRIPTION     
        "This object represents the Impulse Noise Monitoring Equivalent INP
         histogram for the previous 15 minute interval. The histogram consists
         of seventeen saturating counters representing the different class
         intervals.
         Class intervals 1 to 16 contain the number of impulse noise events
         detected per equivalent level of INP as defined by
         xdslLineEquivInpMode. Class interval 17 contains the number of impulse
         noise events detected with equivalent level of INP greater than 16.
         The equivalent INP histogram is coded as a fixed length
         octet string defined as follows:
         OCTETS 0..1: INTEGER (0..65535), value of the first class interval.
         The value is defined as MSB-LSB (big-endian).
         OCTETS 2..3: define the value of class interval 2.
         ....        up to
         OCTETS 32..33: define the last class interval 17.

         ALCATEL NOTE:
             ACCESS:   NA                  USAGE:    NA
             PERSIST:  NO                  INSRVMOD: NA
             RANGE:    NA                  DEFVALUE: '00000000000000000000000000000000000000000000000000000000000000000000'H
             UNITS:    octets              SPARSE:   NA
             DESCR:    NA "
::= {xdslLineInmPreviousIntervalEntry 2}

xdslLineInmPreviousIntervalTotalDataSymbolCounter   OBJECT-TYPE
        SYNTAX          Counter
        ACCESS          read-only
        STATUS          mandatory
        DESCRIPTION     
        " This object represents the total number of data symbols that have
         been monitored to construct the Impulse Noise Monitoring histograms of
         Impulse Length and Inter-Arrival Time for the previous 15 minute
         interval.

         ALCATEL NOTE:
             ACCESS:   NA                  USAGE:    NA
             PERSIST:  NO                  INSRVMOD: NA
             RANGE:    NA                  DEFVALUE: 0
             UNITS:    NA                  SPARSE:   NA
             DESCR:    NA "
::= {xdslLineInmPreviousIntervalEntry 3}

xdslLineInmPrevious1DayTable       OBJECT-TYPE
        SYNTAX          SEQUENCE OF XdslLineInmPrevious1DayEntry
        ACCESS          not-accessible
        STATUS          mandatory
        DESCRIPTION     
        " The xdsl line Impulse noise Monitoring near end previous 1 day interval
         table.

         ALCATEL NOTE:
             TABLESIZE: DEP [number of XDSL lines]                    
             DESCR:     NA                   "
::= {xdslLinePrevious 8}

xdslLineInmPrevious1DayEntry       OBJECT-TYPE
        SYNTAX          XdslLineInmPrevious1DayEntry
        ACCESS          not-accessible
        STATUS          mandatory
        DESCRIPTION     
        " An entry in the xdsl line Impulse Noise Monitoring previous 1 day
         interval table.

         Row creation : Entries for all XDSL lines belonging to a board are 
                        created by the system when the board is planned.
         Row deletion : Entries for all XDSL lines belonging to a board are 
                        deleted by the system when the board is unplanned. "
        INDEX          {ifIndex}
::= {xdslLineInmPrevious1DayTable 1}

XdslLineInmPrevious1DayEntry ::=
        SEQUENCE {
            xdslLineInmPrevious1DayIatHistogram            IatHistogramType,
            xdslLineInmPrevious1DayEquivInpHistogram       EquivInpHistogramType,
            xdslLineInmPrevious1DayTotalDataSymbolCounter  Counter
        }
        
xdslLineInmPrevious1DayIatHistogram              OBJECT-TYPE
        SYNTAX          IatHistogramType
        ACCESS          read-only
        STATUS          mandatory
        DESCRIPTION     
        " This object represents the Impulse Noise Monitoring Inter-Arrival Time
         histogram for the previous 1 day interval. The histogram consists
         of eight saturating counters representing the different class
         intervals configured.
         The Inter-Arrival Time is defined as the time between the start of two
         consecutive impulses, expressed as an number of data symbols.
         The class intervals width and offset are defined by
         xdslLineInmInterArrivalTimeStep and xdslLineInmInterArrivalTimeOffset.
         The Inter-Arrival Time histogram is coded as a fixed length
         octet string defined as follows:
         OCTETS 0..1: INTEGER (0..65535), value of the first class interval.
         The value is defined as MSB-LSB (big-endian).
         OCTETS 2..3: define the value of class interval 2.
         ....        up to
         OCTETS 14..15: define the last class interval 8.

         ALCATEL NOTE:
             ACCESS:   NA                  USAGE:    NA
             PERSIST:  NO                  INSRVMOD: NA
             RANGE:    NA                  DEFVALUE: '00000000000000000000000000000000'H
             UNITS:    octets              SPARSE:   NA
             DESCR:    NA "
::= {xdslLineInmPrevious1DayEntry 1}

xdslLineInmPrevious1DayEquivInpHistogram              OBJECT-TYPE
        SYNTAX          EquivInpHistogramType
        ACCESS          read-only
        STATUS          mandatory
        DESCRIPTION     
        "This object represents the Impulse Noise Monitoring Equivalent INP
         histogram for the previous 1 day interval. The histogram consists
         of seventeen saturating counters representing the different class
         intervals.
         Class intervals 1 to 16 contain the number of impulse noise events
         detected per equivalent level of INP as defined by
         xdslLineEquivInpMode. Class interval 17 contains the number of impulse
         noise events detected with equivalent level of INP greater than 16.
         The equivalent INP histogram is coded as a fixed length
         octet string defined as follows:
         OCTETS 0..1: INTEGER (0..65535), value of the first class interval.
         The value is defined as MSB-LSB (big-endian).
         OCTETS 2..3: define the value of class interval 2.
         ....        up to
         OCTETS 32..33: define the last class interval 17.

         ALCATEL NOTE:
             ACCESS:   NA                  USAGE:    NA
             PERSIST:  NO                  INSRVMOD: NA
             RANGE:    NA                  DEFVALUE: '00000000000000000000000000000000000000000000000000000000000000000000'H
             UNITS:    octets              SPARSE:   NA
             DESCR:    NA "
::= {xdslLineInmPrevious1DayEntry 2}

xdslLineInmPrevious1DayTotalDataSymbolCounter   OBJECT-TYPE
        SYNTAX          Counter
        ACCESS          read-only
        STATUS          mandatory
        DESCRIPTION     
        " This object represents the total number of data symbols that have
         been monitored to construct the Impulse Noise Monitoring histograms of
         Impulse Length and Inter-Arrival Time for the previous 1 day interval.

         ALCATEL NOTE:
             ACCESS:   NA                  USAGE:    NA
             PERSIST:  NO                  INSRVMOD: NA
             RANGE:    NA                  DEFVALUE: 0
             UNITS:    NA                  SPARSE:   NA
             DESCR:    NA "
::= {xdslLineInmPrevious1DayEntry 3}

xdslLineSpectrumProfileIndexOffset     OBJECT-TYPE
        SYNTAX          AsamMaxProfileIndex
        ACCESS          read-only
        STATUS          mandatory
        DESCRIPTION
        "This object represents the offset to be added to an existing spectrum
         profile index during a modification in order to access the temporary
         profile entry that contains the updates being done on that profile, 
         see xdslLineSpectrumProfileIndex.

         ALCATEL NOTE:
             ACCESS:   NA                  USAGE:    NA
             PERSIST:  NO                  INSRVMOD: NA
             RANGE:    1000                DEFVALUE: 1000
             UNITS:    NA                  SPARSE:   NA
             DESCR:    NA "
::= {xdslLine 10}

xdslLineInsConfTable       OBJECT-TYPE
        SYNTAX          SEQUENCE OF XdslLineInsConfEntry
        ACCESS          not-accessible
        STATUS          mandatory
        DESCRIPTION     
        " The xdsl line impulse noise sensor configuration table.

         ALCATEL NOTE:
             TABLESIZE: DEP [number of XDSL lines]                    
             DESCR:     NA                   "
::= {xdslLine 12}

xdslLineInsConfEntry       OBJECT-TYPE
        SYNTAX          XdslLineInsConfEntry
        ACCESS          not-accessible
        STATUS          mandatory
        DESCRIPTION     
        " An entry in the xdsl line impulse noise sensor configuration table.

         Row creation : Entries for all XDSL lines belonging to a board are 
                        created by the system when the board is planned.
         Row deletion : Entries for all XDSL lines belonging to a board are 
                        deleted by the system when the board is unplanned. "
        INDEX          {ifIndex}
::= {xdslLineInsConfTable 1}

XdslLineInsConfEntry ::=
        SEQUENCE {
            xdslLineInmMode                         INTEGER,
            xdslLineInmEquivInpMode                 INTEGER,
            xdslLineInsSensitivity                  INTEGER,
            xdslLineInmClusterContinuation          INTEGER,
            xdslLineInmInterArrivalTimeOffset       INTEGER,
            xdslLineInmInterArrivalTimeStep         INTEGER
        }
        
xdslLineInmMode              OBJECT-TYPE
        SYNTAX          INTEGER {
                            disabled (1),
                            enabled (2)
                        }
        ACCESS          read-write
        STATUS          mandatory
        DESCRIPTION     
        "This parameter indicates if the Upstream Impulse Noise Monitoring
         statistics collection mechanism is enabled or disabled.

         ALCATEL NOTE:
             ACCESS:   NA                  USAGE:    OPT
             PERSIST:  NO                  INSRVMOD: YES
             RANGE:    NA                  DEFVALUE: disabled
             UNITS:    NA                  SPARSE:   NA
             DESCR:    NA "
::= {xdslLineInsConfEntry 1}

xdslLineInmEquivInpMode              OBJECT-TYPE
        SYNTAX          INTEGER
        ACCESS          read-write
        STATUS          mandatory
        DESCRIPTION     
    "This parameter indicates the mode used in the computation of the
     equivalent INP for construction of the INM Equivalent INP histograms.

     Mode 0 : Impulse length.
     Mode 1 : Cluster length.
     Mode 2 : Sum of impulse length in cluster.
     Mode 3 : Gap compensated impulse length in cluster.

         ALCATEL NOTE:
             ACCESS:   NA                  USAGE:    OPT
             PERSIST:  NO                  INSRVMOD: YES
             RANGE:    0..3                DEFVALUE: 0
             UNITS:    NA                  SPARSE:   NA
             DESCR:    NA "
::= {xdslLineInsConfEntry 2}

xdslLineInsSensitivity              OBJECT-TYPE
        SYNTAX          INTEGER
        ACCESS          read-write
        STATUS          mandatory
        DESCRIPTION     
        "This parameters indicates the Upstream Impulse Noise Sensor
         sensitivity relative to the default detection capability under current
         loop condition and noise margin.
         Range: -12.8 dB to 12.7 dB with 0.1 dB steps.
         The value 0 dB corresponds to default sensitivity.

         ALCATEL NOTE:
             ACCESS:   NA                  USAGE:    OPT
             PERSIST:  NO                  INSRVMOD: YES
             RANGE:    -128..127           DEFVALUE: 0
             UNITS:    dB / 10             SPARSE:   NA
             DESCR:    NA "
::= {xdslLineInsConfEntry 3}

xdslLineInmClusterContinuation              OBJECT-TYPE
        SYNTAX          INTEGER
        ACCESS          read-write
        STATUS          mandatory
        DESCRIPTION     
        "This parameter indicates for the Impulse Noise Monitoring statistics
         collection the way the degraded data symbols have to be grouped by the
         cluster continuation mechanism to indicate impulses.
         Range: 1 to 64 DMT Symbols plus special value 0.
         Special value 0 is used to indicate that cluster continuation is
         disabled.

         ALCATEL NOTE:
             ACCESS:   NA                  USAGE:    OPT
             PERSIST:  NO                  INSRVMOD: YES
             RANGE:    0..64               DEFVALUE: 0
             UNITS:    DMT Symbol          SPARSE:   NA
             DESCR:    NA "
::= {xdslLineInsConfEntry 4}

xdslLineInmInterArrivalTimeOffset              OBJECT-TYPE
        SYNTAX          INTEGER
        ACCESS          read-write
        STATUS          mandatory
        DESCRIPTION     
        "This parameter indicates the offset applied on the class intervals of
         the Upstream Inter-Arrival Time histograms.
         Range: 3 to 511 DMT Symbol.

         ALCATEL NOTE:
             ACCESS:   NA                  USAGE:    OPT
             PERSIST:  NO                  INSRVMOD: YES
             RANGE:    3..511              DEFVALUE: 3
             UNITS:    DMT Symbol          SPARSE:   NA
             DESCR:    NA "
::= {xdslLineInsConfEntry 5}

xdslLineInmInterArrivalTimeStep              OBJECT-TYPE
        SYNTAX          INTEGER
        ACCESS          read-write
        STATUS          mandatory
        DESCRIPTION     
        "This parameter indicates the width of the class intervals of the
         Upstream Inter-Arrival Time histograms.
         Range: 0 to 7.

         ALCATEL NOTE:
             ACCESS:   NA                  USAGE:    OPT
             PERSIST:  NO                  INSRVMOD: YES
             RANGE:    0..7                DEFVALUE: 0
             UNITS:    NA                  SPARSE:   NA
             DESCR:    NA "
::= {xdslLineInsConfEntry 6}

xdslFarEndLineOperDataTable            OBJECT-TYPE
        SYNTAX          SEQUENCE OF XdslFarEndLineOperDataEntry
        ACCESS          not-accessible
        STATUS          mandatory
        DESCRIPTION     
        "The xdsl far end line operational data table.

         ALCATEL NOTE:
             TABLESIZE: DEP [number of XDSL lines]                    
             DESCR:     NA                   "
::= {xdslFarEndLineCurrent 1}

xdslFarEndLineOperDataEntry            OBJECT-TYPE
        SYNTAX          XdslFarEndLineOperDataEntry                     
        ACCESS          not-accessible
        STATUS          mandatory
        DESCRIPTION     
        "An entry in the xdsl far end line operational data table.

         Row creation : Entries for all XDSL lines belonging to a board are 
                        created when the board becomes operational.
         Row deletion : Entries for all XDSL lines belonging to a board are 
                        deleted when the board becomes unavailable. "
        INDEX          {ifIndex}
::= {xdslFarEndLineOperDataTable 1}

XdslFarEndLineOperDataEntry ::=
        SEQUENCE {
          xdslFarEndLineRelCapacityOccupationDownstream    INTEGER,
          xdslFarEndLineNoiseMarginDownstream              INTEGER,
          xdslFarEndLineOutputPowerUpstream                INTEGER,
          xdslFarEndLineSignalAttenuationDownstream        INTEGER,
          xdslFarEndLineLoopAttenuationDownstream          INTEGER,
          xdslFarEndLineXturOpModeCapabilities             OpModeType,
          xdslFarEndLineLastTxStateUpstream                INTEGER,
          xdslFarEndLineActualPsdUpstream                  INTEGER,
          xdslFarEndLinePerBandLoopAttenuationDownstream   PerBandOperDataType,
          xdslFarEndLinePerBandSignalAttenuationDownstream PerBandOperDataType,
          xdslFarEndLinePerBandNoiseMarginDownstream       PerBandOperDataType,
          xdslFarEndLineHighestFrequencyDownstream         INTEGER,
          xdslFarEndLineElectricalLengthEstimated          INTEGER,
          xdslFarEndLineTimingAdvanceProposed              INTEGER,
          xdslFarEndLineActualRaModeDownstream             XdslActualRAModeType,
          xdslFarEndLineActualRtxModeDownstream            ActualRtxMode
        }

xdslFarEndLineRelCapacityOccupationDownstream    OBJECT-TYPE
        SYNTAX          INTEGER
        ACCESS          read-only
        STATUS          mandatory
        DESCRIPTION     
        "This parameter represents the ratio of the actual line bitrate over
         the maximum attainable line bitrate in the downstream direction,
         calculated in the latency path in use and represented in percentages.
         The line rate is equal to the net data rate plus all overhead 
         information (framing overhead, Reed Solomon overhead, Trellis 
         overhead). 
         When the modem is not in showtime, then the value measured in 
         preceeding showtime session is returned. The value is fixed to 100% in 
         case of activation failure when for that particular downstream 
         direction a bitrate higher than the attainable bitrate has been
         requested.
         When no data is available (e.g. before first showtime) value 0
         is used.
         Range is 0 to 100% with a granularity of 1 %.

         ALCATEL NOTE:
             ACCESS:   NA                  USAGE:    NA
             PERSIST:  NO                  INSRVMOD: NA
             RANGE:    0..100              DEFVALUE: 0
             UNITS:    percent             SPARSE:   NA
             DESCR:    NA "
::= {xdslFarEndLineOperDataEntry 1}

xdslFarEndLineNoiseMarginDownstream    OBJECT-TYPE
        SYNTAX          INTEGER
        ACCESS          read-only
        STATUS          mandatory
        DESCRIPTION     
        "This parameter indicates the current noise margin 
         for the downstream direction. When the modem is not in showtime this
         object will have the previously measured value.
         When no data is available (e.g. before first showtime) value 0
         is used.
         Range is -64 to 63 dB with a granularity of 0,1 dB.
         It is representyes as 1/10 * xdslFarEndLineNoiseMarginDownstream.

         ALCATEL NOTE:
             ACCESS:   NA                  USAGE:    NA
             PERSIST:  NO                  INSRVMOD: NA
             RANGE:    -640..630           DEFVALUE: 0
             UNITS:    dB / 10             SPARSE:   NA
             DESCR:    NA "
::= {xdslFarEndLineOperDataEntry 2}

xdslFarEndLineOutputPowerUpstream      OBJECT-TYPE
        SYNTAX          INTEGER
        ACCESS          read-only
        STATUS          mandatory
        DESCRIPTION     
        "This object gives the actual aggregate output power for the upstream 
         carriers. When the modem is not in showtime this object will have the
         previously measured value. 
         When no data is available (e.g. before first showtime) value 0
         is used.
         Range is -31 to 31 dBm with a granularity of 0,1 dB.
         It is representyes as 1/10 * xdslFarEndLineOutputPowerUpstream.

         ALCATEL NOTE:
             ACCESS:   NA                  USAGE:    NA
             PERSIST:  NO                  INSRVMOD: NA
             RANGE:    -310..310           DEFVALUE: 0
             UNITS:    dBm / 10            SPARSE:   NA
             DESCR:    NA "
::= {xdslFarEndLineOperDataEntry 3}

xdslFarEndLineSignalAttenuationDownstream        OBJECT-TYPE
        SYNTAX          INTEGER
        ACCESS          read-only
        STATUS          mandatory
        DESCRIPTION     
        "This object gives the difference in dB between the power measured at
         the far-end receiver and that transmitted from the near-end. The
         signal attenuation is measured over all data carriers and is updated
         during showtime.
         When the modem is not in showtime this object will have the value
         measured during the previous showtime session.
         When no data is available (e.g. before first showtime) value 0
         is used.
         It is represented as 1/10 * xdslFarEndLineSignalAttenuationDownstream, 
         with a range of (0..127dB) and a granularity of 0.1 dB.

         ALCATEL NOTE:
             ACCESS:   NA                  USAGE:    NA
             PERSIST:  NO                  INSRVMOD: NA
             RANGE:    0..1270             DEFVALUE: 0
             UNITS:    dB / 10             SPARSE:   NA
             DESCR:    NA "
::= {xdslFarEndLineOperDataEntry 4}

xdslFarEndLineLoopAttenuationDownstream          OBJECT-TYPE
        SYNTAX          INTEGER
        ACCESS          read-only
        STATUS          mandatory
        DESCRIPTION     
        "This object gives the difference in dB between the power 
         measured at the far-end receiver and that transmitted from the
         near-end over all sub-carriers. The loop attenuation is measured at
         initialization and is not updated during showtime.
         When the modem is not in showtime this object will have the value
         measured during the previous showtime session.
         When no data is available (e.g. before first showtime) value 0
         is used.
         It is represented as 1/10 * xdslFarEndLineLoopAttenuationDownstream,
         with a range of (0..127dB) and a granularity of 0.1 dB.

         ALCATEL NOTE:
             ACCESS:   NA                  USAGE:    NA
             PERSIST:  NO                  INSRVMOD: NA
             RANGE:    0..1270             DEFVALUE: 0
             UNITS:    dB / 10             SPARSE:   NA
             DESCR:    NA "
::= {xdslFarEndLineOperDataEntry 5}

xdslFarEndLineXturOpModeCapabilities   OBJECT-TYPE
        SYNTAX          OpModeType
        ACCESS          read-only
        STATUS          mandatory
        DESCRIPTION 
        "This variable consists of a bitmap which represents the operational
         modes supported at the XTU-R. It uses the same coding as defined in
         xdslLineOpMode.
         When the modem is not in showtime this object will have the value
         measured during the previous showtime session.
         When no data is available (e.g. before first showtime) value 0
         is used.

         ALCATEL NOTE:
             ACCESS:   NA                  USAGE:    NA
             PERSIST:  NO                  INSRVMOD: NA
             RANGE:    NA
             DEFVALUE: '00 00 00 00 00 00 00 00 
                        00 00 00 00 00 00 00 00'H
             UNITS:    octets              SPARSE:   NA
             DESCR:    NA "
::= {xdslFarEndLineOperDataEntry 6}

xdslFarEndLineLastTxStateUpstream     OBJECT-TYPE
        SYNTAX          INTEGER
        ACCESS          read-only
        STATUS          mandatory
        DESCRIPTION     
        "This object gives the last successful transmitted initialisation state
         as defined in G.999.1. It is reported for ADSL2 modes in Loop
         Diagnostics State only.
         ALCATEL NOTE:
             ACCESS:   NA                  USAGE:    NA
             PERSIST:  NA                  INSRVMOD: NA
             RANGE:    NA                  DEFVALUE: NA
             UNITS:    NA                  SPARSE:   NA
             DESCR:    This object is not supported. "
::= {xdslFarEndLineOperDataEntry 7}

xdslFarEndLineActualPsdUpstream        OBJECT-TYPE
        SYNTAX          INTEGER
        ACCESS          read-only
        STATUS          mandatory
        DESCRIPTION     
        "This object gives the average transmit power spectrum density over the
         used carriers in the upstream direction as measured at the U-C
         reference point.
         When the modem is not in showtime this object will have the value
         measured during the previous showtime session.
         When no data is available (e.g. before first showtime) value 0
         is used.
         Range is -95.5 dBm/Hz to 0 dBm/Hz with 0,1 dB steps. The actual PSD is
         represented as 1/10 * xdslFarEndLineActualPsdUpstream.

         ALCATEL NOTE:
             ACCESS:   NA                  USAGE:    NA
             PERSIST:  NO                  INSRVMOD: NA
             RANGE:    -955..0             DEFVALUE: 0
             UNITS:    dBm/Hz * 1/10       SPARSE:   NA
             DESCR:    NA "
::= {xdslFarEndLineOperDataEntry 8}

xdslFarEndLinePerBandLoopAttenuationDownstream   OBJECT-TYPE
        SYNTAX          PerBandOperDataType
        ACCESS          read-only
        STATUS          mandatory
        DESCRIPTION
        "This object indicates loop attenuation for each downstream
         band (including optional band) in case of VDSL2.
         It is represented for each band as 
         1/10 * xdslFarEndLinePerBandLoopAttenuationDownstream,
         with a range of (0..127dB) and a granularity of 0.1 dB.
         Max value is used to indicate that no Opdata is available for the
         corresponding band.
         OCTETS (0,1) represent value for band 0, coded as an integer in the
         range 0.. 1270. The value is defined as MSB-LSB (big-endian).
         OCTETS (2*N,2*N+1) represent value for band N, coded as an integer in
         the range 0.. 1270.
         Maximum value for N is 4.

         ALCATEL NOTE:
             ACCESS:   NA                  USAGE:    NA
             PERSIST:  NO                  INSRVMOD: NA
             RANGE:    NA 
             DEFVALUE: '00 00 00 00 00 00 00 00 00 00'H
             UNITS:    octets              SPARSE:   NA
             DESCR:    NA "
::= {xdslFarEndLineOperDataEntry 9}

xdslFarEndLinePerBandSignalAttenuationDownstream OBJECT-TYPE
        SYNTAX          PerBandOperDataType
        ACCESS          read-only
        STATUS          mandatory
        DESCRIPTION
        "This object indicates signal attenuation for each downstream
         band (including optional band) in case of VDSL2.
         It is represented for each band
         as 1/10 * xdslFarEndLinePerBandSignalAttenuationDownstream,
         with a range of (0..127dB) and a granularity of 0.1 dB.
         Max value is used to indicate that no Opdata is available for the
         corresponding band.
         OCTETS (0,1) represent value for band 0, coded as an integer in the
         range 0.. 1270. The value is defined as MSB-LSB (big-endian).
         OCTETS (2*N,2*N+1) represent value for band N, coded as an integer in 
         the range 0.. 1270.
         Maximum value for N is 4.

         ALCATEL NOTE:
             ACCESS:   NA                  USAGE:    NA
             PERSIST:  NO                  INSRVMOD: NA
             RANGE:    NA
             DEFVALUE: '00 00 00 00 00 00 00 00 00 00'H
             UNITS:    octets              SPARSE:   NA
             DESCR:    NA "
::= {xdslFarEndLineOperDataEntry 10}

xdslFarEndLinePerBandNoiseMarginDownstream       OBJECT-TYPE
        SYNTAX          PerBandOperDataType
        ACCESS          read-only
        STATUS          mandatory
        DESCRIPTION
        "This object indicates noise margin for each upstream band (including
         optional band) in case of VDSL2. It is represented as 1/10 * 
         xdslFarEndLinePerBandNoiseMarginDownstream, with a range of 
         (-64..63dB) and a granularity of 0.1 dB for each band.
         Max value is used to indicate that no Opdata is available for the
         corresponding band.
         OCTETS (0,1) represent value for band 0, coded as an integer in the
         range -640.. 630. The value is defined as MSB-LSB (big-endian).
         OCTETS (2*N,2*N+1) represent value for band N, coded as an integer in 
         the range -640.. 630.
         Maximum value for N is 4.

         ALCATEL NOTE:
             ACCESS:   NA                  USAGE:    NA
             PERSIST:  NO                  INSRVMOD: NA
             RANGE:    NA
             DEFVALUE: '00 00 00 00 00 00 00 00 00 00'H
             UNITS:    octets              SPARSE:   NA
             DESCR:    NA "
::= {xdslFarEndLineOperDataEntry 11}

xdslFarEndLineHighestFrequencyDownstream         OBJECT-TYPE
        SYNTAX          INTEGER
        ACCESS          read-only
        STATUS          mandatory
        DESCRIPTION
        "This object indicates the highest carrier frequency used
         in the downstream direction in case of VDSL2.

         ALCATEL NOTE:
             ACCESS:   NA                  USAGE:    NA
             PERSIST:  NO                  INSRVMOD: NA
             RANGE:    0..30000            DEFVALUE: 0
             UNITS:    kHz                 SPARSE:   NA
             DESCR:    NA "
::= {xdslFarEndLineOperDataEntry 12}

xdslFarEndLineElectricalLengthEstimated          OBJECT-TYPE
        SYNTAX          INTEGER
        ACCESS          read-only
        STATUS          mandatory
        DESCRIPTION
        "This object indicates the Line Electrical Length actually estimated
         by XTU-R when mode is VDSL2.
         Range: 0 to 127.5 dB @ 1MHz , with 0.5 dB steps.
         Integer range: 0..255, actual value * 2.

         ALCATEL NOTE:
             ACCESS:   NA                  USAGE:    NA
             PERSIST:  NO                  INSRVMOD: NA
             RANGE:    0..255              DEFVALUE: 0
             UNITS:    dB/2 @ 1MHz         SPARSE:   NA
             DESCR:    NA "
::= {xdslFarEndLineOperDataEntry 13}

xdslFarEndLineTimingAdvanceProposed    OBJECT-TYPE
        SYNTAX          INTEGER
        ACCESS          read-only
        STATUS          mandatory
        DESCRIPTION
        "This object defines the timing advance of transmitted symbol with 
         respect to the received symbol when mode is VDSL-2.  Near end value
         corresponds to the value proposed by XTU-R.
         Range: -250000..250000 ns in steps of 10 ns.
         Integer range: -25000..25000 (actual value / 10)

         ALCATEL NOTE:
             ACCESS:   NA                  USAGE:    NA
             PERSIST:  NO                  INSRVMOD: NA
             RANGE:    -25000..25000       DEFVALUE: 0
             UNITS:    ns * 10             SPARSE:   NA
             DESCR:    NA "
::= {xdslFarEndLineOperDataEntry 14}

xdslFarEndLineActualRaModeDownstream             OBJECT-TYPE
        SYNTAX          XdslActualRAModeType
        ACCESS          read-only
        STATUS          mandatory
        DESCRIPTION
        "This object indicates the Rate Adaptive mode in the downstream direction 
         that is actually used.

         ALCATEL NOTE:
             ACCESS:   NA                  USAGE:    NA
             PERSIST:  NO                  INSRVMOD: NA
             RANGE:    1,2,3,255           DEFVALUE: UnknownNotSupported
             UNITS:    NA                  SPARSE:   NA
             DESCR:    NA "
::= { xdslFarEndLineOperDataEntry 15}

xdslFarEndLineActualRtxModeDownstream             OBJECT-TYPE
        SYNTAX          ActualRtxMode
        ACCESS          read-only
        STATUS          mandatory
        DESCRIPTION
        "This object indicates if the RTX is used in the downstream direction.

         ALCATEL NOTE:
             ACCESS:   NA                  USAGE:    NA
             PERSIST:  NO                  INSRVMOD: NA
             RANGE:    1..6,255            DEFVALUE: UnknownNotSupported
             UNITS:    NA                  SPARSE:   NA
             DESCR:    NA "
::= { xdslFarEndLineOperDataEntry 16}

xdslFarEndLineCarrierDataTable         OBJECT-TYPE
        SYNTAX          SEQUENCE OF XdslFarEndLineCarrierDataEntry
        ACCESS          not-accessible
        STATUS          mandatory
        DESCRIPTION     
        "The xdsl far end line carrier data table.

         ALCATEL NOTE:
             TABLESIZE: DEP [number of XDSL lines]                   
             DESCR:     NA                   "
::= {xdslFarEndLineCurrent 2}

xdslFarEndLineCarrierDataEntry         OBJECT-TYPE
        SYNTAX          XdslFarEndLineCarrierDataEntry                   
        ACCESS          not-accessible
        STATUS          mandatory
        DESCRIPTION     
        "An entry in the xdsl far end line carrier data table.

         Row creation : Entries for all XDSL lines belonging to a board are 
                        created when the board becomes operational.
         Row deletion : Entries for all XDSL lines belonging to a board are 
                        deleted when the board becomes unavailable. "
        INDEX          {ifIndex}
::= {xdslFarEndLineCarrierDataTable 1}

XdslFarEndLineCarrierDataEntry ::=
        SEQUENCE {
            xdslFarEndLineCarrierLoadUpstream         OCTET STRING,
            xdslFarEndLineCarrierGainUpstream         OCTET STRING,
            xdslFarEndLineCarrierTssUpstream          OCTET STRING,
            xdslFarEndLineCarrierSnrDownstream        OCTET STRING,
            xdslFarEndLineCarrierQlnDownstream        OCTET STRING,
            xdslFarEndLineCarrierHlinDownstream       OCTET STRING,
            xdslFarEndLineCarrierHlogDownstream       OCTET STRING,
            xdslFarEndLineCarrierSpacingUpstream      CarrierSpacingType,
            xdslFarEndLineCarrierTxPsdUpstream        OCTET STRING,
            xdslFarEndLineCarrierGroupTxPsd           SubCarrierGroupSizeType,
            xdslFarEndLineCarrierGroupLoad            SubCarrierGroupSizeType,
            xdslFarEndLineCarrierGroupGain            SubCarrierGroupSizeType,
            xdslFarEndLineCarrierGroupTss            SubCarrierGroupSizeType,
            xdslFarEndLineCarrierGroupSnr             SubCarrierGroupSizeType,
            xdslFarEndLineCarrierGroupQln             SubCarrierGroupSizeType,
            xdslFarEndLineCarrierGroupHLin            SubCarrierGroupSizeType,
            xdslFarEndLineCarrierGroupHLog            SubCarrierGroupSizeType
        }

xdslFarEndLineCarrierLoadUpstream      OBJECT-TYPE
        SYNTAX          OCTET STRING
        ACCESS          read-only
        STATUS          mandatory
        DESCRIPTION     
        "This object represents the bit load distribution i.e. the number of
         bits per carrier group over the upstream passband.
         When the modem is not in showtime this object will have the previously
         measured value.
         When the data are not available because the measurement is not
         completed, not enabled or not supported, an empty string will be
         returned.
         The XDSL upstream passband is composed of one or more bands (maximum
         5,including VDSL optional band). Each carrier can carry up to 15 bits.
         The carrier load is coded as a bitmap defined as follows:
         OCTETS 0,1: INTEGER (0..4096), index of the start carrier group of the
         first upstream band. The value is defined as MSB-LSB (big-endian).
         OCTETS 2,3: INTEGER (0..4096), index of the stop carrier group of the
         first upstream band. The value is defined as MSB-LSB (big-endian).
         OCTET 4: contains the bit load of the first two carrier groups of the
         band. The load of the first carrier group uses the most significant 4
         bits nibble.
         Range is 0-15 bits per carrier group, with a granularity of 1 bit/
         carrier group.
         OCTETS 5..L: and so on, up to the last carrier group of the first
         upstream band. The last nibble of OCTET L is set to 0x0 if not used.
         OCTETS L+1..M: contain the start/stop carrier groups and the carrier
         load of the second upstream band when available.
         OCTETS M+1..N: contain the start/stop carrier groups and the carrier
         load of the third upstream band when available.
         OCTETS N+1..P: contain the start/stop carrier groups and the carrier
         load of the fourth upstream band when available.
         OCTETS P+1..Q: contain the start/stop carrier groups and the carrier
         load of the fifth upstream band when available.

         ALCATEL NOTE:
             ACCESS:   NA                  USAGE:    NA
             PERSIST:  NO                  INSRVMOD: NA
             RANGE:    0..4117             DEFVALUE: ''H
             UNITS:    octets              SPARSE:   NA
             DESCR:    NA "
::= {xdslFarEndLineCarrierDataEntry 1}

xdslFarEndLineCarrierGainUpstream      OBJECT-TYPE
        SYNTAX          OCTET STRING
        ACCESS          read-only
        STATUS          mandatory
        DESCRIPTION     
        "This object provides the gain allocation (i.e. gi) per carrier group
         over the upstream passband.
         When the modem is not in showtime this object will have the previously
         measured value.
         When the data are not available because the measurement is not
         completed, not enabled or not supported, an empty string will be
         returned.
         The XDSL upstream passband is composed of one or more bands (maximum
         5, including VDSL optional band ).
         The gain has a range of approximately 0 - 8, in steps of 1/512. 
         The gain value is represented as gi/512 on a linear scale with gi a
         12 bits unsigned integer in the 0 to 4095 range given by the 12 LSB
         bits of a 2 bytes integer. 
         The carrier gain allocation is coded as a bitmap defined as follows:
         OCTETS 0,1: INTEGER (0..4096), index of the start carrier group of the
         first upstream band. The value is defined as MSB-LSB (big-endian).
         OCTETS 2,3: INTEGER (0..4096), index of the stop carrier group of the
         first upstream band. The value is defined as MSB-LSB (big-endian).
         OCTETS 4,5: INTEGER, contains the gain of the first carrier group of
         the band (start carrier group). 
         The value is defined as MSB-LSB (big-endian).
         OCTETS 6..L: and so on until the last carrier group of the first
         upstream band (stop carrier group).
         OCTETS L+1..M: contain the start/stop carrier groups and the carrier
         gain of the second upstream band when available.
         OCTETS M+1..N: contain the start/stop carrier groups and the carrier
         gain of the third upstream band when available.
         OCTETS N+1..P: contain the start/stop carrier groups and the carrier
         gain of the fourth upstream band when available.
         OCTETS P+1..Q: contain the start/stop carrier groups and the carrier
         gain of the fifth upstream band when available.

         ALCATEL NOTE:
             ACCESS:   NA                  USAGE:    NA
             PERSIST:  NO                  INSRVMOD: NA
             RANGE:    0..8214             DEFVALUE: ''H
             UNITS:    octets              SPARSE:   NA
             DESCR:    NA "
::= {xdslFarEndLineCarrierDataEntry 2}

xdslFarEndLineCarrierTssUpstream     OBJECT-TYPE
        SYNTAX                    OCTET STRING
        ACCESS                    read-only
        STATUS                    mandatory
        DESCRIPTION     
         "This object provides the Transmit Spectrum Shaping parameters
         (i.e. tssi) for the upstream direction.
         Its definition is for further study.
         ALCATEL NOTE:
             ACCESS:   NA                  USAGE:    NA
             PERSIST:  NA                  INSRVMOD: NA
             RANGE:    NA                  DEFVALUE: NA
             UNITS:    NA                  SPARSE:   NA
             DESCR:    This object is not supported. "
::= {xdslFarEndLineCarrierDataEntry 3}

xdslFarEndLineCarrierSnrDownstream     OBJECT-TYPE
        SYNTAX          OCTET STRING
        ACCESS          read-only
        STATUS          mandatory
        DESCRIPTION     
        "This object provides the Signal to Noise Ratio per carrier group over
         the downstream passband.
         When the modem is not in showtime this object will have the previously
         measured value.
         When the data are not available because the measurement is not
         completed, not enabled or not supported, an empty string will be
         returned.
         The XDSL downstream passband is composed of one or more bands (maximum
         5, including VDSL optional band).
         The SNR has a range from -32 to 95 dB in steps of 0.5 dB.
         It is represented as SNRi = -32 + snri/2, with snri an 8 bit
         unsigned integer in the range 0 to 254.
         The special value 255 indicates that no measurement is available for
         the carrier or that the measurement is out of range.
         The carrier snrs are coded as a bitmap defined as follows:
         OCTETS 0,1: INTEGER, contains the number of symbols used to
         measure the data. The value is defined as MSB-LSB (big-endian).
         OCTETS 2,3: INTEGER (0..4096), index of the start carrier group of the
         first downstream band. The value is defined as MSB-LSB (big-endian).
         OCTETS 4,5: INTEGER (0..4096), index of the stop carrier group of the
         first downstream band. The value is defined as MSB-LSB (big-endian).
         OCTETS 6: INTEGER, contains the snr of the first carrier group of the
         band (start carrier group).
         OCTETS 7..L: and so on until the last carrier group of the first
         downstream band (stop carrier group).
         OCTETS L+1..M: contain the start/stop carrier groups and the carrier
         snr of the second downstream band when available.
         OCTETS M+1..N: contain the start/stop carrier groups and the carrier
         snr of the third downstream band when available.
         OCTETS N+1..P: contain the start/stop carrier groups and the carrier
         snr of the fourth downstream band when available.
         OCTETS P+1..Q: contain the start/stop carrier groups and the carrier
         snr of the fifth downstream band when available.

         ALCATEL NOTE:
             ACCESS:   NA                  USAGE:    NA
             PERSIST:  NO                  INSRVMOD: NA
             RANGE:    0..4119             DEFVALUE: ''H
             UNITS:    octets              SPARSE:   NA
             DESCR:    NA "
::= {xdslFarEndLineCarrierDataEntry 4}

xdslFarEndLineCarrierQlnDownstream     OBJECT-TYPE
        SYNTAX          OCTET STRING
        ACCESS          read-only
        STATUS          mandatory
        DESCRIPTION     
        "This object provides the Quiet Line Noise measurement (QLN) per
         carrier group over the downstream passband.
         When the data are not available because the measurement is not
         completed, not enabled or not supported, an empty string will be
         returned.
         The XDSL downstream passband is composed of one or more bands (maximum
         5, including VDSL optional band).
         The QLN has a range from -150 dBm/Hz to -23 dBm/Hz in steps of
         0.5 dB. It is represented as QLNi = -23 - qlni/2, with qlni an 8 bit
         unsigned integer in the range 0 to 254.
         The special value 255 indicates that no measurement is available for
         the carrier or that the measurement is out of range.
         The carrier qlns are coded as a bitmap defined as follows:
         OCTETS 0,1: INTEGER, contains the number of symbols used to
         measure the data. The value is defined as MSB-LSB (big-endian).
         OCTETS 2,3: INTEGER (0..4096), index of the start carrier group of the
         first downstream band. The value is defined as MSB-LSB (big-endian).
         OCTETS 4,5: INTEGER (0..4096), index of the stop carrier group of the
         first downstream band. The value is defined as MSB-LSB (big-endian).
         OCTETS 6: INTEGER, contains the qln of the first carrier group of the
         band (start carrier group).
         OCTETS 7..L: and so on until the last carrier group of the first
         downstream band (stop carrier group).
         OCTETS L+1..M: contain the start/stop carrier groups and the carrier
         qln of the second downstream band when available.
         OCTETS M+1..N: contain the start/stop carrier groups and the carrier
         qln of the third downstream band when available.
         OCTETS N+1..P: contain the start/stop carrier groups and the carrier
         qln of the fourth downstream band when available.
         OCTETS P+1..Q: contain the start/stop carrier groups and the carrier
         qln of the fifth downstream band when available.

         ALCATEL NOTE:
             ACCESS:   NA                  USAGE:    NA
             PERSIST:  NO                  INSRVMOD: NA
             RANGE:    0..4119             DEFVALUE: ''H
             UNITS:    octets              SPARSE:   NA
             DESCR:    NA "
::= {xdslFarEndLineCarrierDataEntry 5}

xdslFarEndLineCarrierHlinDownstream    OBJECT-TYPE
        SYNTAX          OCTET STRING
        ACCESS          read-only
        STATUS          mandatory
        DESCRIPTION      
        "This object provides the channel characteristics function complex
         values in linear scale for each carrier group over the downstream
         passband.
         When the data are not available because the measurement is not
         completed, not enabled or not supported, an empty string will be
         returned.
         The XDSL downstream passband is composed of one or more bands (maximum
         5, including VDSL optional band).
         HLIN has a range of approximately +6 dB to -90 dB, with a granularity
         of 2^-15. The Hlin is represented as
         HLINi = (scale/2^15)*((ai+j*bi)/2^15),
         with ai and bi 2 bytes signed integers in the range -32767 to 32767.
         The special value -32768 indicates that no measurement is available
         for the carrier or that the measurement is out of range.
         The scale factor is a 2 bytes unsigned integer. The scale factor
         must be chosen such that:
         max(|Ai|,|Bi|) over all i is equal to 2^15-1, i.e. over all carriers
         of the XDSL band(s) of the corresponding direction.

         The carrier HLINs are coded as a bitmap defined as follows:
         OCTETS 0,1: INTEGER, contains the number of symbols used to
         measure the data. The value is defined as MSB-LSB (big-endian).
         OCTETS 2,3: INTEGER(0..65535), contains the scale factor to apply to
         the hlin values over the downstream band(s).
         The value is defined as MSB-LSB (big-endian).
         OCTETS 4,5: INTEGER (0..4096), index of the start carrier group of the
         first downstream band. The value is defined as MSB-LSB (big-endian).
         OCTETS 6,7: INTEGER (0..4096), index of the stop carrier group of the
         first downstream band. The value is defined as MSB-LSB (big-endian).
         OCTETS 8,9: SIGNED INTEGER , contains the ai for the first carrier
         group of the band (start carrier group).
         The value is defined as MSB-LSB (big-endian).
         OCTETS 10,11: SIGNED INTEGER , contains the bi for the first carrier
         group of the band (start carrier group).
         The value is defined as MSB-LSB (big-endian).
         OCTETS 12..L: ai and bi for the next carrier group and so on until the
         last carrier group of the first downstream band (stop carrier group).
         OCTETS L+1..M: contain the start/stop carrier groups and the HLIN ai
         and bi of the second downstream band when available.
         OCTETS M+1..N: contain the start/stop carrier groups and the HLIN ai
         and bi of the third downstream band when available.
         OCTETS N+1..P: contain the start/stop carrier groups and the HLIN ai
         and bi of the fourth downstream band when available.
         OCTETS P+1..Q: contain the start/stop carrier groups and the HLIN ai
         and bi of the fifth downstream band when available.

         ALCATEL NOTE:
             ACCESS:   NA                  USAGE:    NA
             PERSIST:  NO                  INSRVMOD: NA
             RANGE:    0..8218             DEFVALUE: ''H
             UNITS:    octets              SPARSE:   NA
             DESCR:    NA "
::= {xdslFarEndLineCarrierDataEntry 6}

xdslFarEndLineCarrierHlogDownstream    OBJECT-TYPE
        SYNTAX          OCTET STRING
        ACCESS          read-only
        STATUS          mandatory
        DESCRIPTION     
        "This object provides the channel characteristics function real values
         in dB for each carrier group over the downstream passband.
         When the data are not available because the measurement is not
         completed, not enabled or not supported, an empty string will be
         returned.
         The XDSL downstream passband is composed of one or more bands (maximum
         5, including VDSL optional band).
         Hlog has a range of approximately +6 dB to - 96 dB in steps of
         0.1 dB. The Hlog is represented as HLOGi = 6 - mi/10,
         with mi a 10 bits unsigned integer in the range 0 to 1022.
         The special value 1023 indicates that no measurement is available for
         the carrier or that the measurement is out of range.

         The carrier HLOGs are coded as a bitmap defined as follows:
         OCTETS 0,1: INTEGER, contains the number of symbols used to
         measure the data. The value is defined as MSB-LSB (big-endian).
         OCTETS 2,3: INTEGER (0..4096), index of the start carrier group of the
         first downstream band. The value is defined as MSB-LSB (big-endian).
         OCTETS 4,5: INTEGER (0..4096), index of the stop carrier group of the
         first downstream band. The value is defined as MSB-LSB (big-endian).
         OCTETS 6,7: INTEGER (0..1023), contains the HLOG mi of the first
         carrier group of the band (start carrier group).
         The value is defined as MSB-LSB (big-endian).
         OCTETS 8..L: mi for the next carrier group and so on until the last
         carrier group of the first downstream band (stop carrier group).
         OCTETS L+1..M: contain the start/stop carrier groups and the HLOG mi
         of the second downstream band when available.
         OCTETS M+1..N: contain the start/stop carrier groups and the HLOG mi
         of the third downstream band when available.
         OCTETS N+1..P: contain the start/stop carrier groups and the HLOG mi
         of the fourth downstream band when available.
         OCTETS P+1..Q: contain the start/stop carrier groups and the HLOG mi
         of the fifth downstream band when available.

         ALCATEL NOTE:
             ACCESS:   NA                  USAGE:    NA
             PERSIST:  NO                  INSRVMOD: NA
             RANGE:    0..8216             DEFVALUE: ''H
             UNITS:    octets              SPARSE:   NA
             DESCR:    NA "
::= {xdslFarEndLineCarrierDataEntry 7}

xdslFarEndLineCarrierSpacingUpstream   OBJECT-TYPE
        SYNTAX          CarrierSpacingType
        ACCESS          read-only
        STATUS          mandatory
        DESCRIPTION     
        "This object provides the actual carrier spacing used on the XDSL line
         in the upstream direction:
          singleCarrierSpacing:  4.3125 kHz 
          doubleCarrierSpacing:  8.6250 kHz 
          halfCarrierSpacing:    2.15625 kHz 
          quarterCarrierSpacing: 1.078125 kHz

         ALCATEL NOTE:
             ACCESS:   NA                  USAGE:    NA
             PERSIST:  NO                  INSRVMOD: NA
             RANGE:    NA                  DEFVALUE: NA
             UNITS:    NA                  SPARSE:   NA
             DESCR:    NA "
::= {xdslFarEndLineCarrierDataEntry 8}

xdslFarEndLineCarrierTxPsdUpstream     OBJECT-TYPE
        SYNTAX          OCTET STRING
        ACCESS          read-only
        STATUS          mandatory
        DESCRIPTION
        "Provides the actual transmit PSD per carrier group over the
         upstream passband.
         When the modem is not in showtime this object will have the previously
         measured value.
         When the data are not available because the measurement is not
         completed, not enabled or not supported, an empty string will be
         returned.
         The XDSL upstream passband is composed of one or more bands (maximum
         5, including VDSL optional band). 
         The PSD has a range from -127 dBm/Hz to 0 dBm/Hz in steps of 0.5 dB.
         It is represented as PSDi = - psdi/2, with psdi an 8 bit
         unsigned integer in the range 0 to 254.
         The special value 255 indicates that no measurement is available for
         the carrier, the carrier is not loaded, or that the measurement is out
         of range.
         The carrier Tx PSD is coded as a bitmap defined as follows:
         OCTETS 0,1: INTEGER (0..4096), index of the start carrier group of the
         upstream band. The value is defined as MSB-LSB (big-endian).
         OCTETS 2,3: INTEGER (0..4096), index of the stop carrier group of the
         upstream band. The value is defined as MSB-LSB (big-endian).
         OCTET 4: INTEGER(0..255), PSD of the first carrier group of the band
         (start carrier group).
         OCTETS 5..L: and so on until the last carrier group of the first
         downstream band (stop carrier group).
         OCTETS L+1..M: contain the start/stop carrier groups and the carrier
         PSD of the second upstream band when available.
         OCTETS M+1..N: contain the start/stop carrier groups and the carrier
         PSD of the third upstream band when available.
         OCTETS N+1..P: contain the start/stop carrier groups and the carrier
         PSD of the fourth upstream band when available.
         OCTETS P+1..Q: contain the start/stop carrier groups and the carrier
         PSD of the fifth upstream band when available.

         ALCATEL NOTE:
             ACCESS:   NA                  USAGE:    NA
             PERSIST:  NO                  INSRVMOD: NA
             RANGE:    0..4117             DEFVALUE: ''H
             UNITS:    octets              SPARSE:   NA
             DESCR:    NA "
::= {xdslFarEndLineCarrierDataEntry 9}

xdslFarEndLineCarrierGroupTxPsd        OBJECT-TYPE
        SYNTAX          SubCarrierGroupSizeType
        ACCESS          read-only
        STATUS          mandatory
        DESCRIPTION
        "Provides the grouping factor for Actual Tx Power Spectrum Density
         carrier data octet-string.  The grouping factor represents the number
         of carriers that have been grouped together in view to reduce data 
         size.

         ALCATEL NOTE:
             ACCESS:   NA                  USAGE:    NA
             PERSIST:  NO                  INSRVMOD: NA
             RANGE:    1, 2, 4, 8          DEFVALUE: 1
             UNITS:    NA                  SPARSE:   NA
             DESCR:    NA "
::= {xdslFarEndLineCarrierDataEntry 10}

xdslFarEndLineCarrierGroupLoad         OBJECT-TYPE
        SYNTAX          SubCarrierGroupSizeType
        ACCESS          read-only
        STATUS          mandatory
        DESCRIPTION
        "Provides the grouping factor for carrier load data octet-
         string.  The grouping factor represents the number of carriers that
         have been grouped together in view to reduce data size.

         ALCATEL NOTE:
             ACCESS:   NA                  USAGE:    NA
             PERSIST:  NO                  INSRVMOD: NA
             RANGE:    1, 2, 4, 8          DEFVALUE: 1
             UNITS:    NA                  SPARSE:   NA
             DESCR:    NA "
::= {xdslFarEndLineCarrierDataEntry 11}

xdslFarEndLineCarrierGroupGain         OBJECT-TYPE
        SYNTAX          SubCarrierGroupSizeType
        ACCESS          read-only
        STATUS          mandatory
        DESCRIPTION
        "Provides the grouping factor for carrier gain allocation data octet-
         string.  The grouping factor represents the number of carriers that
         have been grouped together in view to reduce data size.

         ALCATEL NOTE:
             ACCESS:   NA                  USAGE:    NA
             PERSIST:  NO                  INSRVMOD: NA
             RANGE:    1, 2, 4, 8          DEFVALUE: 1
             UNITS:    NA                  SPARSE:   NA
             DESCR:    NA "
::= {xdslFarEndLineCarrierDataEntry 12}

xdslFarEndLineCarrierGroupTss                           OBJECT-TYPE
                SYNTAX                                  SubCarrierGroupSizeType
                ACCESS                                  read-only
                STATUS                                  mandatory
                DESCRIPTION
                "Provides the grouping factor for Transmit Spectrum Shaping carrier data
                 octet-string.  The grouping factor represents the number of carriers that
                 have been grouped together in view to reduce data size.
         ALCATEL NOTE:
             ACCESS:   NA                  USAGE:    NA
             PERSIST:  NA                  INSRVMOD: NA
             RANGE:    NA                  DEFVALUE: NA
             UNITS:    NA                  SPARSE:   NA
             DESCR:    This object is not supported. "
::= {xdslFarEndLineCarrierDataEntry 13}

xdslFarEndLineCarrierGroupSnr          OBJECT-TYPE
        SYNTAX          SubCarrierGroupSizeType
        ACCESS          read-only
        STATUS          mandatory
        DESCRIPTION
        "Provides the grouping factor for Signal to Noise Ratio per carrier
         data octet-string.  The grouping factor represents the number of 
         carriers that have been grouped together in view to reduce data size.

         ALCATEL NOTE:
             ACCESS:   NA                  USAGE:    NA
             PERSIST:  NO                  INSRVMOD: NA
             RANGE:    1, 2, 4, 8          DEFVALUE: 1
             UNITS:    NA                  SPARSE:   NA
             DESCR:    NA "
::= {xdslFarEndLineCarrierDataEntry 14}

xdslFarEndLineCarrierGroupQln          OBJECT-TYPE
        SYNTAX          SubCarrierGroupSizeType
        ACCESS          read-only
        STATUS          mandatory
        DESCRIPTION
        "Provides the grouping factor for Quiet Line Noise data octet-
         string.  The grouping factor represents the number of carriers that
         have been grouped together in view to reduce data size.

         ALCATEL NOTE:
             ACCESS:   NA                  USAGE:    NA
             PERSIST:  NO                  INSRVMOD: NA
             RANGE:    1, 2, 4, 8          DEFVALUE: 1
             UNITS:    NA                  SPARSE:   NA
             DESCR:    NA "
::= {xdslFarEndLineCarrierDataEntry 15}

xdslFarEndLineCarrierGroupHLin         OBJECT-TYPE
        SYNTAX          SubCarrierGroupSizeType
        ACCESS          read-only
        STATUS          mandatory
        DESCRIPTION
        "Provides the grouping factor for Complex Channel Characteristics data
         in linear scale.  The grouping factor represents the number of 
         carriers that have been grouped together in view to reduce data size.

         ALCATEL NOTE:
             ACCESS:   NA                  USAGE:    NA
             PERSIST:  NO                  INSRVMOD: NA
             RANGE:    1, 2, 4, 8          DEFVALUE: 1
             UNITS:    NA                  SPARSE:   NA
             DESCR:    NA "
::= {xdslFarEndLineCarrierDataEntry 16}

xdslFarEndLineCarrierGroupHLog         OBJECT-TYPE
        SYNTAX          SubCarrierGroupSizeType
        ACCESS          read-only
        STATUS          mandatory
        DESCRIPTION
        "Provides the grouping factor for Channel Characteristics data in dB.
         The grouping factor represents the number of carriers that
         have been grouped together in view to reduce data size.

         ALCATEL NOTE:
             ACCESS:   NA                  USAGE:    NA
             PERSIST:  NO                  INSRVMOD: NA
             RANGE:    1, 2, 4, 8          DEFVALUE: 1
             UNITS:    NA                  SPARSE:   NA
             DESCR:    NA "
::= {xdslFarEndLineCarrierDataEntry 17}

xdslFarEndLineFailureStatusTable       OBJECT-TYPE
        SYNTAX          SEQUENCE OF XdslFarEndLineFailureStatusEntry
        ACCESS          not-accessible
        STATUS          mandatory
        DESCRIPTION     
        "The xdsl far end line failure status table.

         ALCATEL NOTE:
             TABLESIZE: DEP [number of XDSL lines]                   
             DESCR:     NA                   "
::= {xdslFarEndLineCurrent 3}
        
xdslFarEndLineFailureStatusEntry       OBJECT-TYPE
        SYNTAX          XdslFarEndLineFailureStatusEntry                        
        ACCESS          not-accessible
        STATUS          mandatory
        DESCRIPTION     
        "An entry in the xdsl line far end failure status table.

         Row creation : Entries for all XDSL lines belonging to a board are 
                        created when the board becomes operational.
         Row deletion : Entries for all XDSL lines belonging to a board are 
                        deleted when the board becomes unavailable. "
        INDEX          {ifIndex}
::= {xdslFarEndLineFailureStatusTable 1}
        
XdslFarEndLineFailureStatusEntry ::=
        SEQUENCE {
                xdslFarEndLineFailureStatus             INTEGER
        }

xdslFarEndLineFailureStatus            OBJECT-TYPE
        SYNTAX          INTEGER (1..65535)
        ACCESS          read-only
        STATUS          mandatory
        DESCRIPTION 
        "This variable indicates the status of the far end interface. It is
         a bitmap represented as a sum, therefore, it can represent multiple
         failure simultaneuosly. The xdslFarEndLineNoDefect should be set if
         and only if no other flag is set. The various bit positions are:
             1      xdslFarEndLineNoDefect
             2      xdslFarEndLineLOS (loss of signal) in the downstream 
                    direction
             4      xdslFarEndLineLOF (loss of frame) in the downstream
                    direction 
             8      xdslFarEndLineLOM (loss of margin) in the downstream
                    direction 
            16      xdslFarEndLineLPR (loss of power) of the XTU-R
            32      xdslFarEndLineLOL (loss of link)
            64      xdslFarEndLineESE (Excessive severe errors)
           128      xdslFarEndLineActivationFailure due to communication
                    problems  
           256      xdslFarEndLineActivationFailure due to no XTU-R detected
    512 ..2048      reserved
          4096      xdslFarEndLineBitrateThreshold for the downstream
                    direction.
          8192      xdslFarEndLineUpboViolation
         16384      xdslFarEndLineActivationFailure due to CPE Policing
                    (Modem stays in L3 Idle mode)

         ALCATEL NOTE:
             ACCESS:   NA                  USAGE:    NA
             PERSIST:  NO                  INSRVMOD: NA
             RANGE:    NA                  DEFVALUE: 1
             UNITS:    NA                  SPARSE:   NA
             DESCR:    NA "
::= {xdslFarEndLineFailureStatusEntry 1}

xdslFarEndLineCurrentIntervalTable     OBJECT-TYPE
        SYNTAX          SEQUENCE OF XdslFarEndLineCurrentIntervalEntry
        ACCESS          not-accessible
        STATUS          mandatory
        DESCRIPTION 
        "The xdsl far end line current interval table.

         ALCATEL NOTE:
             TABLESIZE: DEP [number of XDSL lines]                    
             DESCR:     NA                   "
::= {xdslFarEndLineCurrent 4}
        
xdslFarEndLineCurrentIntervalEntry     OBJECT-TYPE
        SYNTAX          XdslFarEndLineCurrentIntervalEntry                      
        ACCESS          not-accessible
        STATUS          mandatory
        DESCRIPTION     
        "An entry in the xdsl far end line current interval table.

         Row creation : Entries for all XDSL lines belonging to a board are 
                        created when the board becomes operational.
         Row deletion : Entries for all XDSL lines belonging to a board are 
                        deleted when the board becomes unavailable. "
        INDEX          {ifIndex}
::= {xdslFarEndLineCurrentIntervalTable 1}

XdslFarEndLineCurrentIntervalEntry ::=
        SEQUENCE {
            xdslFarEndLineCurrentIntervalLOSCounter      Counter,
            xdslFarEndLineCurrentIntervalLOFCounter      Counter,
            xdslFarEndLineCurrentIntervalLOMCounter      Counter,
            xdslFarEndLineCurrentIntervalLPRCounter      Counter,
            xdslFarEndLineCurrentIntervalLOLCounter      Counter,
            xdslFarEndLineCurrentIntervalESECounter      Counter,
            xdslFarEndLineCurrentIntervalESCounter       Counter,
            xdslFarEndLineCurrentIntervalSESCounter      Counter,
            xdslFarEndLineCurrentIntervalUASCounter      Counter,
            xdslFarEndLineCurrentIntervalMeasuredTime    INTEGER,        
            xdslFarEndLineCurrentIntervalInvalidDataFlag INTEGER,
            xdslFarEndLineCurrentIntervalRAUCounter      Counter,
            xdslFarEndLineCurrentIntervalRADCounter      Counter,
            xdslFarEndLineCurrentIntervalLEFTRSCounter          Counter,
            xdslFarEndLineCurrentIntervalErrFreeBitsCounter     Counter,
            xdslFarEndLineCurrentIntervalMinEFTRValue           INTEGER
        }        

xdslFarEndLineCurrentIntervalLOSCounter          OBJECT-TYPE
        SYNTAX          Counter
        ACCESS          read-only
        STATUS          mandatory
        DESCRIPTION     
        "This object represents for the current 15 minute interval the LOS 
         failure count, which is the number of occurences of an LOS failure 
         event, where a failure event occurs when the failure is declared and 
         ends when the failure clears.

         ALCATEL NOTE:
             ACCESS:   NA                  USAGE:    NA
             PERSIST:  NO                  INSRVMOD: NA
             RANGE:    NA                  DEFVALUE: 0
             UNITS:    NA                  SPARSE:   NA
             DESCR:    NA "
::= {xdslFarEndLineCurrentIntervalEntry 1}

xdslFarEndLineCurrentIntervalLOFCounter          OBJECT-TYPE
        SYNTAX          Counter
        ACCESS          read-only
        STATUS          mandatory
        DESCRIPTION     
        "This object represents for the current 15 minute interval the LOF 
         failure count, which is the number of occurences of an LOF failure 
         event, where a failure event occurs when the failure is declared and 
         ends when the failure clears.

         ALCATEL NOTE:
             ACCESS:   NA                  USAGE:    NA
             PERSIST:  NO                  INSRVMOD: NA
             RANGE:    NA                  DEFVALUE: 0
             UNITS:    NA                  SPARSE:   NA
             DESCR:    NA "
::= {xdslFarEndLineCurrentIntervalEntry 2}

xdslFarEndLineCurrentIntervalLOMCounter          OBJECT-TYPE
        SYNTAX          Counter
        ACCESS          read-only
        STATUS          mandatory
        DESCRIPTION     
        "This object represents for the current 15 minute interval the LOM 
         failure count, which is the number of occurences of an LOM failure 
         event, where a failure event occurs when the failure is declared and 
         ends when the failure clears.

         ALCATEL NOTE:
             ACCESS:   NA                  USAGE:    NA
             PERSIST:  NO                  INSRVMOD: NA
             RANGE:    NA                  DEFVALUE: 0
             UNITS:    NA                  SPARSE:   NA
             DESCR:    NA "
::= {xdslFarEndLineCurrentIntervalEntry 3}

xdslFarEndLineCurrentIntervalLPRCounter          OBJECT-TYPE
        SYNTAX          Counter
        ACCESS          read-only
        STATUS          mandatory
        DESCRIPTION     
        "This object represents for the current 15 minute interval the LPR 
         failure count, which is the number of occurences of an LPR failure 
         event, where a failure event occurs when the failure is declared and 
         ends when the failure  clears.

         ALCATEL NOTE:
             ACCESS:   NA                  USAGE:    NA
             PERSIST:  NO                  INSRVMOD: NA
             RANGE:    NA                  DEFVALUE: 0
             UNITS:    NA                  SPARSE:   NA
             DESCR:    NA "
::= {xdslFarEndLineCurrentIntervalEntry 4}

xdslFarEndLineCurrentIntervalLOLCounter          OBJECT-TYPE
        SYNTAX          Counter
        ACCESS          read-only
        STATUS          mandatory
        DESCRIPTION     
        "This object represents for the current 15 minute interval the LOL 
         failure count, which is the number of occurences of an LOL failure 
         event, where a failure event occurs when the failure is declared and 
         ends when the failure clears.

         ALCATEL NOTE:
             ACCESS:   NA                  USAGE:    NA
             PERSIST:  NO                  INSRVMOD: NA
             RANGE:    0                   DEFVALUE: 0
             UNITS:    NA                  SPARSE:   NA
             DESCR:    Because an LOL failure event never occurs, the value of
                       the counter is always 0. "
::= {xdslFarEndLineCurrentIntervalEntry 5}

xdslFarEndLineCurrentIntervalESECounter          OBJECT-TYPE
        SYNTAX          Counter
        ACCESS          read-only
        STATUS          mandatory
        DESCRIPTION     
        "This object represents for the current 15 minute interval the ESE 
         failure count, which is the number of occurences of an ESE failure 
         event, where a failure event occurs when the failure is declared and 
         ends when the failure clears.

         ALCATEL NOTE:
             ACCESS:   NA                  USAGE:    NA
             PERSIST:  NO                  INSRVMOD: NA
             RANGE:    NA                  DEFVALUE: 0
             UNITS:    NA                  SPARSE:   NA
             DESCR:    NA "
::= {xdslFarEndLineCurrentIntervalEntry 6}

xdslFarEndLineCurrentIntervalESCounter OBJECT-TYPE
        SYNTAX          Counter
        ACCESS          read-only
        STATUS          mandatory
        DESCRIPTION     
        "The counter associated with the number of Errored Seconds encountered 
         by the line in the current 15 min interval.

         ALCATEL NOTE:
             ACCESS:   NA                  USAGE:    NA
             PERSIST:  NO                  INSRVMOD: NA
             RANGE:    NA                  DEFVALUE: 0
             UNITS:    NA                  SPARSE:   NA
             DESCR:    NA "
::= {xdslFarEndLineCurrentIntervalEntry 7}

xdslFarEndLineCurrentIntervalSESCounter          OBJECT-TYPE
        SYNTAX          Counter
        ACCESS          read-only
        STATUS          mandatory
        DESCRIPTION     
        "The counter associated with the number of Severely Errored Seconds
         encountered by the line in the current 15 min interval.

         ALCATEL NOTE:
             ACCESS:   NA                  USAGE:    NA
             PERSIST:  NO                  INSRVMOD: NA
             RANGE:    NA                  DEFVALUE: 0
             UNITS:    NA                  SPARSE:   NA
             DESCR:    NA "
::= {xdslFarEndLineCurrentIntervalEntry 8}

xdslFarEndLineCurrentIntervalUASCounter          OBJECT-TYPE
        SYNTAX          Counter
        ACCESS          read-only
        STATUS          mandatory
        DESCRIPTION     
        "The counter associated with the number of Unavailable Seconds
         encountered by the line in the current 15 min interval.

         ALCATEL NOTE:
             ACCESS:   NA                  USAGE:    NA
             PERSIST:  NO                  INSRVMOD: NA
             RANGE:    NA                  DEFVALUE: 0
             UNITS:    NA                  SPARSE:   NA
             DESCR:    NA "
::= {xdslFarEndLineCurrentIntervalEntry 9}

xdslFarEndLineCurrentIntervalMeasuredTime        OBJECT-TYPE
        SYNTAX          INTEGER(0..900)
        ACCESS          read-only
        STATUS          mandatory
        DESCRIPTION     
        "The amount of time, measured in seconds, that statistics for this 
         entry have been counted.

         ALCATEL NOTE:
             ACCESS:   NA                  USAGE:    NA
             PERSIST:  NO                  INSRVMOD: NA
             RANGE:    NA                  DEFVALUE: 0
             UNITS:    seconds             SPARSE:   NA
             DESCR:    NA "
::= {xdslFarEndLineCurrentIntervalEntry 10}

xdslFarEndLineCurrentIntervalInvalidDataFlag     OBJECT-TYPE
        SYNTAX          INTEGER
        ACCESS          read-only
        STATUS          mandatory
        DESCRIPTION     
        "This object indicates the validity of the corresponding PM data.
         It is set to 1 when the PM data is incomplete or invalid and set to 0
         when the PM data is complete and valid.

         ALCATEL NOTE:
             ACCESS:   NA                  USAGE:    NA
             PERSIST:  NO                  INSRVMOD: NA
             RANGE:    0..1                DEFVALUE: 1
             UNITS:    NA                  SPARSE:   NA
             DESCR:    NA "
::= {xdslFarEndLineCurrentIntervalEntry 11}

xdslFarEndLineCurrentIntervalRAUCounter          OBJECT-TYPE
        SYNTAX          Counter
        ACCESS          read-only
        STATUS          mandatory
        DESCRIPTION     
        "This object represents for the current 15 minute interval the RAU 
         anomaly count, which is the number of occurences of an Upshift Rate
         Adaptation.

         ALCATEL NOTE:
             ACCESS:   NA                  USAGE:    NA
             PERSIST:  NO                  INSRVMOD: NA
             RANGE:    NA                  DEFVALUE: 0
             UNITS:    NA                  SPARSE:   NA
             DESCR:    NA "
::= {xdslFarEndLineCurrentIntervalEntry 12}

xdslFarEndLineCurrentIntervalRADCounter          OBJECT-TYPE
        SYNTAX          Counter
        ACCESS          read-only
        STATUS          mandatory
        DESCRIPTION     
        "This object represents for the current 15 minute interval the RAD 
         anomaly count, which is the number of occurences of a Downshift Rate
         Adaptation.

         ALCATEL NOTE:
             ACCESS:   NA                  USAGE:    NA
             PERSIST:  NO                  INSRVMOD: NA
             RANGE:    NA                  DEFVALUE: 0
             UNITS:    NA                  SPARSE:   NA
             DESCR:    NA "
::= {xdslFarEndLineCurrentIntervalEntry 13}

xdslFarEndLineCurrentIntervalLEFTRSCounter      OBJECT-TYPE
        SYNTAX          Counter
        ACCESS          read-only
        STATUS          mandatory
        DESCRIPTION     
        "When RTX is in use then this counter associates with the number of
         LEFTR seconds encountered by the line in the current 15 minute interval.
         Otherwise the default value will be returned.

         ALCATEL NOTE:
             ACCESS:   NA                  USAGE:    NA
             PERSIST:  NO                  INSRVMOD: NA
             RANGE:    NA                  DEFVALUE: 0
             UNITS:    NA                  SPARSE:   NA
             DESCR:    NA "
::= { xdslFarEndLineCurrentIntervalEntry 14}

xdslFarEndLineCurrentIntervalErrFreeBitsCounter      OBJECT-TYPE
        SYNTAX          Counter
        ACCESS          read-only
        STATUS          mandatory
        DESCRIPTION     
        " When RTX is in use then this counter represents for the current 
         15 minute interval the count of the number of error-free bits divided 
         by 2^16.
         Otherwise the default value will be returned.

         ALCATEL NOTE:
             ACCESS:   NA                  USAGE:    NA
             PERSIST:  NO                  INSRVMOD: NA
             RANGE:    NA                  DEFVALUE: 0
             UNITS:    NA                  SPARSE:   NA
             DESCR:    NA "
::= { xdslFarEndLineCurrentIntervalEntry 15}

xdslFarEndLineCurrentIntervalMinEFTRValue      OBJECT-TYPE
        SYNTAX          INTEGER
        ACCESS          read-only
        STATUS          mandatory
        DESCRIPTION     
        " When RTX is in use then this counter represents for the current 
         15 minute interval the count of the Minimum of the EFTR observed
         during this interval.
         Otherwise the default value will be returned.

         ALCATEL NOTE:
             ACCESS:   NA                  USAGE:    NA
             PERSIST:  NO                  INSRVMOD: NA
             RANGE:    NA                  DEFVALUE: 0
             UNITS:    NA                  SPARSE:   NA
             DESCR:    NA "
::= { xdslFarEndLineCurrentIntervalEntry 16}

xdslFarEndLineCurrent1DayTable         OBJECT-TYPE
        SYNTAX          SEQUENCE OF XdslFarEndLineCurrent1DayEntry
        ACCESS          not-accessible
        STATUS          mandatory
        DESCRIPTION     
        "The xdsl line far end current 1 day table.

         ALCATEL NOTE:
             TABLESIZE: DEP [number of XDSL lines]                    
             DESCR:     NA                   "
::= {xdslFarEndLineCurrent 5}
        
xdslFarEndLineCurrent1DayEntry         OBJECT-TYPE
        SYNTAX          XdslFarEndLineCurrent1DayEntry                  
        ACCESS          not-accessible
        STATUS          mandatory
        DESCRIPTION     
        "An entry in the xdsl line far end current 1 day table.

         Row creation : Entries for all XDSL lines belonging to a board are 
                        created when the board becomes operational.
         Row deletion : Entries for all XDSL lines belonging to a board are 
                        deleted when the board becomes unavailable. "
        INDEX          {ifIndex}
::= {xdslFarEndLineCurrent1DayTable 1}

XdslFarEndLineCurrent1DayEntry ::=
        SEQUENCE {
            xdslFarEndLineCurrent1DayLOSCounter       Counter,
            xdslFarEndLineCurrent1DayLOFCounter       Counter,
            xdslFarEndLineCurrent1DayLOMCounter       Counter,
            xdslFarEndLineCurrent1DayLPRCounter       Counter,
            xdslFarEndLineCurrent1DayLOLCounter       Counter,
            xdslFarEndLineCurrent1DayESECounter       Counter,
            xdslFarEndLineCurrent1DayESCounter        Counter,
            xdslFarEndLineCurrent1DaySESCounter       Counter,
            xdslFarEndLineCurrent1DayUASCounter       Counter,
            xdslFarEndLineCurrent1DayMeasuredTime     INTEGER,
            xdslFarEndLineCurrent1DayInvalidDataFlag  INTEGER,
            xdslFarEndLineCurrent1DayRAUCounter       Counter,
            xdslFarEndLineCurrent1DayRADCounter       Counter,
            xdslFarEndLineCurrent1DayLEFTRSCounter          Counter,
            xdslFarEndLineCurrent1DayErrFreeBitsCounter     Counter,
            xdslFarEndLineCurrent1DayMinEFTRValue           INTEGER
        }

xdslFarEndLineCurrent1DayLOSCounter    OBJECT-TYPE
        SYNTAX          Counter
        ACCESS          read-only
        STATUS          mandatory
        DESCRIPTION     
        "This object represents for the current 1 day interval the LOS failure 
         count, which is the number of occurences of an LOS failure event,
         where a failure event occurs when the failure is declared and ends
         when the failure clears.

         ALCATEL NOTE:
             ACCESS:   NA                  USAGE:    NA
             PERSIST:  NO                  INSRVMOD: NA
             RANGE:    NA                  DEFVALUE: 0
             UNITS:    NA                  SPARSE:   NA
             DESCR:    NA "
::= {xdslFarEndLineCurrent1DayEntry 1}

xdslFarEndLineCurrent1DayLOFCounter    OBJECT-TYPE
        SYNTAX          Counter
        ACCESS          read-only
        STATUS          mandatory
        DESCRIPTION     
        "This object represents for the current 1 day interval the LOF failure 
         count, which is the number of occurences of an LOF failure event, 
         where a failure event occurs when the failure is declared and ends
         when the failure clears.

         ALCATEL NOTE:
             ACCESS:   NA                  USAGE:    NA
             PERSIST:  NO                  INSRVMOD: NA
             RANGE:    NA                  DEFVALUE: 0
             UNITS:    NA                  SPARSE:   NA
             DESCR:    NA "
::= {xdslFarEndLineCurrent1DayEntry 2}

xdslFarEndLineCurrent1DayLOMCounter    OBJECT-TYPE
        SYNTAX          Counter
        ACCESS          read-only
        STATUS          mandatory
        DESCRIPTION     
        "This object represents for the current 1 day interval the LOM failure 
         count, which is the number of occurences of an LOM failure event, 
         where a failure event occurs when the failure is declared and ends
         when the failure clears.

         ALCATEL NOTE:
             ACCESS:   NA                  USAGE:    NA
             PERSIST:  NO                  INSRVMOD: NA
             RANGE:    NA                  DEFVALUE: 0
             UNITS:    NA                  SPARSE:   NA
             DESCR:    NA "
::= {xdslFarEndLineCurrent1DayEntry 3}

xdslFarEndLineCurrent1DayLPRCounter    OBJECT-TYPE
        SYNTAX          Counter
        ACCESS          read-only
        STATUS          mandatory
        DESCRIPTION     
        "This object represents for the current 1 day interval the LPR failure 
         count, which is the number of occurences of an LPR failure event,
         where a failure event occurs when the failure is declared and ends
         when the failure clears.

         ALCATEL NOTE:
             ACCESS:   NA                  USAGE:    NA
             PERSIST:  NO                  INSRVMOD: NA
             RANGE:    NA                  DEFVALUE: 0
             UNITS:    NA                  SPARSE:   NA
             DESCR:    NA "
::= {xdslFarEndLineCurrent1DayEntry 4}

xdslFarEndLineCurrent1DayLOLCounter    OBJECT-TYPE
        SYNTAX          Counter
        ACCESS          read-only
        STATUS          mandatory
        DESCRIPTION     
        "This object represents for the current 1 day interval the LOL failure 
         count, which is the number of occurences of an LOL failure event, 
         where a failure event occurs when the failure is declared and ends 
         when the failure clears.

         ALCATEL NOTE:
             ACCESS:   NA                  USAGE:    NA
             PERSIST:  NO                  INSRVMOD: NA
             RANGE:    0                   DEFVALUE: 0
             UNITS:    NA                  SPARSE:   NA
             DESCR:    Because an LOL failure event never occurs, the value of
                       the counter is always 0. "
::= {xdslFarEndLineCurrent1DayEntry 5}

xdslFarEndLineCurrent1DayESECounter    OBJECT-TYPE
        SYNTAX          Counter
        ACCESS          read-only
        STATUS          mandatory
        DESCRIPTION     
        "This object represents for the current 1 day interval the ESE failure 
         count, which is the number of occurences of an ESE failure event, 
         where a failure event occurs when the failure is declared and ends 
         when the failure clears.

         ALCATEL NOTE:
             ACCESS:   NA                  USAGE:    NA
             PERSIST:  NO                  INSRVMOD: NA
             RANGE:    NA                  DEFVALUE: 0
             UNITS:    NA                  SPARSE:   NA
             DESCR:    NA "
::= {xdslFarEndLineCurrent1DayEntry 6}

xdslFarEndLineCurrent1DayESCounter    OBJECT-TYPE
        SYNTAX          Counter
        ACCESS          read-only
        STATUS          mandatory
        DESCRIPTION     
        "The counter associated with the number of Errored Seconds encountered 
         by the line in the current 1 Day interval.

         ALCATEL NOTE:
             ACCESS:   NA                  USAGE:    NA
             PERSIST:  NO                  INSRVMOD: NA
             RANGE:    NA                  DEFVALUE: 0
             UNITS:    NA                  SPARSE:   NA
             DESCR:    NA "
::= {xdslFarEndLineCurrent1DayEntry 7}

xdslFarEndLineCurrent1DaySESCounter    OBJECT-TYPE
        SYNTAX          Counter
        ACCESS          read-only
        STATUS          mandatory
        DESCRIPTION     
        "The counter associated with the number of Severely Errored Seconds
         encountered by the line in the current 1 Day interval.

         ALCATEL NOTE:
             ACCESS:   NA                  USAGE:    NA
             PERSIST:  NO                  INSRVMOD: NA
             RANGE:    NA                  DEFVALUE: 0
             UNITS:    NA                  SPARSE:   NA
             DESCR:    NA "
::= {xdslFarEndLineCurrent1DayEntry 8}

xdslFarEndLineCurrent1DayUASCounter    OBJECT-TYPE
        SYNTAX          Counter
        ACCESS          read-only
        STATUS          mandatory
        DESCRIPTION     
        "The counter associated with the number of Unavailable Seconds
         encountered by the line in the current 1 Day interval.

         ALCATEL NOTE:
             ACCESS:   NA                  USAGE:    NA
             PERSIST:  NO                  INSRVMOD: NA
             RANGE:    NA                  DEFVALUE: 0
             UNITS:    NA                  SPARSE:   NA
             DESCR:    NA "
::= {xdslFarEndLineCurrent1DayEntry 9}

xdslFarEndLineCurrent1DayMeasuredTime  OBJECT-TYPE
        SYNTAX          INTEGER(0..86400)
        ACCESS          read-only
        STATUS          mandatory
        DESCRIPTION     
        "The amount of time, measured in seconds, that statistics for this
         entry have been counted.

         ALCATEL NOTE:
             ACCESS:   NA                  USAGE:    NA
             PERSIST:  NO                  INSRVMOD: NA
             RANGE:    NA                  DEFVALUE: 0
             UNITS:    seconds             SPARSE:   NA
             DESCR:    NA "
::= {xdslFarEndLineCurrent1DayEntry 10}

xdslFarEndLineCurrent1DayInvalidDataFlag         OBJECT-TYPE
        SYNTAX          INTEGER
        ACCESS          read-only
        STATUS          mandatory
        DESCRIPTION     
        "This object indicates the validity of the corresponding PM data.
         It is set to 1 when the PM data is incomplete or invalid and set to 0
         when the PM data is complete and valid.

         ALCATEL NOTE:
             ACCESS:   NA                  USAGE:    NA
             PERSIST:  NO                  INSRVMOD: NA
             RANGE:    0..1                DEFVALUE: 0
             UNITS:    NA                  SPARSE:   NA
             DESCR:    NA "
::= {xdslFarEndLineCurrent1DayEntry 11}

xdslFarEndLineCurrent1DayRAUCounter    OBJECT-TYPE
        SYNTAX          Counter
        ACCESS          read-only
        STATUS          mandatory
        DESCRIPTION     
        "This object represents for the current 1 day interval the RAU anomaly 
         count, which is the number of occurences of an Upshift Rate 
         Adaptation.

         ALCATEL NOTE:
             ACCESS:   NA                  USAGE:    NA
             PERSIST:  NO                  INSRVMOD: NA
             RANGE:    NA                  DEFVALUE: 1
             UNITS:    NA                  SPARSE:   NA
             DESCR:    NA "
::= {xdslFarEndLineCurrent1DayEntry 12}

xdslFarEndLineCurrent1DayRADCounter    OBJECT-TYPE
        SYNTAX          Counter
        ACCESS          read-only
        STATUS          mandatory
        DESCRIPTION     
        "This object represents for the current 1 day interval the RAD anomaly 
         count, which is the number of occurences of a Downshift Rate 
         Adaptation.

         ALCATEL NOTE:
             ACCESS:   NA                  USAGE:    NA
             PERSIST:  NO                  INSRVMOD: NA
             RANGE:    NA                  DEFVALUE: 0
             UNITS:    NA                  SPARSE:   NA
             DESCR:    NA "
::= {xdslFarEndLineCurrent1DayEntry 13}

xdslFarEndLineCurrent1DayLEFTRSCounter      OBJECT-TYPE
        SYNTAX          Counter
        ACCESS          read-only
        STATUS          mandatory
        DESCRIPTION     
        "When RTX is in use then this counter associates with the number of
         LEFTR seconds encountered by the line in the current 1 day interval.
         Otherwise the default value will be returned.

         ALCATEL NOTE:
             ACCESS:   NA                  USAGE:    NA
             PERSIST:  NO                  INSRVMOD: NA
             RANGE:    NA                  DEFVALUE: 0
             UNITS:    NA                  SPARSE:   NA
             DESCR:    NA "
::= { xdslFarEndLineCurrent1DayEntry 14}

xdslFarEndLineCurrent1DayErrFreeBitsCounter      OBJECT-TYPE
        SYNTAX          Counter
        ACCESS          read-only
        STATUS          mandatory
        DESCRIPTION     
        "When RTX is in use then this counter represents for the current 
         1 day interval the count of the number of error-free bits divided 
         by 2^16.
         Otherwise the default value will be returned.

         ALCATEL NOTE:
             ACCESS:   NA                  USAGE:    NA
             PERSIST:  NO                  INSRVMOD: NA
             RANGE:    NA                  DEFVALUE: 0
             UNITS:    NA                  SPARSE:   NA
             DESCR:    NA "
::= { xdslFarEndLineCurrent1DayEntry 15}

xdslFarEndLineCurrent1DayMinEFTRValue      OBJECT-TYPE
        SYNTAX          INTEGER
        ACCESS          read-only
        STATUS          mandatory
        DESCRIPTION     
        "When RTX is in use then this counter represents for the current 
         1 day interval the count of the Minimum of the EFTR observed
         during this interval.
         Otherwise the default value will be returned.

         ALCATEL NOTE:
             ACCESS:   NA                  USAGE:    NA
             PERSIST:  NO                  INSRVMOD: NA
             RANGE:    NA                  DEFVALUE: 0
             UNITS:    NA                  SPARSE:   NA
             DESCR:    NA "
::= { xdslFarEndLineCurrent1DayEntry 16}

xdslFarEndLineInsOperDataTable       OBJECT-TYPE
        SYNTAX          SEQUENCE OF XdslFarEndLineInsOperDataEntry
        ACCESS          not-accessible
        STATUS          mandatory
        DESCRIPTION     
        " The xdsl far end line impulse noise sensor operational data table.

         ALCATEL NOTE:
             TABLESIZE: DEP [number of XDSL lines]                    
             DESCR:     NA                   "
::= {xdslFarEndLineCurrent 6}

xdslFarEndLineInsOperDataEntry       OBJECT-TYPE
        SYNTAX          XdslFarEndLineInsOperDataEntry
        ACCESS          not-accessible
        STATUS          mandatory
        DESCRIPTION     
        "An entry in the xdsl far end line impulse noise sensor operational
         data table.

         Row creation : Entries for all XDSL lines belonging to a board are 
                        created by the system when the board is planned.
         Row deletion : Entries for all XDSL lines belonging to a board are 
                        deleted by the system when the board is unplanned. "
        INDEX          {ifIndex}
::= {xdslFarEndLineInsOperDataTable 1}

XdslFarEndLineInsOperDataEntry ::=
        SEQUENCE {
            xdslFarEndLineInsActualSensitivity                  INTEGER,
            xdslFarEndLineInmActualEquivInpMode                 INTEGER
        }
        
xdslFarEndLineInsActualSensitivity              OBJECT-TYPE
        SYNTAX          INTEGER
        ACCESS          read-only
        STATUS          mandatory
        DESCRIPTION     
        " This object represents the Impulse Noise Sensor sensitivity actually
         applied by the modem. The value can be different from the configured
         Impulse Noise Sensitivity depending on the current noise conditions
         on the line and modem capability.
         Range: -12.8 dB to 12.7 dB with 0.1 dB steps.
         The Actual Sensitivity is represented as
         1/10 * xdslLineInsActualSensitivity.

         ALCATEL NOTE:
             ACCESS:   NA                  USAGE:    NA
             PERSIST:  NO                  INSRVMOD: NA
             RANGE:    -128 .. 127         DEFVALUE: 0
             UNITS:    dB / 10             SPARSE:   NA
             DESCR:    NA "
::= {xdslFarEndLineInsOperDataEntry 1}

xdslFarEndLineInmActualEquivInpMode                   OBJECT-TYPE
        SYNTAX          INTEGER
        ACCESS          read-only
        STATUS          mandatory
        DESCRIPTION     
        " This object represents the actual Impulse Noise Monitoring Equivalent
         INP Mode applied by the modem. The value will be different from the
         configured INM Equivalent INP Mode if the modem is using a fallback
         mode because the configured mode is not supported, or if INM is not
         supported.
         Range: 0 to 3 plus special value 255.
         Special value 255 indicates that INM is not supported.

         ALCATEL NOTE:
             ACCESS:   NA                  USAGE:    NA
             PERSIST:  NO                  INSRVMOD: NA
             RANGE:    0..3, 255           DEFVALUE: 0
             UNITS:    NA                  SPARSE:   NA
             DESCR:    NA "
::= {xdslFarEndLineInsOperDataEntry 2}

xdslFarEndLineInmCurrentIntervalTable       OBJECT-TYPE
        SYNTAX          SEQUENCE OF XdslFarEndLineInmCurrentIntervalEntry
        ACCESS          not-accessible
        STATUS          mandatory
        DESCRIPTION     
        " The xdsl far end line Impulse noise Monitoring near end current
         15 minute interval table.

         ALCATEL NOTE:
             TABLESIZE: DEP [number of XDSL lines]                    
             DESCR:     NA                   "
::= {xdslFarEndLineCurrent 7}

xdslFarEndLineInmCurrentIntervalEntry       OBJECT-TYPE
        SYNTAX          XdslFarEndLineInmCurrentIntervalEntry
        ACCESS          not-accessible
        STATUS          mandatory
        DESCRIPTION     
        " An entry in the xdsl far end line Impulse Noise Monitoring current
         15 minute interval table.

         Row creation : Entries for all XDSL lines belonging to a board are 
                        created by the system when the board is planned.
         Row deletion : Entries for all XDSL lines belonging to a board are 
                        deleted by the system when the board is unplanned. "
        INDEX          {ifIndex}
::= {xdslFarEndLineInmCurrentIntervalTable 1}

XdslFarEndLineInmCurrentIntervalEntry ::=
        SEQUENCE {
            xdslFarEndLineInmCurrentIntervalIatHistogram            IatHistogramType,
            xdslFarEndLineInmCurrentIntervalEquivInpHistogram  EquivInpHistogramType,
            xdslFarEndLineInmCurrentIntervalTotalDataSymbolCounter  Counter
        }
        
xdslFarEndLineInmCurrentIntervalIatHistogram              OBJECT-TYPE
        SYNTAX          IatHistogramType
        ACCESS          read-only
        STATUS          mandatory
        DESCRIPTION     
        "This object represents the Impulse Noise Monitoring Inter-Arrival Time
         histogram for the current 15 minute interval. The histogram consists
         of eight saturating counters representing the different class
         intervals configured.
         The Inter-Arrival Time is defined as the time between the start of two
         consecutive impulses, expressed as an number of data symbols.
         The class intervals width and offset are defined by
         xdslLineInmInterArrivalTimeStep and xdslLineInmInterArrivalTimeOffset.
         The Inter-Arrival Time histogram is coded as a fixed length
         octet string defined as follows:
         OCTETS 0..1: INTEGER (0..65535), value of the first class interval.
         The value is defined as MSB-LSB (big-endian).
         OCTETS 2..3: define the value of class interval 2.
         ....        up to
         OCTETS 14..15: define the last class interval 8.

         ALCATEL NOTE:
             ACCESS:   NA                  USAGE:    NA
             PERSIST:  NO                  INSRVMOD: NA
             RANGE:    NA                  DEFVALUE: '00000000000000000000000000000000'H
             UNITS:    octets              SPARSE:   NA
             DESCR:    NA "
::= {xdslFarEndLineInmCurrentIntervalEntry 1}

xdslFarEndLineInmCurrentIntervalEquivInpHistogram              OBJECT-TYPE
        SYNTAX          EquivInpHistogramType
        ACCESS          read-only
        STATUS          mandatory
        DESCRIPTION     
        "This object represents the Impulse Noise Monitoring Equivalent INP
         histogram for the current 15 minute interval. The histogram consists
         of seventeen saturating counters representing the different class
         intervals.
         Class intervals 1 to 16 contain the number of impulse noise events
         detected per equivalent level of INP as defined by
         xdslLineEquivInpMode. Class interval 17 contains the number of impulse
         noise events detected with equivalent level of INP greater than 16.
         The equivalent INP histogram is coded as a fixed length
         octet string defined as follows:
         OCTETS 0..1: INTEGER (0..65535), value of the first class interval.
         The value is defined as MSB-LSB (big-endian).
         OCTETS 2..3: define the value of class interval 2.
         ....        up to
         OCTETS 32..33: define the last class interval 17.

         ALCATEL NOTE:
             ACCESS:   NA                  USAGE:    NA
             PERSIST:  NO                  INSRVMOD: NA
             RANGE:    NA                  DEFVALUE: '00000000000000000000000000000000000000000000000000000000000000000000'H
             UNITS:    octets              SPARSE:   NA
             DESCR:    NA "
::= {xdslFarEndLineInmCurrentIntervalEntry 2}

xdslFarEndLineInmCurrentIntervalTotalDataSymbolCounter   OBJECT-TYPE
        SYNTAX          Counter
        ACCESS          read-only
        STATUS          mandatory
        DESCRIPTION     
        " This object represents the total number of data symbols that have
         been monitored to construct the Impulse Noise Monitoring histograms of
         Impulse Length and Inter-Arrival Time for the current 15 minute
         interval.

         ALCATEL NOTE:
             ACCESS:   NA                  USAGE:    NA
             PERSIST:  NO                  INSRVMOD: NA
             RANGE:    NA                  DEFVALUE: 0
             UNITS:    NA                  SPARSE:   NA
             DESCR:    NA "
::= {xdslFarEndLineInmCurrentIntervalEntry 3}

xdslFarEndLineInmCurrent1DayTable       OBJECT-TYPE
        SYNTAX          SEQUENCE OF XdslFarEndLineInmCurrent1DayEntry
        ACCESS          not-accessible
        STATUS          mandatory
        DESCRIPTION     
        " The xdsl far end line Impulse noise Monitoring current
         1 day interval table.

         ALCATEL NOTE:
             TABLESIZE: DEP [number of XDSL Lines]                    
             DESCR:     NA                   "
::= {xdslFarEndLineCurrent 8}

xdslFarEndLineInmCurrent1DayEntry       OBJECT-TYPE
        SYNTAX          XdslFarEndLineInmCurrent1DayEntry
        ACCESS          not-accessible
        STATUS          mandatory
        DESCRIPTION     
        " An entry in the xdsl far end line Impulse Noise Monitoring current
         1 day interval table.

         Row creation : Entries for all XDSL lines belonging to a board are 
                        created by the system when the board is planned.
         Row deletion : Entries for all XDSL lines belonging to a board are 
                        deleted by the system when the board is unplanned. "
        INDEX          {ifIndex}
::= {xdslFarEndLineInmCurrent1DayTable 1}

XdslFarEndLineInmCurrent1DayEntry ::=
        SEQUENCE {
            xdslFarEndLineInmCurrent1DayIatHistogram            IatHistogramType,
            xdslFarEndLineInmCurrent1DayEquivInpHistogram       EquivInpHistogramType,
            xdslFarEndLineInmCurrent1DayTotalDataSymbolCounter  Counter
        }
        
xdslFarEndLineInmCurrent1DayIatHistogram              OBJECT-TYPE
        SYNTAX          IatHistogramType
        ACCESS          read-only
        STATUS          mandatory
        DESCRIPTION     
        " This object represents the Impulse Noise Monitoring Inter-Arrival Time
         histogram for the current 1 day interval. The histogram consists
         of eight saturating counters representing the different class
         intervals configured.
         The Inter-Arrival Time is defined as the time between the start of two
         consecutive impulses, expressed as an number of data symbols.
         The class intervals width and offset are defined by
         xdslLineInmInterArrivalTimeStep and xdslLineInmInterArrivalTimeOffset.
         The Inter-Arrival Time histogram is coded as a fixed length
         octet string defined as follows:
         OCTETS 0..1: INTEGER (0..65535), value of the first class interval.
         The value is defined as MSB-LSB (big-endian).
         OCTETS 2..3: define the value of class interval 2.
         ....        up to
         OCTETS 14..15: define the last class interval 8.

         ALCATEL NOTE:
             ACCESS:   NA                  USAGE:    NA
             PERSIST:  NO                  INSRVMOD: NA
             RANGE:    NA                  DEFVALUE: '00000000000000000000000000000000'H
             UNITS:    octets              SPARSE:   NA
             DESCR:    NA "
::= {xdslFarEndLineInmCurrent1DayEntry 1}

xdslFarEndLineInmCurrent1DayEquivInpHistogram              OBJECT-TYPE
        SYNTAX          EquivInpHistogramType
        ACCESS          read-only
        STATUS          mandatory
        DESCRIPTION     
        "This object represents the Impulse Noise Monitoring Equivalent INP
         histogram for the current 1 day interval. The histogram consists
         of seventeen saturating counters representing the different class
         intervals.
         Class intervals 1 to 16 contain the number of impulse noise events
         detected per equivalent level of INP as defined by
         xdslLineEquivInpMode. Class interval 17 contains the number of impulse
         noise events detected with equivalent level of INP greater than 16.
         The equivalent INP histogram is coded as a fixed length
         octet string defined as follows:
         OCTETS 0..1: INTEGER (0..65535), value of the first class interval.
         The value is defined as MSB-LSB (big-endian).
         OCTETS 2..3: define the value of class interval 2.
         ....        up to
         OCTETS 32..33: define the last class interval 17.

         ALCATEL NOTE:
             ACCESS:   NA                  USAGE:    NA
             PERSIST:  NO                  INSRVMOD: NA
             RANGE:    NA                  DEFVALUE: '00000000000000000000000000000000000000000000000000000000000000000000'H
             UNITS:    octets              SPARSE:   NA
             DESCR:    NA "
::= {xdslFarEndLineInmCurrent1DayEntry 2}

xdslFarEndLineInmCurrent1DayTotalDataSymbolCounter   OBJECT-TYPE
        SYNTAX          Counter
        ACCESS          read-only
        STATUS          mandatory
        DESCRIPTION     
        " This object represents the total number of data symbols that have
         been monitored to construct the Impulse Noise Monitoring histograms of
         Impulse Length and Inter-Arrival Time for the current 1 day interval.

         ALCATEL NOTE:
             ACCESS:   NA                  USAGE:    NA
             PERSIST:  NO                  INSRVMOD: NA
             RANGE:    NA                  DEFVALUE: 0
             UNITS:    NA                  SPARSE:   NA
             DESCR:    NA "
::= {xdslFarEndLineInmCurrent1DayEntry 3}

xdslFarEndLinePreviousIntervalTable    OBJECT-TYPE
        SYNTAX          SEQUENCE OF XdslFarEndLinePreviousIntervalEntry
        ACCESS          not-accessible
        STATUS          mandatory
        DESCRIPTION     
        "The xdsl line far end previous interval table.
         ALCATEL NOTE:
             TABLESIZE: DEP [number of XDSL lines * 192]                    
             DESCR:     NA                   "
::= {xdslFarEndLinePrevious 1}
        
xdslFarEndLinePreviousIntervalEntry    OBJECT-TYPE
        SYNTAX          XdslFarEndLinePreviousIntervalEntry                     
        ACCESS          not-accessible
        STATUS          mandatory
        DESCRIPTION     
        "An entry in the xdsl line far end previous interval table.

         Row creation : Entries for all XDSL lines belonging to a board are 
                        created when the board becomes operational.
         Row deletion : Entries for all XDSL lines belonging to a board are 
                        deleted when the board becomes unavailable. "
        INDEX          {ifIndex, 
                        xdslFarEndLinePreviousIntervalNumber}
::= {xdslFarEndLinePreviousIntervalTable 1}

XdslFarEndLinePreviousIntervalEntry ::=
        SEQUENCE {
            xdslFarEndLinePreviousIntervalNumber          INTEGER,
            xdslFarEndLinePreviousIntervalLOSCounter      Counter,
            xdslFarEndLinePreviousIntervalLOFCounter      Counter,
            xdslFarEndLinePreviousIntervalLOMCounter      Counter,
            xdslFarEndLinePreviousIntervalLPRCounter      Counter,
            xdslFarEndLinePreviousIntervalLOLCounter      Counter,
            xdslFarEndLinePreviousIntervalESECounter      Counter,
            xdslFarEndLinePreviousIntervalESCounter       Counter,
            xdslFarEndLinePreviousIntervalSESCounter      Counter,
            xdslFarEndLinePreviousIntervalUASCounter      Counter,
            xdslFarEndLinePreviousIntervalMeasuredTime    INTEGER,
            xdslFarEndLinePreviousIntervalInvalidDataFlag INTEGER,
            xdslFarEndLinePreviousIntervalRAUCounter      Counter,
            xdslFarEndLinePreviousIntervalRADCounter      Counter,
            xdslFarEndLinePreviousIntervalLEFTRSCounter     Counter,
            xdslFarEndLinePreviousIntervalErrFreeBitsCounter Counter,
            xdslFarEndLinePreviousIntervalMinEFTRValue       INTEGER
        }
        
xdslFarEndLinePreviousIntervalNumber   OBJECT-TYPE
        SYNTAX          INTEGER(1..192)
        ACCESS          read-only
        STATUS          mandatory
        DESCRIPTION     
        "A number between 1 and 192, which identifies the interval for which
         the set of statistics is available. The interval identified by 1 is 
         the most recently completed 15 minute interval, and the interval
         identified by N is the interval immediately preceding the one
         identified by N-1.

         ALCATEL NOTE:
             ACCESS:   NA                  USAGE:    NA
             PERSIST:  NO                  INSRVMOD: NA
             RANGE:    NA                  DEFVALUE: NA
             UNITS:    NA                  SPARSE:   NA
             DESCR:    NA "
::= {xdslFarEndLinePreviousIntervalEntry 1}

xdslFarEndLinePreviousIntervalLOSCounter         OBJECT-TYPE
        SYNTAX          Counter
        ACCESS          read-only
        STATUS          mandatory
        DESCRIPTION     
        "This object represents for a particular 15 minute interval the LOS 
         failure count, which is the number of occurences of an LOS failure 
         event, where a failure event occurs when the failure is declared and 
         ends when the failure clears.

         ALCATEL NOTE:
             ACCESS:   NA                  USAGE:    NA
             PERSIST:  NO                  INSRVMOD: NA
             RANGE:    NA                  DEFVALUE: NA
             UNITS:    NA                  SPARSE:   NA
             DESCR:    NA "
::= {xdslFarEndLinePreviousIntervalEntry 2}

xdslFarEndLinePreviousIntervalLOFCounter         OBJECT-TYPE
        SYNTAX          Counter
        ACCESS          read-only
        STATUS          mandatory
        DESCRIPTION     
        "This object represents for a particular 15 minute interval the LOF 
         failure count, which is the number of occurences of an LOF failure 
         event, where a failure event occurs when the failure is declared and 
         ends when the failure clears.

         ALCATEL NOTE:
             ACCESS:   NA                  USAGE:    NA
             PERSIST:  NO                  INSRVMOD: NA
             RANGE:    NA                  DEFVALUE: 0
             UNITS:    NA                  SPARSE:   NA
             DESCR:    NA "
::= {xdslFarEndLinePreviousIntervalEntry 3}

xdslFarEndLinePreviousIntervalLOMCounter         OBJECT-TYPE
        SYNTAX          Counter
        ACCESS          read-only
        STATUS          mandatory
        DESCRIPTION     
        "This object represents for a particular 15 minute interval the LOM 
         failure count, which is the number of occurences of an LOM failure 
         event, where a failure event occurs when the failure is declared and 
         ends when the failure clears.

         ALCATEL NOTE:
             ACCESS:   NA                  USAGE:    NA
             PERSIST:  NO                  INSRVMOD: NA
             RANGE:    NA                  DEFVALUE: 0
             UNITS:    NA                  SPARSE:   NA
             DESCR:    NA "
::= {xdslFarEndLinePreviousIntervalEntry 4}

xdslFarEndLinePreviousIntervalLPRCounter         OBJECT-TYPE
        SYNTAX          Counter
        ACCESS          read-only
        STATUS          mandatory
        DESCRIPTION     
        "This object represents for a particular 15 minute interval the LPR 
         failure count, which is the number of occurences of an LPR failure 
         event, where a failure event occurs when the failure is declared and 
         ends when the failure clears.

         ALCATEL NOTE:
             ACCESS:   NA                  USAGE:    NA
             PERSIST:  NO                  INSRVMOD: NA
             RANGE:    NA                  DEFVALUE: 0
             UNITS:    NA                  SPARSE:   NA
             DESCR:    NA "
::= {xdslFarEndLinePreviousIntervalEntry 5}

xdslFarEndLinePreviousIntervalLOLCounter         OBJECT-TYPE
        SYNTAX          Counter
        ACCESS          read-only
        STATUS          mandatory
        DESCRIPTION     
        "This object represents for a particular 15 minute interval the LOL 
         failure count, which is the number of occurences of an LOL failure 
         event, where a failure event occurs when the failure is declared and 
         ends when the failure clears.

         ALCATEL NOTE:
             ACCESS:   NA                  USAGE:    NA
             PERSIST:  NO                  INSRVMOD: NA
             RANGE:    0                   DEFVALUE: 0
             UNITS:    NA                  SPARSE:   NA
             DESCR:    Because an LOL failure event never occurs, the value of
                       the counter is always 0. "
::= {xdslFarEndLinePreviousIntervalEntry 6}

xdslFarEndLinePreviousIntervalESECounter         OBJECT-TYPE
        SYNTAX          Counter
        ACCESS          read-only
        STATUS          mandatory
        DESCRIPTION     
        "This object represents for a particular 15 minute interval the ESE 
         failure count, which is the number of occurences of an ESE failure 
         event, where a failure event occurs when the failure is declared and 
         ends when the failure clears.

         ALCATEL NOTE:
             ACCESS:   NA                  USAGE:    NA
             PERSIST:  NO                  INSRVMOD: NA
             RANGE:    NA                  DEFVALUE: 0
             UNITS:    NA                  SPARSE:   NA
             DESCR:    NA "
::= {xdslFarEndLinePreviousIntervalEntry 7}

xdslFarEndLinePreviousIntervalESCounter          OBJECT-TYPE
        SYNTAX          Counter
        ACCESS          read-only
        STATUS          mandatory
        DESCRIPTION     
        "The counter associated with the number of Errored Seconds encountered 
         by the line in a particular 15 minute interval.

         ALCATEL NOTE:
             ACCESS:   NA                  USAGE:    NA
             PERSIST:  NO                  INSRVMOD: NA
             RANGE:    NA                  DEFVALUE: 0
             UNITS:    NA                  SPARSE:   NA
             DESCR:    NA "
::= {xdslFarEndLinePreviousIntervalEntry 8}

xdslFarEndLinePreviousIntervalSESCounter         OBJECT-TYPE
        SYNTAX          Counter
        ACCESS          read-only
        STATUS          mandatory
        DESCRIPTION     
        "The counter associated with the number of  Severely Errored Seconds
         encountered by the line in a particular 15 minute interval.

         ALCATEL NOTE:
             ACCESS:   NA                  USAGE:    NA
             PERSIST:  NO                  INSRVMOD: NA
             RANGE:    NA                  DEFVALUE: 0
             UNITS:    NA                  SPARSE:   NA
             DESCR:    NA "
::= {xdslFarEndLinePreviousIntervalEntry 9}

xdslFarEndLinePreviousIntervalUASCounter         OBJECT-TYPE
        SYNTAX          Counter
        ACCESS          read-only
        STATUS          mandatory
        DESCRIPTION     
        "The counter associated with the number of  Unavailable Seconds
         encountered by the line in a particular 15 minute interval.

         ALCATEL NOTE:
             ACCESS:   NA                  USAGE:    NA
             PERSIST:  NO                  INSRVMOD: NA
             RANGE:    NA                  DEFVALUE: 0
             UNITS:    NA                  SPARSE:   NA
             DESCR:    NA "
::= {xdslFarEndLinePreviousIntervalEntry 10}

xdslFarEndLinePreviousIntervalMeasuredTime       OBJECT-TYPE
        SYNTAX          INTEGER(0..900)
        ACCESS          read-only
        STATUS          mandatory
        DESCRIPTION     
        "The amount of time, measured in seconds, that statistics for this
         entry have been counted.

         ALCATEL NOTE:
             ACCESS:   NA                  USAGE:    NA
             PERSIST:  NO                  INSRVMOD: NA
             RANGE:    NA                  DEFVALUE: 0
             UNITS:    seconds             SPARSE:   NA
             DESCR:    NA "
::= {xdslFarEndLinePreviousIntervalEntry 11}

xdslFarEndLinePreviousIntervalInvalidDataFlag    OBJECT-TYPE
        SYNTAX          INTEGER
        ACCESS          read-only
        STATUS          mandatory
        DESCRIPTION     
        "This object indicates the validity of the corresponding PM data.
         It is set to 1 when the PM data is incomplete or invalid and set to 0
         when the PM data is complete and valid.

         ALCATEL NOTE:
             ACCESS:   NA                  USAGE:    NA
             PERSIST:  NO                  INSRVMOD: NA
             RANGE:    0..1                DEFVALUE: 1
             UNITS:    NA                  SPARSE:   NA
             DESCR:    NA "
::= {xdslFarEndLinePreviousIntervalEntry 12}

xdslFarEndLinePreviousIntervalRAUCounter         OBJECT-TYPE
        SYNTAX          Counter
        ACCESS          read-only
        STATUS          mandatory
        DESCRIPTION     
        "This object represents for a particular 15 minute interval the RAU 
         anomaly count, which is the number of occurences of an Upshift Rate 
         Adaptation.

         ALCATEL NOTE:
             ACCESS:   NA                  USAGE:    NA
             PERSIST:  NO                  INSRVMOD: NA
             RANGE:    NA                  DEFVALUE: 0
             UNITS:    NA                  SPARSE:   NA
             DESCR:    NA "
::= {xdslFarEndLinePreviousIntervalEntry 13}

xdslFarEndLinePreviousIntervalRADCounter         OBJECT-TYPE
        SYNTAX          Counter
        ACCESS          read-only
        STATUS          mandatory
        DESCRIPTION     
        "This object represents for a particular 15 minute interval the RAD 
         anomaly count, which is the number of occurences of a Downshift Rate
         Adaptation.

         ALCATEL NOTE:
             ACCESS:   NA                  USAGE:    NA
             PERSIST:  NO                  INSRVMOD: NA
             RANGE:    NA                  DEFVALUE: 0
             UNITS:    NA                  SPARSE:   NA
             DESCR:    NA "
::= {xdslFarEndLinePreviousIntervalEntry 14}

xdslFarEndLinePreviousIntervalLEFTRSCounter      OBJECT-TYPE
        SYNTAX          Counter
        ACCESS          read-only
        STATUS          mandatory
        DESCRIPTION     
        "When RTX is in use then this counter associates with the number of
         LEFTR seconds encountered by the line in the previous 15 minute interval.
         Otherwise the default value will be returned.

         ALCATEL NOTE:
             ACCESS:   NA                  USAGE:    NA
             PERSIST:  NO                  INSRVMOD: NA
             RANGE:    NA                  DEFVALUE: 0
             UNITS:    NA                  SPARSE:   NA
             DESCR:    NA "
::= { xdslFarEndLinePreviousIntervalEntry 15}

xdslFarEndLinePreviousIntervalErrFreeBitsCounter      OBJECT-TYPE
        SYNTAX          Counter
        ACCESS          read-only
        STATUS          mandatory
        DESCRIPTION     
        " When RTX is in use then this counter represents for the previous 
         15 minute interval the count of the number of error-free bits divided 
         by 2^16.
         Otherwise the default value will be returned.

         ALCATEL NOTE:
             ACCESS:   NA                  USAGE:    NA
             PERSIST:  NO                  INSRVMOD: NA
             RANGE:    NA                  DEFVALUE: 0
             UNITS:    NA                  SPARSE:   NA
             DESCR:    NA "
::= { xdslFarEndLinePreviousIntervalEntry 16}

xdslFarEndLinePreviousIntervalMinEFTRValue      OBJECT-TYPE
        SYNTAX          INTEGER
        ACCESS          read-only
        STATUS          mandatory
        DESCRIPTION     
        " When RTX is in use then this counter represents for the previous 
         15 minute interval the count of the Minimum of the EFTR observed
         during this interval.
         Otherwise the default value will be returned.

         ALCATEL NOTE:
             ACCESS:   NA                  USAGE:    NA
             PERSIST:  NO                  INSRVMOD: NA
             RANGE:    NA                  DEFVALUE: 0
             UNITS:    NA                  SPARSE:   NA
             DESCR:    NA "
::= { xdslFarEndLinePreviousIntervalEntry 17}

xdslFarEndLinePrevious1DayTable        OBJECT-TYPE
        SYNTAX          SEQUENCE OF XdslFarEndLinePrevious1DayEntry
        ACCESS          not-accessible
        STATUS          mandatory
        DESCRIPTION     
        "The xdsl line far end previous 1 day table.
         ALCATEL NOTE:
             TABLESIZE: DEP [number of XDSL lines * number of days (1)]                     
             DESCR:     NA                   "
::= {xdslFarEndLinePrevious 2}
        
xdslFarEndLinePrevious1DayEntry        OBJECT-TYPE
        SYNTAX          XdslFarEndLinePrevious1DayEntry                 
        ACCESS          not-accessible
        STATUS          mandatory
        DESCRIPTION     
        "An entry in the xdsl line far end previous 1 day table.

         Row creation : Entries for all XDSL lines belonging to a board are 
                        created when the board becomes operational.
         Row deletion : Entries for all XDSL lines belonging to a board are 
                        deleted when the board becomes unavailable. "
        INDEX          {ifIndex, 
                        xdslFarEndLinePrevious1DayNumber}

::= {xdslFarEndLinePrevious1DayTable 1}

XdslFarEndLinePrevious1DayEntry ::=
        SEQUENCE {
            xdslFarEndLinePrevious1DayNumber          INTEGER,
            xdslFarEndLinePrevious1DayLOSCounter      Counter,
            xdslFarEndLinePrevious1DayLOFCounter      Counter,
            xdslFarEndLinePrevious1DayLOMCounter      Counter,
            xdslFarEndLinePrevious1DayLPRCounter      Counter,
            xdslFarEndLinePrevious1DayLOLCounter      Counter,
            xdslFarEndLinePrevious1DayESECounter      Counter,
            xdslFarEndLinePrevious1DayESCounter       Counter,
            xdslFarEndLinePrevious1DaySESCounter      Counter,
            xdslFarEndLinePrevious1DayUASCounter      Counter,
            xdslFarEndLinePrevious1DayMeasuredTime    INTEGER,
            xdslFarEndLinePrevious1DayInvalidDataFlag INTEGER,
            xdslFarEndLinePrevious1DayRAUCounter      Counter,
            xdslFarEndLinePrevious1DayRADCounter      Counter,
            xdslFarEndLinePrevious1DayLEFTRSCounter         Counter,
            xdslFarEndLinePrevious1DayErrFreeBitsCounter    Counter,     
            xdslFarEndLinePrevious1DayMinEFTRValue          INTEGER
        }

xdslFarEndLinePrevious1DayNumber       OBJECT-TYPE
        SYNTAX          INTEGER(1..7)
        ACCESS          read-only
        STATUS          mandatory
        DESCRIPTION     
        "A number between 1 and 7, which identifies the day for which the 
         set of statistics is available. The day identified by 1 is the 
         most recently completed 1Day, and the day identified 
         by N is the day immediately preceding the one identified by N-1.

         ALCATEL NOTE:
             ACCESS:   NA                  USAGE:    NA
             PERSIST:  NO                  INSRVMOD: NA
             RANGE:    1                   DEFVALUE: NA
             UNITS:    NA                  SPARSE:   NA
             DESCR:    Only statistics for one previous day is kept. "
::= {xdslFarEndLinePrevious1DayEntry 1}

xdslFarEndLinePrevious1DayLOSCounter   OBJECT-TYPE
        SYNTAX          Counter
        ACCESS          read-only
        STATUS          mandatory
        DESCRIPTION     
        "This object represents for the previous 1 day interval the LOS failure
         count, which is the number of occurences of an LOS failure event, 
         where a failure event occurs when the failure is declared and ends
         when the failure clears.

         ALCATEL NOTE:
             ACCESS:   NA                  USAGE:    NA
             PERSIST:  NO                  INSRVMOD: NA
             RANGE:    NA                  DEFVALUE: 0
             UNITS:    NA                  SPARSE:   NA
             DESCR:    NA "
::= {xdslFarEndLinePrevious1DayEntry 2}

xdslFarEndLinePrevious1DayLOFCounter   OBJECT-TYPE
        SYNTAX          Counter
        ACCESS          read-only
        STATUS          mandatory
        DESCRIPTION     
        "This object represents for the previous 1 day interval the LOF failure
         count, which is the number of occurences of an LOF failure event,
         where a failure event occurs when the failure is declared and ends 
         when the failure clears.

         ALCATEL NOTE:
             ACCESS:   NA                  USAGE:    NA
             PERSIST:  NO                  INSRVMOD: NA
             RANGE:    NA                  DEFVALUE: 0
             UNITS:    NA                  SPARSE:   NA
             DESCR:    NA "
::= {xdslFarEndLinePrevious1DayEntry 3}

xdslFarEndLinePrevious1DayLOMCounter   OBJECT-TYPE
        SYNTAX          Counter
        ACCESS          read-only
        STATUS          mandatory
        DESCRIPTION     
        "This object represents for the previous 1 day interval the LOM failure
         count, which is the number of occurences of an LOM failure event, 
         where a failure event occurs when the failure is declared and ends 
         when the failure clears.

         ALCATEL NOTE:
             ACCESS:   NA                  USAGE:    NA
             PERSIST:  NO                  INSRVMOD: NA
             RANGE:    NA                  DEFVALUE: 0
             UNITS:    NA                  SPARSE:   NA
             DESCR:    NA "
::= {xdslFarEndLinePrevious1DayEntry 4}

xdslFarEndLinePrevious1DayLPRCounter   OBJECT-TYPE
        SYNTAX          Counter
        ACCESS          read-only
        STATUS          mandatory
        DESCRIPTION     
        "This object represents for the previous 1 day interval the LPR failure
         count, which is the number of occurences of an LPR failure event, 
         where a failure event occurs when the failure is declared and ends
         when the failure clears.

         ALCATEL NOTE:
             ACCESS:   NA                  USAGE:    NA
             PERSIST:  NO                  INSRVMOD: NA
             RANGE:    NA                  DEFVALUE: 0
             UNITS:    NA                  SPARSE:   NA
             DESCR:    NA "
::= {xdslFarEndLinePrevious1DayEntry 5}

xdslFarEndLinePrevious1DayLOLCounter   OBJECT-TYPE
        SYNTAX          Counter
        ACCESS          read-only
        STATUS          mandatory
        DESCRIPTION     
        "This object represents for the previous 1 day interval the LOL failure
         count, which is the number of occurences of an LOL failure event, 
         where a failure event occurs when the failure is declared and ends 
         when the failure clears.

         ALCATEL NOTE:
             ACCESS:   NA                  USAGE:    NA
             PERSIST:  NO                  INSRVMOD: NA
             RANGE:    0                   DEFVALUE: 0
             UNITS:    NA                  SPARSE:   NA
             DESCR:    Because an LOL failure event never occurs, the value of
                       the counter is always 0. "
::= {xdslFarEndLinePrevious1DayEntry 6}

xdslFarEndLinePrevious1DayESECounter   OBJECT-TYPE
        SYNTAX          Counter
        ACCESS          read-only
        STATUS          mandatory
        DESCRIPTION     
        "This object represents for the previous 1 day interval the ESE failure
         count, which is the number of occurences of an ESE failure event, 
         where a failure event occurs when the failure is declared and ends 
         when the failure clears.

         ALCATEL NOTE:
             ACCESS:   NA                  USAGE:    NA
             PERSIST:  NO                  INSRVMOD: NA
             RANGE:    NA                  DEFVALUE: 0
             UNITS:    NA                  SPARSE:   NA
             DESCR:    NA "
::= {xdslFarEndLinePrevious1DayEntry 7}

xdslFarEndLinePrevious1DayESCounter    OBJECT-TYPE
        SYNTAX          Counter
        ACCESS          read-only
        STATUS          mandatory
        DESCRIPTION     
        "The counter associated with the number of Errored Seconds encountered 
         by the line in the previous 1 day interval.

         ALCATEL NOTE:
             ACCESS:   NA                  USAGE:    NA
             PERSIST:  NO                  INSRVMOD: NA
             RANGE:    NA                  DEFVALUE: 0
             UNITS:    NA                  SPARSE:   NA
             DESCR:    NA "
::= {xdslFarEndLinePrevious1DayEntry 8}

xdslFarEndLinePrevious1DaySESCounter   OBJECT-TYPE
        SYNTAX          Counter
        ACCESS          read-only
        STATUS          mandatory
        DESCRIPTION     
        "The counter associated with the number of  Severely Errored Seconds
         encountered by the line in the previous 1 day interval.

         ALCATEL NOTE:
             ACCESS:   NA                  USAGE:    NA
             PERSIST:  NO                  INSRVMOD: NA
             RANGE:    NA                  DEFVALUE: 0
             UNITS:    NA                  SPARSE:   NA
             DESCR:    NA "
::= {xdslFarEndLinePrevious1DayEntry 9}

xdslFarEndLinePrevious1DayUASCounter   OBJECT-TYPE
        SYNTAX          Counter
        ACCESS          read-only
        STATUS          mandatory
        DESCRIPTION     
        "The counter associated with the number of Unavailable Seconds
         encountered by the line in the previous 1 day interval.

         ALCATEL NOTE:
             ACCESS:   NA                  USAGE:    NA
             PERSIST:  NO                  INSRVMOD: NA
             RANGE:    NA                  DEFVALUE: 0
             UNITS:    NA                  SPARSE:   NA
             DESCR:    NA "
::= {xdslFarEndLinePrevious1DayEntry 10}

xdslFarEndLinePrevious1DayMeasuredTime OBJECT-TYPE
        SYNTAX          INTEGER(0..86400)
        ACCESS          read-only
        STATUS          mandatory
        DESCRIPTION      
        "The amount of time, measured in seconds, that statistics for this
         entry have been counted.

         ALCATEL NOTE:
             ACCESS:   NA                  USAGE:    NA
             PERSIST:  NO                  INSRVMOD: NA
             RANGE:    NA                  DEFVALUE: 0
             UNITS:    seconds             SPARSE:   NA
             DESCR:    NA "
::= {xdslFarEndLinePrevious1DayEntry 11}

xdslFarEndLinePrevious1DayInvalidDataFlag        OBJECT-TYPE
        SYNTAX          INTEGER
        ACCESS          read-only
        STATUS          mandatory
        DESCRIPTION      
        "This object indicates the validity of the corresponding PM data.
         It is set to 1 when the PM data is incomplete or invalid and set to 0
         when the PM data is complete and valid.

         ALCATEL NOTE:
             ACCESS:   NA                  USAGE:    NA
             PERSIST:  NO                  INSRVMOD: NA
             RANGE:    0..1                DEFVALUE: 1
             UNITS:    NA                  SPARSE:   NA
             DESCR:    NA "
::= {xdslFarEndLinePrevious1DayEntry 12}

xdslFarEndLinePrevious1DayRAUCounter   OBJECT-TYPE
        SYNTAX          Counter
        ACCESS          read-only
        STATUS          mandatory
        DESCRIPTION     
        "This object represents for the previous 1 day interval the RAU anomaly 
         count, which is the number of occurences of an Upshift Rate 
         Adaptation.

         ALCATEL NOTE:
             ACCESS:   NA                  USAGE:    NA
             PERSIST:  NO                  INSRVMOD: NA
             RANGE:    NA                  DEFVALUE: 0
             UNITS:    NA                  SPARSE:   NA
             DESCR:    NA "
::= {xdslFarEndLinePrevious1DayEntry 13}

xdslFarEndLinePrevious1DayRADCounter   OBJECT-TYPE
        SYNTAX          Counter
        ACCESS          read-only
        STATUS          mandatory
        DESCRIPTION     
        "This object represents for the previous 1 day interval the RAD anomaly 
         count, which is the number of occurences of a Downshift Rate 
         Adaptation.

         ALCATEL NOTE:
             ACCESS:   NA                  USAGE:    NA
             PERSIST:  NO                  INSRVMOD: NA
             RANGE:    NA                  DEFVALUE: 0
             UNITS:    NA                  SPARSE:   NA
             DESCR:    NA "
::= {xdslFarEndLinePrevious1DayEntry 14}

xdslFarEndLinePrevious1DayLEFTRSCounter      OBJECT-TYPE
        SYNTAX          Counter
        ACCESS          read-only
        STATUS          mandatory
        DESCRIPTION     
        "When RTX is in use then this counter associates with the number of
         LEFTR seconds encountered by the line in the previous 1 day interval.
         Otherwise the default value will be returned.

         ALCATEL NOTE:
             ACCESS:   NA                  USAGE:    NA
             PERSIST:  NO                  INSRVMOD: NA
             RANGE:    NA                  DEFVALUE: 0
             UNITS:    NA                  SPARSE:   NA
             DESCR:    NA "
::= { xdslFarEndLinePrevious1DayEntry 15}

xdslFarEndLinePrevious1DayErrFreeBitsCounter      OBJECT-TYPE
        SYNTAX          Counter
        ACCESS          read-only
        STATUS          mandatory
        DESCRIPTION     
        "When RTX is in use then this counter represents for the previous 
         1 day interval the count of the number of error-free bits divided 
         by 2^16.
         Otherwise the default value will be returned.

         ALCATEL NOTE:
             ACCESS:   NA                  USAGE:    NA
             PERSIST:  NO                  INSRVMOD: NA
             RANGE:    NA                  DEFVALUE: 0
             UNITS:    NA                  SPARSE:   NA
             DESCR:    NA "
::= { xdslFarEndLinePrevious1DayEntry 16}

xdslFarEndLinePrevious1DayMinEFTRValue      OBJECT-TYPE
        SYNTAX          INTEGER
        ACCESS          read-only
        STATUS          mandatory
        DESCRIPTION     
        "When RTX is in use then this counter represents for the previous 
         1 day interval the count of the Minimum of the EFTR observed
         during this interval.
         Otherwise the default value will be returned.

         ALCATEL NOTE:
             ACCESS:   NA                  USAGE:    NA
             PERSIST:  NO                  INSRVMOD: NA
             RANGE:    NA                  DEFVALUE: 0
             UNITS:    NA                  SPARSE:   NA
             DESCR:    NA "
::= { xdslFarEndLinePrevious1DayEntry 17}

xdslFarEndLineInmPreviousIntervalTable       OBJECT-TYPE
        SYNTAX          SEQUENCE OF XdslFarEndLineInmPreviousIntervalEntry
        ACCESS          not-accessible
        STATUS          mandatory
        DESCRIPTION     
        " The xdsl far end line Impulse noise Monitoring previous
         15 minute interval table.

         ALCATEL NOTE:
             TABLESIZE: DEP [number of XDSL lines]                    
             DESCR:     NA                   "
::= {xdslFarEndLinePrevious 3}

xdslFarEndLineInmPreviousIntervalEntry       OBJECT-TYPE
        SYNTAX          XdslFarEndLineInmPreviousIntervalEntry
        ACCESS          not-accessible
        STATUS          mandatory
        DESCRIPTION     
        " An entry in the xdsl far end line Impulse Noise Monitoring previous
         15 minute interval table.

         Row creation : Entries for all XDSL lines belonging to a board are 
                        created by the system when the board is planned.
         Row deletion : Entries for all XDSL lines belonging to a board are 
                        deleted by the system when the board is unplanned. "
        INDEX          {ifIndex}
::= {xdslFarEndLineInmPreviousIntervalTable 1}

XdslFarEndLineInmPreviousIntervalEntry ::=
        SEQUENCE {
            xdslFarEndLineInmPreviousIntervalIatHistogram            IatHistogramType,
            xdslFarEndLineInmPreviousIntervalEquivInpHistogram  EquivInpHistogramType,
            xdslFarEndLineInmPreviousIntervalTotalDataSymbolCounter  Counter
        }
        
xdslFarEndLineInmPreviousIntervalIatHistogram              OBJECT-TYPE
        SYNTAX          IatHistogramType
        ACCESS          read-only
        STATUS          mandatory
        DESCRIPTION     
        " This object represents the Impulse Noise Monitoring Inter-Arrival Time
         histogram for the previous 15 minute interval. The histogram consists
         of eight saturating counters representing the different class
         intervals configured.
         The Inter-Arrival Time is defined as the time between the start of two
         consecutive impulses, expressed as an number of data symbols.
         The class intervals width and offset are defined by
         xdslLineInmInterArrivalTimeStep and xdslLineInmInterArrivalTimeOffset.
         The Inter-Arrival Time histogram is coded as a fixed length
         octet string defined as follows:
         OCTETS 0..1: INTEGER (0..65535), value of the first class interval.
         The value is defined as MSB-LSB (big-endian).
         OCTETS 2..3: define the value of class interval 2.
         ....        up to
         OCTETS 14..15: define the last class interval 8.

         ALCATEL NOTE:
             ACCESS:   NA                  USAGE:    NA
             PERSIST:  NO                  INSRVMOD: NA
             RANGE:    16                  DEFVALUE: '00000000000000000000000000000000'H
             UNITS:    octets              SPARSE:   NA
             DESCR:    NA "
::= {xdslFarEndLineInmPreviousIntervalEntry 1}

xdslFarEndLineInmPreviousIntervalEquivInpHistogram              OBJECT-TYPE
        SYNTAX          EquivInpHistogramType
        ACCESS          read-only
        STATUS          mandatory
        DESCRIPTION     
        "This object represents the Impulse Noise Monitoring Equivalent INP
         histogram for the previous 15 minute interval. The histogram consists
         of seventeen saturating counters representing the different class
         intervals.
         Class intervals 1 to 16 contain the number of impulse noise events
         detected per equivalent level of INP as defined by
         xdslLineEquivInpMode. Class interval 17 contains the number of impulse
         noise events detected with equivalent level of INP greater than 16.
         The equivalent INP histogram is coded as a fixed length
         octet string defined as follows:
         OCTETS 0..1: INTEGER (0..65535), value of the first class interval.
         The value is defined as MSB-LSB (big-endian).
         OCTETS 2..3: define the value of class interval 2.
         ....        up to
         OCTETS 32..33: define the last class interval 17.

         ALCATEL NOTE:
             ACCESS:   NA                  USAGE:    NA
             PERSIST:  NO                  INSRVMOD: NA
             RANGE:    NA                  DEFVALUE: '00000000000000000000000000000000000000000000000000000000000000000000'H
             UNITS:    octets              SPARSE:   NA
             DESCR:    NA "
::= {xdslFarEndLineInmPreviousIntervalEntry 2}

xdslFarEndLineInmPreviousIntervalTotalDataSymbolCounter   OBJECT-TYPE
        SYNTAX          Counter
        ACCESS          read-only
        STATUS          mandatory
        DESCRIPTION     
        " This object represents the total number of data symbols that have
         been monitored to construct the Impulse nois Monitoring histograms of
         Impulse Length and Inter-Arrival Time for the previous 15 minute
         interval.

         ALCATEL NOTE:
             ACCESS:   NA                  USAGE:    NA
             PERSIST:  NO                  INSRVMOD: NA
             RANGE:    NA                  DEFVALUE: 0
             UNITS:    NA                  SPARSE:   NA
             DESCR:    NA "
::= {xdslFarEndLineInmPreviousIntervalEntry 3}

xdslFarEndLineInmPrevious1DayTable       OBJECT-TYPE
        SYNTAX          SEQUENCE OF XdslFarEndLineInmPrevious1DayEntry
        ACCESS          not-accessible
        STATUS          mandatory
        DESCRIPTION     
        " The xdsl far end line Impulse noise Monitoring previous
         1 day interval table.

         ALCATEL NOTE:
             TABLESIZE: DEP [number of XDSL Lines]                    
             DESCR:     NA                   "
::= {xdslFarEndLinePrevious 8}

xdslFarEndLineInmPrevious1DayEntry       OBJECT-TYPE
        SYNTAX          XdslFarEndLineInmPrevious1DayEntry
        ACCESS          not-accessible
        STATUS          mandatory
        DESCRIPTION     
        " An entry in the xdsl far end line Impulse Noise Monitoring previous
         1 day interval table.

         Row creation : Entries for all XDSL lines belonging to a board are 
                        created by the system when the board is planned.
         Row deletion : Entries for all XDSL lines belonging to a board are 
                        deleted by the system when the board is unplanned. "
        INDEX          {ifIndex}
::= {xdslFarEndLineInmPrevious1DayTable 1}

XdslFarEndLineInmPrevious1DayEntry ::=
        SEQUENCE {
            xdslFarEndLineInmPrevious1DayIatHistogram            IatHistogramType,
            xdslFarEndLineInmPrevious1DayEquivInpHistogram  EquivInpHistogramType,
            xdslFarEndLineInmPrevious1DayTotalDataSymbolCounter  Counter
        }
        
xdslFarEndLineInmPrevious1DayIatHistogram              OBJECT-TYPE
        SYNTAX          IatHistogramType
        ACCESS          read-only
        STATUS          mandatory
        DESCRIPTION     
        " This object represents the Impulse Noise Monitoring Inter-Arrival Time
         histogram for the previous 1 day interval. The histogram consists
         of eight saturating counters representing the different class
         intervals configured.
         The Inter-Arrival Time is defined as the time between the start of two
         consecutive impulses, expressed as an number of data symbols.
         The class intervals width and offset are defined by
         xdslLineInmInterArrivalTimeStep and xdslLineInmInterArrivalTimeOffset.
         The Inter-Arrival Time histogram is coded as a fixed length
         octet string defined as follows:
         OCTETS 0..1: INTEGER (0..65535), value of the first class interval.
         The value is defined as MSB-LSB (big-endian).
         OCTETS 2..3: define the value of class interval 2.
         ....        up to
         OCTETS 14..15: define the last class interval 8.

         ALCATEL NOTE:
             ACCESS:   NA                  USAGE:    NA
             PERSIST:  NO                  INSRVMOD: NA
             RANGE:    16                  DEFVALUE: '00000000000000000000000000000000'H
             UNITS:    octets              SPARSE:   NA
             DESCR:    NA "
::= {xdslFarEndLineInmPrevious1DayEntry 1}

xdslFarEndLineInmPrevious1DayEquivInpHistogram              OBJECT-TYPE
        SYNTAX          EquivInpHistogramType
        ACCESS          read-only
        STATUS          mandatory
        DESCRIPTION     
        "This object represents the Impulse Noise Monitoring Equivalent INP
         histogram for the previous 1 day interval. The histogram consists
         of seventeen saturating counters representing the different class
         intervals.
         Class intervals 1 to 16 contain the number of impulse noise events
         detected per equivalent level of INP as defined by
         xdslLineEquivInpMode. Class interval 17 contains the number of impulse
         noise events detected with equivalent level of INP greater than 16.
         The equivalent INP histogram is coded as a fixed length
         octet string defined as follows:
         OCTETS 0..1: INTEGER (0..65535), value of the first class interval.
         The value is defined as MSB-LSB (big-endian).
         OCTETS 2..3: define the value of class interval 2.
         ....        up to
         OCTETS 32..33: define the last class interval 17.

         ALCATEL NOTE:
             ACCESS:   NA                  USAGE:    NA
             PERSIST:  NO                  INSRVMOD: NA
             RANGE:    NA                  DEFVALUE: '00000000000000000000000000000000000000000000000000000000000000000000'H
             UNITS:    octets              SPARSE:   NA
             DESCR:    NA "
::= {xdslFarEndLineInmPrevious1DayEntry 2}

xdslFarEndLineInmPrevious1DayTotalDataSymbolCounter   OBJECT-TYPE
        SYNTAX          Counter
        ACCESS          read-only
        STATUS          mandatory
        DESCRIPTION     
        " This object represents the total number of data symbols that have
         been monitored to construct the Impulse Noise Monitoring histograms of
         Impulse Length and Inter-Arrival Time for the previous 1 day interval.

         ALCATEL NOTE:
             ACCESS:   NA                  USAGE:    NA
             PERSIST:  NO                  INSRVMOD: NA
             RANGE:    NA                  DEFVALUE: 0
             UNITS:    NA                  SPARSE:   NA
             DESCR:    NA "
::= {xdslFarEndLineInmPrevious1DayEntry 3}

xdslFarEndLineInsConfTable       OBJECT-TYPE
        SYNTAX          SEQUENCE OF XdslFarEndLineInsConfEntry
        ACCESS          not-accessible
        STATUS          mandatory
        DESCRIPTION     
        " The xdsl far end line impulse noise sensor configuration table.

         ALCATEL NOTE:
             TABLESIZE: DEP [number of XDSL lines]                    
             DESCR:     NA                   "
::= {xdslFarEndLine 3}

xdslFarEndLineInsConfEntry       OBJECT-TYPE
        SYNTAX          XdslFarEndLineInsConfEntry
        ACCESS          not-accessible
        STATUS          mandatory
        DESCRIPTION     
        " An entry in the xdsl far end line impulse noise sensor configuration
         table.

         Row creation : Entries for all XDSL lines belonging to a board are 
                        created by the system when the board is planned.
         Row deletion : Entries for all XDSL lines belonging to a board are 
                        deleted by the system when the board is unplanned. "
        INDEX          {ifIndex}
::= {xdslFarEndLineInsConfTable 1}

XdslFarEndLineInsConfEntry ::=
        SEQUENCE {
            xdslFarEndLineInmMode                         INTEGER,
            xdslFarEndLineInmEquivInpMode                 INTEGER,
            xdslFarEndLineInsSensitivity                  INTEGER,
            xdslFarEndLineInmClusterContinuation          INTEGER,
            xdslFarEndLineInmInterArrivalTimeOffset       INTEGER,
            xdslFarEndLineInmInterArrivalTimeStep         INTEGER
        }
        
xdslFarEndLineInmMode              OBJECT-TYPE
        SYNTAX          INTEGER {
                            disabled (1),
                            enabled (2)
                        }
        ACCESS          read-write
        STATUS          mandatory
        DESCRIPTION     
        "This parameter indicates if the Downstream Impulse Noise Monitoring
         statistics collection mechanism is enabled or disabled.

         ALCATEL NOTE:
             ACCESS:   NA                  USAGE:    OPT
             PERSIST:  NO                  INSRVMOD: YES
             RANGE:    NA                  DEFVALUE: disabled
             UNITS:    NA                  SPARSE:   NA
             DESCR:    NA "
::= {xdslFarEndLineInsConfEntry 1}

xdslFarEndLineInmEquivInpMode              OBJECT-TYPE
        SYNTAX          INTEGER
        ACCESS          read-write
        STATUS          mandatory
        DESCRIPTION     
    "This parameter indicates the mode used in the computation of the
     equivalent INP for construction of the INM Equivalent INP histograms.

     Mode 0 : Impulse length.
     Mode 1 : Cluster length.
     Mode 2 : Sum of impulse length in cluster.
     Mode 3 : Gap compensated impulse length in cluster.

         ALCATEL NOTE:
             ACCESS:   NA                  USAGE:    OPT
             PERSIST:  NO                  INSRVMOD: YES
             RANGE:    0..3                DEFVALUE: 0
             UNITS:    NA                  SPARSE:   NA
             DESCR:    NA "
::= {xdslFarEndLineInsConfEntry 2}

xdslFarEndLineInsSensitivity              OBJECT-TYPE
        SYNTAX          INTEGER
        ACCESS          read-write
        STATUS          mandatory
        DESCRIPTION     
        "This parameters indicates the Downstream Impulse Noise Sensor
         sensitivity relative to the default detection capability under current
         loop condition and noise margin.
         Range: -12.8 dB to 12.7 dB with 0.1 dB steps.
         The value 0 dB corresponds to default sensitivity.

         ALCATEL NOTE:
             ACCESS:   NA                  USAGE:    OPT
             PERSIST:  NO                  INSRVMOD: YES
             RANGE:    -128..127           DEFVALUE: 0
             UNITS:    dB / 10             SPARSE:   NA
             DESCR:    NA "
::= {xdslFarEndLineInsConfEntry 3}

xdslFarEndLineInmClusterContinuation              OBJECT-TYPE
        SYNTAX          INTEGER
        ACCESS          read-write
        STATUS          mandatory
        DESCRIPTION     
        "This parameter indicates for the Impulse Noise Monitoring statistics
         collection the way the degraded data symbols have to be grouped by the
         cluster continuation mechanism to indicate impulses.
         Range: 1 to 64 DMT Symbols plus special value 0.
         Special value 0 is used to indicate that cluster continuation is
         disabled.

         ALCATEL NOTE:
             ACCESS:   NA                  USAGE:    OPT
             PERSIST:  NO                  INSRVMOD: YES
             RANGE:    0..64               DEFVALUE: 0
             UNITS:    DMT Symbol          SPARSE:   NA
             DESCR:    NA "
::= {xdslFarEndLineInsConfEntry 4}

xdslFarEndLineInmInterArrivalTimeOffset              OBJECT-TYPE
        SYNTAX          INTEGER
        ACCESS          read-write
        STATUS          mandatory
        DESCRIPTION     
        "This parameter indicates the offset applied on the class intervals of
         the Downstream Inter-Arrival Time histograms.
         Range: 3 to 511 DMT Symbol.

         ALCATEL NOTE:
             ACCESS:   NA                  USAGE:    OPT
             PERSIST:  NO                  INSRVMOD: YES
             RANGE:    3..511              DEFVALUE: 3
             UNITS:    DMT Symbol          SPARSE:   NA
             DESCR:    NA "
::= {xdslFarEndLineInsConfEntry 5}

xdslFarEndLineInmInterArrivalTimeStep              OBJECT-TYPE
        SYNTAX          INTEGER
        ACCESS          read-write
        STATUS          mandatory
        DESCRIPTION     
        "This parameter indicates the width of the class intervals of the
         Downstream Inter-Arrival Time histograms.
         Range: 0 to 7.

         ALCATEL NOTE:
             ACCESS:   NA                  USAGE:    OPT
             PERSIST:  NO                  INSRVMOD: YES
             RANGE:    0..7                DEFVALUE: 0
             UNITS:    NA                  SPARSE:   NA
             DESCR:    NA "
::= {xdslFarEndLineInsConfEntry 6}

xdslChannelOperDataTable               OBJECT-TYPE
        SYNTAX          SEQUENCE OF XdslChannelOperDataEntry
        ACCESS          not-accessible
        STATUS          mandatory
        DESCRIPTION     
        "The xdsl channel operational data table.

         ALCATEL NOTE:
             TABLESIZE: DEP [number of XDSL lines * maximum number of channels
                             per XDSL line (1)]                    
             DESCR:     NA                   "
::= {xdslChannelCurrent 1}

xdslChannelOperDataEntry               OBJECT-TYPE
        SYNTAX          XdslChannelOperDataEntry
        ACCESS          not-accessible
        STATUS          mandatory
        DESCRIPTION     
        "An entry in the xdsl channel operational data table.

         Row creation : Entries for all XDSL channels belonging to a board are 
                        created when the board becomes operational.
         Row deletion : Entries for all XDSL channels belonging to a board are 
                        deleted when the board becomes unavailable. "
        INDEX          {ifIndex}
::= {xdslChannelOperDataTable 1}

XdslChannelOperDataEntry ::=
        SEQUENCE {
            xdslChannelActualBitrateUpstream              INTEGER,
            xdslChannelAttainableBitrateUpstream          INTEGER,
            xdslChannelActualInterleavingDelayDownstream  INTEGER,
            xdslChannelActualImpNoiseProtDownstream       INTEGER,
            xdslChannelActualNetDataRateUpstream          INTEGER,
            xdslChannelActualImpNoiseProtReinDownstream   INTEGER,
            xdslChannelAttainableNetDataRateUpstream      INTEGER    
        }

xdslChannelActualBitrateUpstream       OBJECT-TYPE
        SYNTAX          INTEGER
        ACCESS          read-only
        STATUS          mandatory
        DESCRIPTION     
        "When the modem is in showtime: 
           - and RTX is not in use, then this object gives the actual net data 
             rate for the upstream fast or interleaved channel data flow.
           - and RTX is in use, then this object gives the actual expected 
             throughput for the upstream retransmission channel data flow.
         When not in showtime, then this object has the value measured in preceeding
         showtime session. After an activation failure, this object represents
         the value as available till activation failure. A value 0 means that
         no data is available.

         ALCATEL NOTE:
             ACCESS:   NA                  USAGE:    NA
             PERSIST:  NO                  INSRVMOD: NA
             RANGE:    0..262143           DEFVALUE: 0
             UNITS:    kbits/sec           SPARSE:   NA
             DESCR:    NA "
::= {xdslChannelOperDataEntry 1}

xdslChannelAttainableBitrateUpstream   OBJECT-TYPE
        SYNTAX         INTEGER
        ACCESS         read-only
        STATUS         mandatory
        DESCRIPTION 
        " When the modem is in showtime :
           - and RTX is not in use, then this object contains the maximum 
             attainable net data rate the modem can support on the corresponding 
             channel. 
           - and RTX is in use, then this object contains the maximum 
             attainable expected throughput the modem can support on the 
             corresponding channel. 
         When the modem is not in showtime this object will have the value
         measured during the previous showtime session.
         When no data is available (e.g. before first showtime) value 0
         is used.

         ALCATEL NOTE:
             ACCESS:   NA                  USAGE:    NA
             PERSIST:  NO                  INSRVMOD: NA
             RANGE:    0..262143           DEFVALUE: 0
             UNITS:    kbits/sec           SPARSE:   NA
             DESCR:    NA "
::= {xdslChannelOperDataEntry 2}

xdslChannelActualInterleavingDelayDownstream     OBJECT-TYPE
        SYNTAX          INTEGER
        ACCESS          read-only
        STATUS          mandatory
        DESCRIPTION     
        "When the modem is in showtime, 
          - and RTX is not in use, then this object gives the actual delay 
            caused by the interleaving and deinterleaving functionality.
          - and RTX is in use, then this object gives the actual value of 
            the delay due to combined effect of retransmission and optional
            interleaving.
         When the modem is not in showtime this object will have the value
         measured during the previous showtime session.
         When no data is available (e.g. before first showtime) value 0
         is used.
         Delay range is 0 to 255 ms in steps of 1 ms.

         ALCATEL NOTE:
             ACCESS:   NA                  USAGE:    NA
             PERSIST:  NO                  INSRVMOD: NA
             RANGE:    0..255              DEFVALUE: 0
             UNITS:    milliseconds        SPARSE:   NA
             DESCR:    NA "
::= {xdslChannelOperDataEntry 3}

xdslChannelActualImpNoiseProtDownstream          OBJECT-TYPE
        SYNTAX          INTEGER
        ACCESS          read-only
        STATUS          mandatory
        DESCRIPTION     
        " When the modem is in showtime :
           - and RTX is not in use, this object gives the actual impulse noise 
             Protection due to FEC and interleaving.
           - and RTX is in use, this object gives the actual impulse noise 
             Protection against SHINE.
         When the modem is not in showtime this object will have the value
         measured during the previous showtime session.
         When no data is available (e.g. before first showtime) value 0
         is used.
         Range is 0 to 204.6 symbols in steps of 0.1 symbol. The value 204.7
         indicates a value for ACTINP of 204.7 or higher.
         It is represented as 1/10 * xdslChannelActualImpNoiseProtDownstream.

         ALCATEL NOTE:
             ACCESS:   NA                  USAGE:    NA
             PERSIST:  NO                  INSRVMOD: NA
             RANGE:    0..2046             DEFVALUE: 0
             UNITS:    symbols / 10        SPARSE:   NA
             DESCR:    NA "
::= {xdslChannelOperDataEntry 4}

xdslChannelActualNetDataRateUpstream       OBJECT-TYPE
        SYNTAX          INTEGER
        ACCESS          read-only
        STATUS          mandatory
        DESCRIPTION     
        "When the modem is in showtime :
   - and RTX mode is in use: then this object gives the actual net data rate    
               that can be achieved when no impulse noise events occur. 
           - and RTX mode is not selected: then the same value as
               xdslChannelActualBitrateUpstream is returned.
         When not in showtime, then this object has the value measured in 
         preceeding showtime session. After an activation failure, this object 
         represents the value as available till activation failure. 
         When no data is available (e.g. before first showtime) value 0
         is used.

         ALCATEL NOTE:
             ACCESS:   NA                  USAGE:    NA
             PERSIST:  NO                  INSRVMOD: NA
             RANGE:    0..262143           DEFVALUE: 0
             UNITS:    kbits/sec           SPARSE:   NA
             DESCR:    NA "
::= {xdslChannelOperDataEntry 5}

xdslChannelActualImpNoiseProtReinDownstream          OBJECT-TYPE
        SYNTAX          INTEGER
        ACCESS          read-only
        STATUS          mandatory
        DESCRIPTION     
        "When the modem is in showtime: 
           - and RTX mode is in use: then this object gives the actual impulse
              noise protection against REIN.
           - and RTX mode is not in use: then value 0 is returned 
         When the modem is not in showtime this object will have the value
         measured during the previous showtime session.
         When no data is available (e.g. before first showtime) value 0
         is returned.
         Range is 0 to 25.4 symbols in steps of 0.1 symbol. A special value 
         of 25.5 indicates a value equal to 25.5 or higher.
         It is represented as 1/10 * xdslChannelActualImpNoiseProtDownstream.

         ALCATEL NOTE:
             ACCESS:   NA                  USAGE:    NA
             PERSIST:  NO                  INSRVMOD: NA
             RANGE:    0..255              DEFVALUE: 0
             UNITS:    symbols / 10        SPARSE:   NA
             DESCR:    NA "
::= {xdslChannelOperDataEntry 6}

xdslChannelAttainableNetDataRateUpstream  OBJECT-TYPE
        SYNTAX          INTEGER
        ACCESS          read-only
        STATUS          mandatory
        DESCRIPTION     
        "When the modem is in showtime :
           - and RTX mode is in use: then this object gives an estimation of the 
             highest achievable NDR. 
           - and RTX mode is not selected: then the same value as
             xdslChannelAttainableBitrateUpstream is returned.
         When not in showtime, then this object has the value measured in 
         preceeding showtime session. After an activation failure, this object 
         represents the value as available till activation failure. 
         When no data is available (e.g. before first showtime) value 0
         is used.

         ALCATEL NOTE:
             ACCESS:   NA                  USAGE:    NA
             PERSIST:  NO                  INSRVMOD: NA
             RANGE:    0..262143           DEFVALUE: 0
             UNITS:    kbits/sec           SPARSE:   NA
             DESCR:    NA "
::= {xdslChannelOperDataEntry 7}

xdslChannelCurrentIntervalTable        OBJECT-TYPE
        SYNTAX          SEQUENCE OF XdslChannelCurrentIntervalEntry
        ACCESS          not-accessible
        STATUS          mandatory
        DESCRIPTION     
        "The xdsl channel current interval table.

         ALCATEL NOTE:
             TABLESIZE: DEP [number of XDSL lines * maximum number of channels
                             per XDSL line (1)]                    
             DESCR:     NA                   "
::= {xdslChannelCurrent 2}

xdslChannelCurrentIntervalEntry        OBJECT-TYPE
        SYNTAX          XdslChannelCurrentIntervalEntry
        ACCESS          not-accessible
        STATUS          mandatory
        DESCRIPTION     
        "An entry in the xdsl channel current interval table.

         Row creation : Entries for all XDSL channels belonging to a board are 
                        created when the board becomes operational.
         Row deletion : Entries for all XDSL channels belonging to a board are 
                        deleted when the board becomes unavailable. "
        INDEX          {ifIndex}
::= {xdslChannelCurrentIntervalTable 1}

XdslChannelCurrentIntervalEntry ::=
        SEQUENCE {
            xdslChannelCurrentIntervalCVs             Counter,
            xdslChannelCurrentIntervalFECCs           Counter,
            xdslChannelCurrentIntervalMeasuredTime    INTEGER,
            xdslChannelCurrentIntervalInvalidDataFlag INTEGER,
            xdslChannelCurrentIntervalCECs            Counter
        }

xdslChannelCurrentIntervalCVs          OBJECT-TYPE
        SYNTAX          Counter
        ACCESS          read-only
        STATUS          mandatory
        DESCRIPTION     
        "The counter associated with the number of Coding Violations
         encountered by the channel in the current 15 minute interval.

         ALCATEL NOTE:
             ACCESS:   NA                  USAGE:    NA
             PERSIST:  NO                  INSRVMOD: NA
             RANGE:    NA                  DEFVALUE: 0
             UNITS:    NA                  SPARSE:   NA
             DESCR:    NA "
::= {xdslChannelCurrentIntervalEntry 1}

xdslChannelCurrentIntervalFECCs        OBJECT-TYPE
        SYNTAX          Counter
        ACCESS          read-only
        STATUS          mandatory
        DESCRIPTION     
        "The counter associated with the number of corrected codewords 
         encountered by the channel, respectively corrected octets in case of
         VDSL G.993.1, in the current 15 minute interval. If more 
         than one error occurs per superframe then only 1 is reported.

         ALCATEL NOTE:
             ACCESS:   NA                  USAGE:    NA
             PERSIST:  NO                  INSRVMOD: NA
             RANGE:    NA                  DEFVALUE: 0
             UNITS:    NA                  SPARSE:   NA
             DESCR:    NA "
::= {xdslChannelCurrentIntervalEntry 2}

xdslChannelCurrentIntervalMeasuredTime OBJECT-TYPE
        SYNTAX          INTEGER(0..900)
        ACCESS          read-only
        STATUS          mandatory
        DESCRIPTION     
        "The amount of time, measured in seconds, that statistics for this
         entry have been counted.

         ALCATEL NOTE:
             ACCESS:   NA                  USAGE:    NA
             PERSIST:  NO                  INSRVMOD: NA
             RANGE:    NA                  DEFVALUE: 0
             UNITS:    seconds             SPARSE:   NA
             DESCR:    NA "
::= {xdslChannelCurrentIntervalEntry 3}

xdslChannelCurrentIntervalInvalidDataFlag        OBJECT-TYPE
        SYNTAX          INTEGER
        ACCESS          read-only
        STATUS          mandatory
        DESCRIPTION     
        "This object indicates the validity of the corresponding PM data.
         It is set to 1 when the PM data is incomplete or invalid and set to 0
         when the PM data is complete and valid.

         ALCATEL NOTE:
             ACCESS:   NA                  USAGE:    NA
             PERSIST:  NO                  INSRVMOD: NA
             RANGE:    0..1                DEFVALUE: 1
             UNITS:    NA                  SPARSE:   NA
             DESCR:    NA "
::= {xdslChannelCurrentIntervalEntry 4}

xdslChannelCurrentIntervalCECs         OBJECT-TYPE
        SYNTAX          Counter
        ACCESS          read-only
        STATUS          mandatory
        DESCRIPTION
        "The counter associated with the number of uncorrected codewords errors
         encountered by the far end channel in the current 15 minute interval
         in VDSL2 mode.

         ALCATEL NOTE:
             ACCESS:   NA                  USAGE:    NA
             PERSIST:  NO                  INSRVMOD: NA
             RANGE:    NA                  DEFVALUE: 0
             UNITS:    NA                  SPARSE:   NA
             DESCR:    NA "
::= {xdslChannelCurrentIntervalEntry 5}

xdslChannelCurrent1DayTable            OBJECT-TYPE
        SYNTAX          SEQUENCE OF XdslChannelCurrent1DayEntry
        ACCESS          not-accessible
        STATUS          mandatory
        DESCRIPTION     
        "The xdsl channel near end current 1 day table.

         ALCATEL NOTE:
             TABLESIZE: DEP [number of XDSL lines * maximum number of channels
                             per XDSL line (1)]                    
             DESCR:     NA                   "
::= {xdslChannelCurrent 3}
        
xdslChannelCurrent1DayEntry            OBJECT-TYPE
        SYNTAX          XdslChannelCurrent1DayEntry                     
        ACCESS          not-accessible
        STATUS          mandatory
        DESCRIPTION     
         "An entry in the xdsl channel near end current 1 day table.

         Row creation : Entries for all XDSL channels belonging to a board are 
                        created when the board becomes operational.
         Row deletion : Entries for all XDSL channels belonging to a board are 
                        deleted when the board becomes unavailable. "
        INDEX          {ifIndex}
::= {xdslChannelCurrent1DayTable 1}

XdslChannelCurrent1DayEntry ::=
        SEQUENCE {
            xdslChannelCurrent1DayCVs                 Counter,
            xdslChannelCurrent1DayFECCs               Counter,
            xdslChannelCurrent1DayMeasuredTime        INTEGER,
            xdslChannelCurrent1DayInvalidDataFlag     INTEGER,
            xdslChannelCurrent1DayCECs                Counter
        }

xdslChannelCurrent1DayCVs              OBJECT-TYPE
        SYNTAX          Counter
        ACCESS          read-only
        STATUS          mandatory
        DESCRIPTION     
        "The counter associated with the number of Coding Violations 
         encountered by the channel in the current 1 day interval.

         ALCATEL NOTE:
             ACCESS:   NA                  USAGE:    NA
             PERSIST:  NO                  INSRVMOD: NA
             RANGE:    NA                  DEFVALUE: 0
             UNITS:    NA                  SPARSE:   NA
             DESCR:    NA "
::= {xdslChannelCurrent1DayEntry 1}

xdslChannelCurrent1DayFECCs            OBJECT-TYPE
        SYNTAX          Counter
        ACCESS          read-only
        STATUS          mandatory
        DESCRIPTION     
        "The counter associated with the number of corrected codewords 
         encountered by the channel, respectively corrected octets in case of
         VDSL G.993.1, in the current 1 day interval. If more than
         one error occurs per superframe then only 1 is reported.

         ALCATEL NOTE:
             ACCESS:   NA                  USAGE:    NA
             PERSIST:  NO                  INSRVMOD: NA
             RANGE:    NA                  DEFVALUE: 0
             UNITS:    NA                  SPARSE:   NA
             DESCR:    NA "
::= {xdslChannelCurrent1DayEntry 2}

xdslChannelCurrent1DayMeasuredTime     OBJECT-TYPE
        SYNTAX          INTEGER(0..86400)
        ACCESS          read-only
        STATUS          mandatory
        DESCRIPTION     
        "The amount of time, measured in seconds, that statistics for this
         entry have been counted.

         ALCATEL NOTE:
             ACCESS:   NA                  USAGE:    NA
             PERSIST:  NO                  INSRVMOD: NA
             RANGE:    NA                  DEFVALUE: 0
             UNITS:    seconds             SPARSE:   NA
             DESCR:    NA "
::= {xdslChannelCurrent1DayEntry 3}

xdslChannelCurrent1DayInvalidDataFlag  OBJECT-TYPE
        SYNTAX          INTEGER
        ACCESS          read-only
        STATUS          mandatory
        DESCRIPTION     
        "This object indicates the validity of the corresponding PM data.
         It is set to 1 when the PM data is incomplete or invalid and set to 0
         when the PM data is complete and valid.

         ALCATEL NOTE:
             ACCESS:   NA                  USAGE:    NA
             PERSIST:  NO                  INSRVMOD: NA
             RANGE:    0..1                DEFVALUE: 1
             UNITS:    NA                  SPARSE:   NA
             DESCR:    NA "
::= {xdslChannelCurrent1DayEntry 4}

xdslChannelCurrent1DayCECs             OBJECT-TYPE
        SYNTAX          Counter
        ACCESS          read-only
        STATUS          mandatory
        DESCRIPTION
        "The counter associated with the number of uncorrected codewords errors
         encountered by the far end channel in the current 15 minute interval
         in VDSL2 mode.

         ALCATEL NOTE:
             ACCESS:   NA                  USAGE:    NA
             PERSIST:  NO                  INSRVMOD: NA
             RANGE:    NA                  DEFVALUE: 0
             UNITS:    NA                  SPARSE:   NA
             DESCR:    NA "
::= {xdslChannelCurrent1DayEntry 5}

xdslChannelPreviousIntervalTable       OBJECT-TYPE
        SYNTAX          SEQUENCE OF XdslChannelPreviousIntervalEntry
        ACCESS          not-accessible
        STATUS          mandatory
        DESCRIPTION     
        "The xdsl channel previous interval table.

         ALCATEL NOTE:
             TABLESIZE: DEP [number of XDSL lines * maximum number of channels
                             per XDSL line (1) * 192]                    
             DESCR:     NA                   "
::= {xdslChannelPrevious 1}

xdslChannelPreviousIntervalEntry       OBJECT-TYPE
        SYNTAX          XdslChannelPreviousIntervalEntry
        ACCESS          not-accessible
        STATUS          mandatory
        DESCRIPTION     
        "An entry in the xdsl channel previous interval table.

         Row creation : Entries for all XDSL channels belonging to a board are 
                        created when the board becomes operational.
         Row deletion : Entries for all XDSL channels belonging to a board are 
                        deleted when the board becomes unavailable. "
        INDEX          {ifIndex, 
                        xdslChannelPreviousIntervalNumber}
::= {xdslChannelPreviousIntervalTable 1}

XdslChannelPreviousIntervalEntry ::=
        SEQUENCE {
            xdslChannelPreviousIntervalNumber           INTEGER,
            xdslChannelPreviousIntervalCVs              Counter,
            xdslChannelPreviousIntervalFECCs            Counter,
            xdslChannelPreviousIntervalMeasuredTime     INTEGER,
            xdslChannelPreviousIntervalInvalidDataFlag  INTEGER,
            xdslChannelPreviousIntervalCECs             Counter
        }
        
xdslChannelPreviousIntervalNumber      OBJECT-TYPE
        SYNTAX          INTEGER(1..192)
        ACCESS          read-only
        STATUS          mandatory
        DESCRIPTION     
        "A number between 1 and 192, which identifies the interval for which
         the set of statistics is available. The interval identified by 1 is
         the most recently completed 15 minute interval, and the interval
         identified by N is the interval immediately preceding the one 
         identified by N-1.

         ALCATEL NOTE:
             ACCESS:   NA                  USAGE:    NA
             PERSIST:  NO                  INSRVMOD: NA
             RANGE:    NA                  DEFVALUE: NA
             UNITS:    NA                  SPARSE:   NA
             DESCR:    NA "
::= {xdslChannelPreviousIntervalEntry 1}

xdslChannelPreviousIntervalCVs         OBJECT-TYPE
        SYNTAX          Counter
        ACCESS          read-only
        STATUS          mandatory
        DESCRIPTION     
        "The counter associated with the number of Coding Violations
         encountered by the channel in a particular 15 minute interval.

         ALCATEL NOTE:
             ACCESS:   NA                  USAGE:    NA
             PERSIST:  NO                  INSRVMOD: NA
             RANGE:    NA                  DEFVALUE: 0
             UNITS:    NA                  SPARSE:   NA
             DESCR:    NA "
::= {xdslChannelPreviousIntervalEntry 2}

xdslChannelPreviousIntervalFECCs       OBJECT-TYPE
        SYNTAX          Counter
        ACCESS          read-only
        STATUS          mandatory
        DESCRIPTION     
        "The counter associated with the number of corrected codewords 
         encountered by the channel, respectively corrected octets in case of
         VDSL G.993.1, in a particular 15 minute interval. 
         If more than one error occurs per superframe then only
         1 is reported.

         ALCATEL NOTE:
             ACCESS:   NA                  USAGE:    NA
             PERSIST:  NO                  INSRVMOD: NA
             RANGE:    NA                  DEFVALUE: 0
             UNITS:    NA                  SPARSE:   NA
             DESCR:    NA "
::= {xdslChannelPreviousIntervalEntry 3}

xdslChannelPreviousIntervalMeasuredTime          OBJECT-TYPE
        SYNTAX          INTEGER(0..900)
        ACCESS          read-only
        STATUS          mandatory
        DESCRIPTION     
        "The amount of time, measured in seconds, that statistics for this 
         entry have been counted.

         ALCATEL NOTE:
             ACCESS:   NA                  USAGE:    NA
             PERSIST:  NO                  INSRVMOD: NA
             RANGE:    NA                  DEFVALUE: 0
             UNITS:    seconds             SPARSE:   NA
             DESCR:    NA "
::= {xdslChannelPreviousIntervalEntry 4}

xdslChannelPreviousIntervalInvalidDataFlag       OBJECT-TYPE
        SYNTAX          INTEGER
        ACCESS          read-only
        STATUS          mandatory
        DESCRIPTION     
        "This object indicates the validity of the corresponding PM data.
         It is set to 1 when the PM data is incomplete or invalid and set to 0
         when the PM data is complete and valid.

         ALCATEL NOTE:
             ACCESS:   NA                  USAGE:    NA
             PERSIST:  NO                  INSRVMOD: NA
             RANGE:    0..1                DEFVALUE: 1
             UNITS:    NA                  SPARSE:   NA
             DESCR:    NA "
::= {xdslChannelPreviousIntervalEntry 5}

xdslChannelPreviousIntervalCECs        OBJECT-TYPE
        SYNTAX          Counter
        ACCESS          read-only
        STATUS          mandatory
        DESCRIPTION
        "The counter associated with the number of uncorrected codewords errors
         encountered by the far end channel in a particular 15 minute interval
         in VDSL2 mode.

         ALCATEL NOTE:
             ACCESS:   NA                  USAGE:    NA
             PERSIST:  NO                  INSRVMOD: NA
             RANGE:    NA                  DEFVALUE: 0
             UNITS:    NA                  SPARSE:   NA
             DESCR:    NA "
::= {xdslChannelPreviousIntervalEntry 6}

xdslChannelPrevious1DayTable           OBJECT-TYPE
        SYNTAX          SEQUENCE OF XdslChannelPrevious1DayEntry
        ACCESS          not-accessible
        STATUS          mandatory
        DESCRIPTION     
        "The xdsl channel near end previous 1 day table.

         ALCATEL NOTE:
             TABLESIZE: DEP [number of XDSL lines * maximum number of channels
                             per XDSL line (1) * number of days (1)]                   
             DESCR:     NA                   "
::= {xdslChannelPrevious 2}
        
xdslChannelPrevious1DayEntry           OBJECT-TYPE
        SYNTAX  XdslChannelPrevious1DayEntry                    
        ACCESS  not-accessible
        STATUS  mandatory
        DESCRIPTION     
        "An entry in the xdsl channel near end previous 1 day table.

         Row creation : Entries for all XDSL channels belonging to a board are 
                        created when the board becomes operational.
         Row deletion : Entries for all XDSL channels belonging to a board are 
                        deleted when the board becomes unavailable. "
        INDEX          {ifIndex, 
                        xdslChannelPrevious1DayNumber}
::= {xdslChannelPrevious1DayTable 1}

XdslChannelPrevious1DayEntry ::=
        SEQUENCE {
            xdslChannelPrevious1DayNumber             INTEGER,
            xdslChannelPrevious1DayCVs                Counter,
            xdslChannelPrevious1DayFECCs              Counter,
            xdslChannelPrevious1DayMeasuredTime       INTEGER,
            xdslChannelPrevious1DayInvalidDataFlag    INTEGER,
            xdslChannelPrevious1DayCECs               Counter
        }

xdslChannelPrevious1DayNumber          OBJECT-TYPE
        SYNTAX          INTEGER(1..7)
        ACCESS          read-only
        STATUS          mandatory
        DESCRIPTION     
        "A number between 1 and 7, which identifies the day for which the 
         set of statistics is available. The day identified by 1 is the 
         most recently completed 1Day, and the day identified 
         by N is the day immediately preceding the one identified by N-1.

         ALCATEL NOTE:
             ACCESS:   NA                  USAGE:    NA
             PERSIST:  NO                  INSRVMOD: NA
             RANGE:    1                   DEFVALUE: NA
             UNITS:    NA                  SPARSE:   NA
             DESCR:    Only statistics for one previous day is kept. "
::= {xdslChannelPrevious1DayEntry 1}

xdslChannelPrevious1DayCVs             OBJECT-TYPE
        SYNTAX          Counter
        ACCESS          read-only
        STATUS          mandatory
        DESCRIPTION     
        "The counter associated with the number of Coding Violations
         encountered by the channel in the previous 1 day interval.

         ALCATEL NOTE:
             ACCESS:   NA                  USAGE:    NA
             PERSIST:  NO                  INSRVMOD: NA
             RANGE:    NA                  DEFVALUE: 0
             UNITS:    NA                  SPARSE:   NA
             DESCR:    NA "
::= {xdslChannelPrevious1DayEntry 2}

xdslChannelPrevious1DayFECCs           OBJECT-TYPE
        SYNTAX          Counter
        ACCESS          read-only
        STATUS          mandatory
        DESCRIPTION     
        "The counter associated with the number of corrected codewords
         encountered by the channel, respectively corrected octets in case of
         VDSL G.993.1, in the previous 1 day interval.
         If more than one error occurs per superframe then only 1 is reported.

         ALCATEL NOTE:
             ACCESS:   NA                  USAGE:    NA
             PERSIST:  NO                  INSRVMOD: NA
             RANGE:    NA                  DEFVALUE: 0
             UNITS:    NA                  SPARSE:   NA
             DESCR:    NA "
::= {xdslChannelPrevious1DayEntry 3}

xdslChannelPrevious1DayMeasuredTime    OBJECT-TYPE
        SYNTAX          INTEGER(0..86400)
        ACCESS          read-only
        STATUS          mandatory
        DESCRIPTION     
        "The amount of time, measured in seconds, that statistics for this
         entry have been counted.

         ALCATEL NOTE:
             ACCESS:   NA                  USAGE:    NA
             PERSIST:  NO                  INSRVMOD: NA
             RANGE:    NA                  DEFVALUE: 0
             UNITS:    seconds             SPARSE:   NA
             DESCR:    NA "
::= {xdslChannelPrevious1DayEntry 4}

xdslChannelPrevious1DayInvalidDataFlag OBJECT-TYPE
        SYNTAX          INTEGER
        ACCESS          read-only
        STATUS          mandatory
        DESCRIPTION     
        "This object indicates the validity of the corresponding PM data.
         It is set to 1 when the PM data is incomplete or invalid and set to 0
         when the PM data is complete and valid.

         ALCATEL NOTE:
             ACCESS:   NA                  USAGE:    NA
             PERSIST:  NO                  INSRVMOD: NA
             RANGE:    0..1                DEFVALUE: 1
             UNITS:    NA                  SPARSE:   NA
             DESCR:    NA "
::= {xdslChannelPrevious1DayEntry 5}

xdslChannelPrevious1DayCECs            OBJECT-TYPE
        SYNTAX  Counter
        ACCESS  read-only
        STATUS  mandatory
        DESCRIPTION
        "The counter associated with the number of uncorrected codewords errors
         encountered by the far end channel in the previous 1 day interval
         in VDSL2 mode.

         ALCATEL NOTE:
             ACCESS:   NA                  USAGE:    NA
             PERSIST:  NO                  INSRVMOD: NA
             RANGE:    NA                  DEFVALUE: 0
             UNITS:    NA                  SPARSE:   NA
             DESCR:    NA "
::= {xdslChannelPrevious1DayEntry 6}

xdslFarEndChannelOperDataTable         OBJECT-TYPE
        SYNTAX          SEQUENCE OF XdslFarEndChannelOperDataEntry
        ACCESS          not-accessible
        STATUS          mandatory
        DESCRIPTION     
        "The xdsl far end channel operational data table.

         ALCATEL NOTE:
             TABLESIZE: DEP [number of XDSL lines * maximum number of channels
                             per XDSL line (1)]                    
             DESCR:     NA                   "
::= {xdslFarEndChannelCurrent 1}

xdslFarEndChannelOperDataEntry         OBJECT-TYPE
        SYNTAX          XdslFarEndChannelOperDataEntry
        ACCESS          not-accessible
        STATUS          mandatory
        DESCRIPTION     
        "An entry in the xdsl far end channel operational data table.

         Row creation : Entries for all XDSL channels belonging to a board are 
                        created when the board becomes operational.
         Row deletion : Entries for all XDSL channels belonging to a board are 
                        deleted when the board becomes unavailable. "
        INDEX          {ifIndex}
::= {xdslFarEndChannelOperDataTable 1}

XdslFarEndChannelOperDataEntry ::=
        SEQUENCE {
            xdslFarEndChannelActualBitrateDownstream           INTEGER,
            xdslFarEndChannelAttainableBitrateDownstream       INTEGER,
            xdslFarEndChannelActualInterleavingDelayUpstream   INTEGER,
            xdslFarEndChannelActualImpNoiseProtUpstream        INTEGER,
            xdslFarEndChannelActualL2LowPowerBitrateDownstream INTEGER,
            xdslFarEndChannelActualNetDataRateDownstream       INTEGER,
            xdslFarEndChannelActualImpNoiseProtReinUpstream    INTEGER,
            xdslFarEndChannelAttainableNetDataRateDownstream   INTEGER
        }

xdslFarEndChannelActualBitrateDownstream         OBJECT-TYPE
        SYNTAX          INTEGER
        ACCESS          read-only
        STATUS          mandatory
        DESCRIPTION     
        "When the modem is in showtime,
          - and RTX is not in use, then this object gives the actual net
            data rate for the downstream fast or interleaved data flow.
          - and RTX is in use, then this object gives the expected throughput
             for the downstream retransmission channel data flow.
         When not in showtime, then this object has the value measured in 
         preceeding showtime session. After an activation failure, this object
         represents the value as available till activation failure. 
         A value 0 means that no data is available.

         ALCATEL NOTE:
             ACCESS:   NA                  USAGE:    NA
             PERSIST:  NO                  INSRVMOD: NA
             RANGE:    0..262143           DEFVALUE: 0
             UNITS:    kbits/sec           SPARSE:   NA
             DESCR:    NA "
::= {xdslFarEndChannelOperDataEntry 1}

xdslFarEndChannelAttainableBitrateDownstream     OBJECT-TYPE
        SYNTAX          INTEGER
        ACCESS          read-only
        STATUS          mandatory
        DESCRIPTION 
        " When the modem is in showtime,.
           - and RTX is not in use, then this object contains the maximum 
             attainable net data rate the modem can support on corresponding 
             channel.
   - and RTX is in use, then this object contains the attainable expected 
     Throughput.
         When the modem is not in showtime this object will have the value
         measured during the previous showtime session.
         When no data is available (e.g. before first showtime) value 0
         is used. 

         ALCATEL NOTE:
             ACCESS:   NA                  USAGE:    NA
             PERSIST:  NO                  INSRVMOD: NA
             RANGE:    0..262143           DEFVALUE: 0
             UNITS:    kbit/sec            SPARSE:   NA
             DESCR:    NA "
::= {xdslFarEndChannelOperDataEntry 2}

xdslFarEndChannelActualInterleavingDelayUpstream OBJECT-TYPE
        SYNTAX          INTEGER
        ACCESS          read-only
        STATUS          mandatory
        DESCRIPTION     
        "When the modem is in showtime, 
          - and RTX is not in use, then this object gives the actual delay 
            caused by the interleaving and deinterleaving functionality.
          - and RTX is in use, then this object gives the actual value of 
            the delay due to combined effect of retransmission and optional
            interleaving.
         When the modem is not in showtime this object will have the value
         measured during the previous showtime session.
         When no data is available (e.g. before first showtime) value 0
         is used.
         Delay range is 0 to 255 ms in steps of 1 ms.

         ALCATEL NOTE:
             ACCESS:   NA                  USAGE:    NA
             PERSIST:  NO                  INSRVMOD: NA
             RANGE:    0..255              DEFVALUE: 0
             UNITS:    milliseconds        SPARSE:   NA
             DESCR:    NA "
::= {xdslFarEndChannelOperDataEntry 3}

xdslFarEndChannelActualImpNoiseProtUpstream      OBJECT-TYPE
        SYNTAX          INTEGER
        ACCESS          read-only
        STATUS          mandatory
        DESCRIPTION     
        " When the modem is in showtime, 
           - and RTX is not in use, this object gives the actual impulse noise
             protection.
           - and RTX is in use, then this object gives the actual impulse noise
             Protection against SHINE. 
         When the modem is not in showtime this object will have the value
         measured during the previous showtime session.
         When no data is available (e.g. before first showtime) value 0
         is used.
         Range is 0 to 204.6 symbols in steps of 0.1 symbol. The value 204.7
         indicates a value for ACTINP of 204.7 or higher.
         It is represented as 1/10 * 
         xdslFarEndChannelActualImpNoiseProtUpstream 

         ALCATEL NOTE:
             ACCESS:   NA                  USAGE:    NA
             PERSIST:  NO                  INSRVMOD: NA
             RANGE:    0..2046             DEFVALUE: 0
             UNITS:    symbols / 10        SPARSE:   NA
             DESCR:    NA "
::= {xdslFarEndChannelOperDataEntry 4}

xdslFarEndChannelActualL2LowPowerBitrateDownstream         OBJECT-TYPE
        SYNTAX          INTEGER
        ACCESS          read-only
        STATUS          mandatory
        DESCRIPTION     
        "When the modem is in the L2 Low Power state, then this object gives
         the actual L2 net data rate for the downstream channel data flow. When 
         not in L2, then this object has the value measured in preceeding L2 
         state. A value 0 means that no data is available.

         ALCATEL NOTE:
             ACCESS:   NA                  USAGE:    NA
             PERSIST:  NO                  INSRVMOD: NA
             RANGE:    0..262143           DEFVALUE: 0
             UNITS:    kbits/sec           SPARSE:   NA
             DESCR:    NA "
::= {xdslFarEndChannelOperDataEntry 5}

xdslFarEndChannelActualNetDataRateDownstream         OBJECT-TYPE
        SYNTAX          INTEGER
        ACCESS          read-only
        STATUS          mandatory
        DESCRIPTION     
        "When the modem is in showtime:
          - and RTX mode is in use: then this object gives the actual 
            net data rate that can be achieved  when no impulse noise events occur.
          - and RTX mode is not in use: then the same value as       
            xdslFarEndChannelActualBitrateDownstream is returned.
         When not in showtime, then this object has the value measured in 
           preceeding showtime session. After an activation failure, this object 
         represents the value as available till activation failure. 
         A value 0 means that no data is available.

         ALCATEL NOTE:
             ACCESS:   NA                  USAGE:    NA
             PERSIST:  NO                  INSRVMOD: NA
             RANGE:    0..262143           DEFVALUE: 0
             UNITS:    kbits/sec           SPARSE:   NA
             DESCR:    NA "
::= {xdslFarEndChannelOperDataEntry 6}

xdslFarEndChannelActualImpNoiseProtReinUpstream      OBJECT-TYPE
        SYNTAX          INTEGER
        ACCESS          read-only
        STATUS          mandatory
        DESCRIPTION     
        " When the modem is in showtime:
           - and RTX is in use, then this object gives the actual impulse noise
              protection against REIN.
           - and RTX is not in use, then the value 0 will be returned.
         When the modem is not in showtime this object will have the value
         measured during the previous showtime session.
         When no data is available (e.g. before first showtime) value 0
         is used.
         Range is 0 to 25.4 symbols in steps of 0.1 symbol. 
         A special value 25.5 indicates a value equal or higher then 25.5.
         It is represented as 1/10 * xdslFarEndChannelActualImpNoiseProtReinUpstream 

         ALCATEL NOTE:
             ACCESS:   NA                  USAGE:    NA
             PERSIST:  NO                  INSRVMOD: NA
             RANGE:    0..255              DEFVALUE: 0
             UNITS:    symbols / 10        SPARSE:   NA
             DESCR:    NA "
::= {xdslFarEndChannelOperDataEntry 7}

xdslFarEndChannelAttainableNetDataRateDownstream   OBJECT-TYPE
        SYNTAX          INTEGER
        ACCESS          read-only
        STATUS          mandatory
        DESCRIPTION     
        "When the modem is in showtime:
          - and RTX mode is in use: then this object gives an estimation of the 
            highest achievable NDR
          - and RTX mode is not in use: then the same value as       
            xdslFarEndChannelAttainableBitrateDownstream is returned.
         When not in showtime, then this object has the value measured in 
           preceeding showtime session. After an activation failure, this object 
         represents the value as available till activation failure. 
         A value 0 means that no data is available.

         ALCATEL NOTE:
             ACCESS:   NA                  USAGE:    NA
             PERSIST:  NO                  INSRVMOD: NA
             RANGE:    0..262143           DEFVALUE: 0
             UNITS:    kbits/sec           SPARSE:   NA
             DESCR:    NA "
::= {xdslFarEndChannelOperDataEntry 8}

xdslFarEndChannelCurrentIntervalTable  OBJECT-TYPE
        SYNTAX          SEQUENCE OF XdslFarEndChannelCurrentIntervalEntry
        ACCESS          not-accessible
        STATUS          mandatory
        DESCRIPTION     
        "The xdsl far end channel current interval table.

         ALCATEL NOTE:
             TABLESIZE: DEP [number of XDSL lines * maximum number of channels
                             per XDSL line (1)]                    
             DESCR:     NA                   "
::= {xdslFarEndChannelCurrent 2}

xdslFarEndChannelCurrentIntervalEntry  OBJECT-TYPE
        SYNTAX          XdslFarEndChannelCurrentIntervalEntry
        ACCESS          not-accessible
        STATUS          mandatory
        DESCRIPTION     
        "An entry in the xdsl far end channel current interval table.

         Row creation : Entries for all XDSL channels belonging to a board are 
                        created when the board becomes operational.
         Row deletion : Entries for all XDSL channels belonging to a board are 
                        deleted when the board becomes unavailable. "
        INDEX          {ifIndex}
::= {xdslFarEndChannelCurrentIntervalTable 1}

XdslFarEndChannelCurrentIntervalEntry ::=
        SEQUENCE {
            xdslFarEndChannelCurrentIntervalCVs             Counter,
            xdslFarEndChannelCurrentIntervalFECCs           Counter,
            xdslFarEndChannelCurrentIntervalMeasuredTime    INTEGER,
            xdslFarEndChannelCurrentIntervalInvalidDataFlag INTEGER,
            xdslFarEndChannelCurrentIntervalCECs            Counter
        }

xdslFarEndChannelCurrentIntervalCVs    OBJECT-TYPE
        SYNTAX          Counter
        ACCESS          read-only
        STATUS          mandatory
        DESCRIPTION     
        "The counter associated with the number of Coding Violations
         encountered by the far end channel in the current 15 minute interval.

         ALCATEL NOTE:
             ACCESS:   NA                  USAGE:    NA
             PERSIST:  NO                  INSRVMOD: NA
             RANGE:    NA                  DEFVALUE: 0
             UNITS:    NA                  SPARSE:   NA
             DESCR:    NA "
::= {xdslFarEndChannelCurrentIntervalEntry 1}

xdslFarEndChannelCurrentIntervalFECCs  OBJECT-TYPE
        SYNTAX          Counter
        ACCESS          read-only
        STATUS          mandatory
        DESCRIPTION     
        "The counter associated with the number of corrected codewords
         encountered by the far end channel, respectively corrected octets in case of
         VDSL G.993.1, in the current 15 minute interval.
         If more than one error occurs per superframe then only 1 is reported.

         ALCATEL NOTE:
             ACCESS:   NA                  USAGE:    NA
             PERSIST:  NO                  INSRVMOD: NA
             RANGE:    NA                  DEFVALUE: 0
             UNITS:    NA                  SPARSE:   NA
             DESCR:    NA "
::= {xdslFarEndChannelCurrentIntervalEntry 2}

xdslFarEndChannelCurrentIntervalMeasuredTime     OBJECT-TYPE
        SYNTAX          INTEGER(0..900)
        ACCESS          read-only
        STATUS          mandatory
        DESCRIPTION     
        "The amount of time, measured in seconds, that statistics for this
         entry have been counted.

         ALCATEL NOTE:
             ACCESS:   NA                  USAGE:    NA
             PERSIST:  NO                  INSRVMOD: NA
             RANGE:    NA                  DEFVALUE: 0
             UNITS:    seconds             SPARSE:   NA
             DESCR:    NA "
::= {xdslFarEndChannelCurrentIntervalEntry 3}

xdslFarEndChannelCurrentIntervalInvalidDataFlag  OBJECT-TYPE
        SYNTAX          INTEGER
        ACCESS          read-only
        STATUS          mandatory
        DESCRIPTION     
        "This object indicates the validity of the corresponding PM data.
         It is set to 1 when the PM data is incomplete or invalid and set to 0
         when the PM data is complete and valid.

         ALCATEL NOTE:
             ACCESS:   NA                  USAGE:    NA
             PERSIST:  NO                  INSRVMOD: NA
             RANGE:    0..1                DEFVALUE: 1
             UNITS:    NA                  SPARSE:   NA
             DESCR:    NA "
::= {xdslFarEndChannelCurrentIntervalEntry 4}

xdslFarEndChannelCurrentIntervalCECs   OBJECT-TYPE
        SYNTAX          Counter
        ACCESS          read-only
        STATUS          mandatory
        DESCRIPTION
        "The counter associated with the number of uncorrected codewords errors
         encountered by the far end channel in the current 15 minute interval
         in VDSL2 mode.

         ALCATEL NOTE:
             ACCESS:   NA                  USAGE:    NA
             PERSIST:  NO                  INSRVMOD: NA
             RANGE:    NA                  DEFVALUE: 0
             UNITS:    NA                  SPARSE:   NA
             DESCR:    NA "
::= {xdslFarEndChannelCurrentIntervalEntry 5}

xdslFarEndChannelCurrent1DayTable      OBJECT-TYPE
        SYNTAX          SEQUENCE OF XdslFarEndChannelCurrent1DayEntry
        ACCESS          not-accessible
        STATUS          mandatory
        DESCRIPTION     
        "The xdsl channel far end current 1 day table.

         ALCATEL NOTE:
             TABLESIZE: DEP [number of XDSL lines * maximum number of channels
                             per XDSL line (1)]                    
             DESCR:     NA                   "
::= {xdslFarEndChannelCurrent 3}
        
xdslFarEndChannelCurrent1DayEntry      OBJECT-TYPE
        SYNTAX  XdslFarEndChannelCurrent1DayEntry                       
        ACCESS  not-accessible
        STATUS  mandatory
        DESCRIPTION     
        "An entry in the xdsl channel far end current 1 day table.

         Row creation : Entries for all XDSL channels belonging to a board are 
                        created when the board becomes operational.
         Row deletion : Entries for all XDSL channels belonging to a board are 
                        deleted when the board becomes unavailable. "
        INDEX          {ifIndex}
::= {xdslFarEndChannelCurrent1DayTable 1}

XdslFarEndChannelCurrent1DayEntry ::=
        SEQUENCE {
            xdslFarEndChannelCurrent1DayCVs             Counter,
            xdslFarEndChannelCurrent1DayFECCs           Counter,
            xdslFarEndChannelCurrent1DayMeasuredTime    INTEGER,
            xdslFarEndChannelCurrent1DayInvalidDataFlag INTEGER,
            xdslFarEndChannelCurrent1DayCECs            Counter
        }

xdslFarEndChannelCurrent1DayCVs        OBJECT-TYPE
        SYNTAX          Counter
        ACCESS          read-only
        STATUS          mandatory
        DESCRIPTION     
        "The counter associated with the number of Coding Violations 
         encountered by the far end channel in the current 1 day interval.

         ALCATEL NOTE:
             ACCESS:   NA                  USAGE:    NA
             PERSIST:  NO                  INSRVMOD: NA
             RANGE:    NA                  DEFVALUE: 0
             UNITS:    NA                  SPARSE:   NA
             DESCR:    NA "
::= {xdslFarEndChannelCurrent1DayEntry 1}

xdslFarEndChannelCurrent1DayFECCs      OBJECT-TYPE
        SYNTAX          Counter
        ACCESS          read-only
        STATUS          mandatory
        DESCRIPTION     
        "The counter associated with the number of corrected codewords
         encountered by the far end channel, respectively corrected octets in case of
         VDSL G.993.1, in the current 1 day interval.
         If more than one error occurs per superframe then only 1 is reported.

         ALCATEL NOTE:
             ACCESS:   NA                  USAGE:    NA
             PERSIST:  NO                  INSRVMOD: NA
             RANGE:    NA                  DEFVALUE: 0
             UNITS:    NA                  SPARSE:   NA
             DESCR:    NA "
::= {xdslFarEndChannelCurrent1DayEntry 2}

xdslFarEndChannelCurrent1DayMeasuredTime         OBJECT-TYPE
        SYNTAX          INTEGER(0..86400)
        ACCESS          read-only
        STATUS          mandatory
        DESCRIPTION     
        "The amount of time, measured in seconds, that statistics for this
         entry have been counted.

         ALCATEL NOTE:
             ACCESS:   NA                  USAGE:    NA
             PERSIST:  NO                  INSRVMOD: NA
             RANGE:    NA                  DEFVALUE: 0
             UNITS:    seconds             SPARSE:   NA
             DESCR:    NA "
::= {xdslFarEndChannelCurrent1DayEntry 3}

xdslFarEndChannelCurrent1DayInvalidDataFlag      OBJECT-TYPE
        SYNTAX          INTEGER
        ACCESS          read-only
        STATUS          mandatory
        DESCRIPTION     
        "This object indicates the validity of the corresponding PM data.
         It is set to 1 when the PM data is incomplete or invalid and set to 0
         when the PM data is complete and valid.

         ALCATEL NOTE:
             ACCESS:   NA                  USAGE:    NA
             PERSIST:  NO                  INSRVMOD: NA
             RANGE:    0..1                DEFVALUE: 1
             UNITS:    NA                  SPARSE:   NA
             DESCR:    NA "
::= {xdslFarEndChannelCurrent1DayEntry 4}

xdslFarEndChannelCurrent1DayCECs       OBJECT-TYPE
        SYNTAX          Counter
        ACCESS          read-only
        STATUS          mandatory
        DESCRIPTION
        "The counter associated with the number of uncorrected codewords errors
         encountered by the far end channel in the current 1 day interval
         in VDSL2 mode.

         ALCATEL NOTE:
             ACCESS:   NA                  USAGE:    NA
             PERSIST:  NO                  INSRVMOD: NA
             RANGE:    NA                  DEFVALUE: 0
             UNITS:    NA                  SPARSE:   NA
             DESCR:    NA "
::= {xdslFarEndChannelCurrent1DayEntry 5}

xdslFarEndChannelPreviousIntervalTable OBJECT-TYPE
        SYNTAX          SEQUENCE OF XdslFarEndChannelPreviousIntervalEntry
        ACCESS          not-accessible
        STATUS          mandatory
        DESCRIPTION     
        "The xdsl far end channel previous interval table.
         ALCATEL NOTE:
             TABLESIZE: DEP [number of XDSL lines * maximum number of channels
                             per XDSL line (1) * 192]                    
             DESCR:     NA                   "
::= {xdslFarEndChannelPrevious 1}

xdslFarEndChannelPreviousIntervalEntry OBJECT-TYPE
        SYNTAX          XdslFarEndChannelPreviousIntervalEntry
        ACCESS          not-accessible
        STATUS          mandatory
        DESCRIPTION     
        "An entry in the xdsl far end channel previous interval table.

         Row creation : Entries for all XDSL channels belonging to a board are 
                        created when the board becomes operational.
         Row deletion : Entries for all XDSL channels belonging to a board are 
                        deleted when the board becomes unavailable. "
        INDEX          {ifIndex, 
                        xdslFarEndChannelPreviousIntervalNumber}
::= {xdslFarEndChannelPreviousIntervalTable 1}

XdslFarEndChannelPreviousIntervalEntry ::=
        SEQUENCE {
            xdslFarEndChannelPreviousIntervalNumber           INTEGER,
            xdslFarEndChannelPreviousIntervalCVs              Counter,
            xdslFarEndChannelPreviousIntervalFECCs            Counter,
            xdslFarEndChannelPreviousIntervalMeasuredTime     INTEGER,
            xdslFarEndChannelPreviousIntervalInvalidDataFlag  INTEGER,
            xdslFarEndChannelPreviousIntervalCECs             Counter
        }
        
xdslFarEndChannelPreviousIntervalNumber          OBJECT-TYPE
       SYNTAX           INTEGER(1..192)
       ACCESS           read-only
       STATUS           mandatory
       DESCRIPTION     
       "A number between 1 and 192, which identifies the interval for which the
        set of statistics is available. The interval identified by 1 is the
        most recently completed 15 minute interval, and the interval
        identified by N is the interval immediately preceding the one
        identified by N-1.

         ALCATEL NOTE:
             ACCESS:   NA                  USAGE:    NA
             PERSIST:  NO                  INSRVMOD: NA
             RANGE:    NA                  DEFVALUE: NA
             UNITS:    NA                  SPARSE:   NA
             DESCR:    NA "
::= {xdslFarEndChannelPreviousIntervalEntry 1}

xdslFarEndChannelPreviousIntervalCVs   OBJECT-TYPE
        SYNTAX          Counter
        ACCESS          read-only
        STATUS          mandatory
        DESCRIPTION     
        "The counter associated with the number of Coding Violations 
         encountered by the far end channel in a particular 15 minute interval.

         ALCATEL NOTE:
             ACCESS:   NA                  USAGE:    NA
             PERSIST:  NO                  INSRVMOD: NA
             RANGE:    NA                  DEFVALUE: 0
             UNITS:    NA                  SPARSE:   NA
             DESCR:    NA "
::= {xdslFarEndChannelPreviousIntervalEntry 2}

xdslFarEndChannelPreviousIntervalFECCs OBJECT-TYPE
        SYNTAX          Counter
        ACCESS          read-only
        STATUS          mandatory
        DESCRIPTION     
        "The counter associated with the number of corrected codewords 
         encountered by the far end channel, respectively corrected octets in case of
         VDSL G.993.1, in a particular 15 minute interval.
         If more than one error occurs per superframe then only 1 is reported.

         ALCATEL NOTE:
             ACCESS:   NA                  USAGE:    NA
             PERSIST:  NO                  INSRVMOD: NA
             RANGE:    NA                  DEFVALUE: 0
             UNITS:    NA                  SPARSE:   NA
             DESCR:    NA "
::= {xdslFarEndChannelPreviousIntervalEntry 3}

xdslFarEndChannelPreviousIntervalMeasuredTime    OBJECT-TYPE
        SYNTAX          INTEGER(0..900)
        ACCESS          read-only
        STATUS          mandatory
        DESCRIPTION     
        "The amount of time, measured in seconds, that statistics for this
         entry have been counted.

         ALCATEL NOTE:
             ACCESS:   NA                  USAGE:    NA
             PERSIST:  NO                  INSRVMOD: NA
             RANGE:    NA                  DEFVALUE: 0
             UNITS:    seconds             SPARSE:   NA
             DESCR:    NA "
::= {xdslFarEndChannelPreviousIntervalEntry 4}

xdslFarEndChannelPreviousIntervalInvalidDataFlag OBJECT-TYPE
        SYNTAX          INTEGER
        ACCESS          read-only
        STATUS          mandatory
        DESCRIPTION     
        "This object indicates the validity of the corresponding PM data.
         It is set to 1 when the PM data is incomplete or invalid and set to 0
         when the PM data is complete and valid.

         ALCATEL NOTE:
             ACCESS:   NA                  USAGE:    NA
             PERSIST:  NO                  INSRVMOD: NA
             RANGE:    0..1                DEFVALUE: 1
             UNITS:    NA                  SPARSE:   NA
             DESCR:    NA "
::= {xdslFarEndChannelPreviousIntervalEntry 5}

xdslFarEndChannelPreviousIntervalCECs  OBJECT-TYPE
        SYNTAX          Counter
        ACCESS          read-only
        STATUS          mandatory
        DESCRIPTION
        "The counter associated with the number of uncorrected codewords errors
         encountered by the far end channel in a particular 15 minute interval
         in VDSL2 mode.

         ALCATEL NOTE:
             ACCESS:   NA                  USAGE:    NA
             PERSIST:  NO                  INSRVMOD: NA
             RANGE:    NA                  DEFVALUE: 0
             UNITS:    NA                  SPARSE:   NA
             DESCR:    NA "
::= {xdslFarEndChannelPreviousIntervalEntry 6}

xdslFarEndChannelPrevious1DayTable     OBJECT-TYPE
        SYNTAX          SEQUENCE OF XdslFarEndChannelPrevious1DayEntry
        ACCESS          not-accessible
        STATUS          mandatory
        DESCRIPTION     
        "The xdsl channel far end previous 1 day table.

         ALCATEL NOTE:
             TABLESIZE: DEP [number of XDSL lines * maximum number of channels
                             per XDSL line (1) * number of days (1)]                    
             DESCR:     NA                   "
::= {xdslFarEndChannelPrevious 2}
        
xdslFarEndChannelPrevious1DayEntry     OBJECT-TYPE
        SYNTAX          XdslFarEndChannelPrevious1DayEntry                      
        ACCESS          not-accessible
        STATUS          mandatory
        DESCRIPTION     
        "An entry in the xdsl channel far end previous 1 day table.

         Row creation : Entries for all XDSL channels belonging to a board are 
                        created when the board becomes operational.
         Row deletion : Entries for all XDSL channels belonging to a board are 
                        deleted when the board becomes unavailable. "
        INDEX          {ifIndex, 
                        xdslFarEndChannelPrevious1DayNumber}
::= {xdslFarEndChannelPrevious1DayTable 1}

XdslFarEndChannelPrevious1DayEntry ::=
        SEQUENCE {
            xdslFarEndChannelPrevious1DayNumber             INTEGER,
            xdslFarEndChannelPrevious1DayCVs                Counter,
            xdslFarEndChannelPrevious1DayFECCs              Counter,
            xdslFarEndChannelPrevious1DayMeasuredTime       INTEGER,
            xdslFarEndChannelPrevious1DayInvalidDataFlag    INTEGER,
            xdslFarEndChannelPrevious1DayCECs               Counter
        }

xdslFarEndChannelPrevious1DayNumber    OBJECT-TYPE
       SYNTAX  INTEGER(1..7)
       ACCESS  read-only
       STATUS  mandatory
       DESCRIPTION     
        "A number between 1 and 7, which identifies the day for which the
         set of statistics is available. The day identified by 1 is the most
         recently completed 1Day, and the day identified by
         N is the day immediately preceding the one identified by N-1.

         ALCATEL NOTE:
             ACCESS:   NA                  USAGE:    NA
             PERSIST:  NO                  INSRVMOD: NA
             RANGE:    1                   DEFVALUE: NA
             UNITS:    NA                  SPARSE:   NA
             DESCR:    Only statistics for one previous day is kept. "
::= {xdslFarEndChannelPrevious1DayEntry 1}

xdslFarEndChannelPrevious1DayCVs       OBJECT-TYPE
        SYNTAX          Counter
        ACCESS          read-only
        STATUS          mandatory
        DESCRIPTION     
        "The counter associated with the number of Coding Violations
         encountered by the far end channel in the previous 1 day interval.

         ALCATEL NOTE:
             ACCESS:   NA                  USAGE:    NA
             PERSIST:  NO                  INSRVMOD: NA
             RANGE:    NA                  DEFVALUE: 0
             UNITS:    NA                  SPARSE:   NA
             DESCR:    NA "
::= {xdslFarEndChannelPrevious1DayEntry 2}

xdslFarEndChannelPrevious1DayFECCs     OBJECT-TYPE
        SYNTAX          Counter
        ACCESS          read-only
        STATUS          mandatory
        DESCRIPTION     
        "The counter associated with the number of corrected codewords 
         encountered by the far end channel, respectively corrected octets in case of
         VDSL G.993.1, in the previous 1 day interval. If 
         more than one error occurs per superframe then only 1 is reported.

         ALCATEL NOTE:
             ACCESS:   NA                  USAGE:    NA
             PERSIST:  NO                  INSRVMOD: NA
             RANGE:    NA                  DEFVALUE: 0
             UNITS:    NA                  SPARSE:   NA
             DESCR:    NA "
::= {xdslFarEndChannelPrevious1DayEntry 3}

xdslFarEndChannelPrevious1DayMeasuredTime        OBJECT-TYPE
        SYNTAX          INTEGER(0..86400)
        ACCESS          read-only
        STATUS          mandatory
        DESCRIPTION     
        "The amount of time, measured in seconds, that statistics for this
         entry have been counted.

         ALCATEL NOTE:
             ACCESS:   NA                  USAGE:    NA
             PERSIST:  NO                  INSRVMOD: NA
             RANGE:    NA                  DEFVALUE: 0
             UNITS:    seconds             SPARSE:   NA
             DESCR:    NA "
::= {xdslFarEndChannelPrevious1DayEntry 4}

xdslFarEndChannelPrevious1DayInvalidDataFlag     OBJECT-TYPE
        SYNTAX          INTEGER
        ACCESS          read-only
        STATUS          mandatory
        DESCRIPTION     
        "This object indicates the validity of the corresponding PM data.
         It is set to 1 when the PM data is incomplete or invalid and set to 0
         when the PM data is complete and valid.

         ALCATEL NOTE:
             ACCESS:   NA                  USAGE:    NA
             PERSIST:  NO                  INSRVMOD: NA
             RANGE:    0..1                DEFVALUE: 1
             UNITS:    NA                  SPARSE:   NA
             DESCR:    NA "
::= {xdslFarEndChannelPrevious1DayEntry 5}

xdslFarEndChannelPrevious1DayCECs      OBJECT-TYPE
        SYNTAX          Counter
        ACCESS          read-only
        STATUS          mandatory
        DESCRIPTION
        "The counter associated with the number of uncorrected codewords errors
         encountered by the far end channel in a particular 1 Day interval
         in VDSL2 mode.

         ALCATEL NOTE:
             ACCESS:   NA                  USAGE:    NA
             PERSIST:  NO                  INSRVMOD: NA
             RANGE:    NA                  DEFVALUE: 0
             UNITS:    NA                  SPARSE:   NA
             DESCR:    NA "
::= {xdslFarEndChannelPrevious1DayEntry 6}

xdslPOTSlineTest             OBJECT IDENTIFIER ::= {xdslTestTypes 1}

xdslXtucNotReachable         OBJECT IDENTIFIER ::= {xdslTestCodes 1}

xdslXturNotReachable        OBJECT IDENTIFIER ::= {xdslTestCodes 2}

xdslNonAlcatelXtur          OBJECT IDENTIFIER ::= {xdslTestCodes 3}

xdslNoHardwareSupport        OBJECT IDENTIFIER ::= {xdslTestCodes 4}

xdslAnotherTestInProgress    OBJECT IDENTIFIER ::= {xdslTestCodes 5}

xdslPreparingPOTSTest       OBJECT IDENTIFIER ::= {xdslTestCodes 6}

xdslLineModeIsdn            OBJECT IDENTIFIER ::= {xdslTestCodes 7}

xdslTestPOTSlineTestDuration           OBJECT-TYPE
        SYNTAX          TimeTicks 
        ACCESS          read-write
        STATUS          mandatory
        DESCRIPTION 
        "Configurable test duration time, the same for all lines.

         ALCATEL NOTE:
             ACCESS:   NA                  USAGE:    NA
             PERSIST:  NO                  INSRVMOD: YES
             RANGE:    1..300              DEFVALUE: 300
             UNITS:    seconds             SPARSE:   NA
             DESCR:    NA "
::= {xdslTest 3}

xdslXtucSeltDataTable   OBJECT-TYPE
        SYNTAX          SEQUENCE OF XdslXtucSeltDataEntry
        ACCESS          not-accessible
        STATUS          mandatory
        DESCRIPTION     "The xdsl SELT data table.
         ALCATEL NOTE:
             DESCR:    NA "
::= {xdslTest 4}

xdslXtucSeltDataEntry   OBJECT-TYPE
        SYNTAX          XdslXtucSeltDataEntry                   
        ACCESS          not-accessible
        STATUS          mandatory
        DESCRIPTION     "An entry in the xdsl SELT data table.
         ALCATEL NOTE:
             DESCR:    NA "
        INDEX           {ifIndex}
::= {xdslXtucSeltDataTable 1}

XdslXtucSeltDataEntry ::=
        SEQUENCE {
                xdslSeltNoise                 OCTET STRING,
                xdslSeltUncalEcho             OCTET STRING,
                xdslSeltUncalEchoVar          OCTET STRING,
                xdslSeltCompEcho              OCTET STRING,
                xdslSeltEchoRefAvailableFlag  INTEGER,
                xdslSeltEchoOpen              OCTET STRING,
                xdslSeltEchoShort             OCTET STRING,
                xdslSeltEchoLoad              OCTET STRING,
                xdslSeltUncalEchoMeasTimeUsed INTEGER,
                xdslSeltQLNoiseMeasTimeUsed   INTEGER,
                xdslSeltSelectedPsdTypeUsed   SeltSelectedPsdType,
                xdslSeltUncalEchoMinSnrUsed   INTEGER,
                xdslSeltFailedErrorCode       INTEGER,
                xdslSeltAGCUsed               INTEGER,
                xdslSeltCarrierSpacingUsed    SeltCarrierSpacingType
        }

xdslSeltNoise     OBJECT-TYPE
        SYNTAX                   OCTET STRING
        ACCESS                   read-only
        STATUS                   mandatory
        DESCRIPTION      
         "This object provides the noise real values per carrier over the SELT
         measurement band for the specified line.
         When the data is not available because the measurement is not completed,
         not enabled or not supported, an empty string will be returned.
         The noise has a range from -150 dBm/Hz to -23 dBm/Hz in steps of 0.5 dB.
         It is represented as NOISEi = -23 - ni/2, with ni an 8 bit unsigned
         integer in the range 0 to 254.
         The special value 255 indicates that no measurement is available for
         the carrier or that the measurement is out of range.

         The noise is coded as a bitmap defined as follows:
         OCTETS 0,1: INTEGER (0..4096), index of the start carrier of the band.
         OCTETS 2,3: INTEGER (0..4096), index of the stop carrier of the band.
         OCTETS 4: INTEGER , contains the ni for the first carrier of the band
         (start carrier).
         OCTETS 5..L: ni for the next carrier and so on until the stop carrier of
         the band.
         ALCATEL NOTE:
             ACCESS:   NA                  USAGE:    NA
             PERSIST:  NA                  INSRVMOD: NA
             RANGE:    NA                  DEFVALUE: NA
             UNITS:    NA                  SPARSE:   NA
             DESCR:    NA "
::= {xdslXtucSeltDataEntry 1}

xdslSeltUncalEcho OBJECT-TYPE
        SYNTAX                   OCTET STRING
        ACCESS                   read-only
        STATUS                   mandatory
        DESCRIPTION      
         "This object provides the uncalibrated echo response complex values per
         carrier over the SELT measurement band for the specified line.
         When the data is not available because the measurement is not completed,
         not enabled or not supported, an empty string will be returned.

         The echo response is represented by a scale factor and an array of
         normalized complex numbers ai+j*bi, where i is the subcarrier index.
         It is represented as ECHOi = (scale/2^31)*((ai+j*bi)/2^31),
         with ai and bi 4 bytes signed integers in the range (-2^31+1) to
         (+2^31-1). The special value -2^31 (and for historical reason the value 0) 
         indicates that no measurement is available for the carrier or that the 
         measurement is out of range.
         The scale factor is a 4 bytes unsigned integer. The scale factor
         must be chosen such that: max(|ai|,|bi|) over all i is equal to 2^31-1.

         The echo response is coded as a bitmap defined as follows:
         OCTETS 0,1,2,3: INTEGER(0..4294967295), contains the scale factor to apply
         to the echo response values.
         OCTETS 4,5: INTEGER (0..4096), index of the start carrier of the band.
         OCTETS 6,7: INTEGER (0..4096), index of the stop carrier of the band.
         OCTETS 8,9,10,11: INTEGER , contains the ai for the first carrier
         of the band (start carrier).
         OCTETS 12,13,14,15: INTEGER , contains the bi for the first carrier
         of the band (start carrier).
         OCTETS 16..L-1: ai and bi for the next carrier and so on until the stop
         carrier of the 1st band.

         Optional 2nd band:
         OCTETS L+0, L+1: INTEGER (0..4096), index of the start carrier 
                          of the 2nd band.    
         OCTETS L+2, L+3: INTEGER (0..4096), index of the stop carrier 
                          of the 2nd band.
         OCTETS L+4,5,6,7: INTEGER, contains the ai for the first carrier of the
                           2nd band (start carrier). 
         OCTETS L+8,9,10,11: INTEGER, contains the bi for the first carrier
                             of the 2nd  band.
         OCTETS L+12..M-1: ai and bi for the next carrier and so on
                           until the stop carrier of 2nd the band.

         Optional 3rd band etc.

         ALCATEL NOTE:
             ACCESS:   NA                  USAGE:    NA
             PERSIST:  NA                  INSRVMOD: NA
             RANGE:    NA                  DEFVALUE: NA
             UNITS:    NA                  SPARSE:   NA
             DESCR:    NA "
::= {xdslXtucSeltDataEntry 2}

xdslSeltUncalEchoVar     OBJECT-TYPE
        SYNTAX                   OCTET STRING
        ACCESS                   read-only
        STATUS                   mandatory
        DESCRIPTION      
         "This object provides the uncalibrated echo response variance real values
         per carrier over the SELT measurement band for the specified line.
         When the data is not available because the measurement is not completed,
         not enabled or not supported, an empty string will be returned.
         The echo response variance has a range from -124 dBm/Hz to +3 dBm/Hz in
         steps of 0.5 dB.
         It is represented as ECHO_VARi = 3 - vi/2, with vi an 8 bit unsigned
         integer in the range 0 to 254.
         The special value 255 indicates that no measurement is available for
         the carrier or that the measurement is out of range.

         The echo response variance is coded as a bitmap defined as follows:
         OCTETS 0,1: INTEGER (0..4096), index of the start carrier 
                     of the 1st band.
         OCTETS 2,3: INTEGER (0..4096), index of the stop carrier 
                   of the 1st band.
         OCTETS 4: INTEGER , contains the vi for the first carrier
                   of the 1st band (start carrier).
         OCTETS 5..L-1: vi for the next carrier and so on until the stop carrier 
                   of the 1st band.

         Optional 2nd band:
         OCTETS L+0, L+1: INTEGER (0..4096), index of the start carrier 
                          of the 2nd band.    
         OCTETS L+2, L+3: INTEGER (0..4096), index of the stop carrier 
                          of the 2nd band.
         OCTETS L+4: OCTET, contains the vi for the first carrier of the
                     2nd band. 
         OCTETS L+5..M-1: OCTET, vi for the next carrier of the 2nd band
                          and so on until the stop carrier of the 2nd band.

         Optional 3rd band etc..

         ALCATEL NOTE:
             ACCESS:   NA                  USAGE:    NA
             PERSIST:  NA                  INSRVMOD: NA
             RANGE:    NA                  DEFVALUE: NA
             UNITS:    NA                  SPARSE:   NA
             DESCR:    NA "
::= {xdslXtucSeltDataEntry 3}

xdslSeltCompEcho OBJECT-TYPE
        SYNTAX                   OCTET STRING
        ACCESS                   read-only
        STATUS                   mandatory
        DESCRIPTION      
         "This object provides the compensated echo response complex values per
         carrier over the SELT measurement band for the specified line.
         When the data is not available because the measurement is not completed,
         not enabled or not supported, an empty string will be returned.

         The echo response is represented by a scale factor and an array of
         normalized complex numbers ai+j*bi, where i is the subcarrier index.
         It is represented as ECHOi = (scale/2^31)*((ai+j*bi)/2^31),
         with ai and bi 4 bytes signed integers in the range (-2^31+1) to
         (+2^31-1). The special value -2^31 indicates that no measurement is
         available for the carrier or that the measurement is out of range.
         The scale factor is a 4 bytes unsigned integer. The scale factor
         must be chosen such that: max(|ai|,|bi|) over all i is equal to 2^31-1.

         The echo response is coded as a bitmap defined as follows:
         OCTETS 0,1,2,3: INTEGER(0..4294967295), contains the scale factor to apply
         to the echo response values.
         OCTETS 4,5: INTEGER (0..4096), index of the start carrier of the band.
         OCTETS 6,7: INTEGER (0..4096), index of the stop carrier of the band.
         OCTETS 8,9,10,11: INTEGER , contains the ai for the first carrier
         of the band (start carrier).
         OCTETS 12,13,14,15: INTEGER , contains the bi for the first carrier
         of the band (start carrier).
         OCTETS 16..L: ai and bi for the next carrier and so on until the stop
         carrier of the band.
         ALCATEL NOTE:
             ACCESS:   NA                  USAGE:    NA
             PERSIST:  NA                  INSRVMOD: NA
             RANGE:    NA                  DEFVALUE: NA
             UNITS:    NA                  SPARSE:   NA
             DESCR:    This object is not supported. "
::= {xdslXtucSeltDataEntry 4}

xdslSeltEchoRefAvailableFlag OBJECT-TYPE
        SYNTAX                   INTEGER
        ACCESS                   read-only
        STATUS                   mandatory
        DESCRIPTION     
         "This object indicates if SELT echo reference measurements on
         open/short/load are available in flash memory or not.
         It is set to 0 when the data is not available and set to 1 when the data
         is available. To actually retrieve these reference measurements, a SELT
         echo response test has to be started first.
         ALCATEL NOTE:
             ACCESS:   NA                  USAGE:    NA
             PERSIST:  NA                  INSRVMOD: NA
             RANGE:    NA                  DEFVALUE: NA
             UNITS:    NA                  SPARSE:   NA
             DESCR:    This object is not supported. "
::= {xdslXtucSeltDataEntry 5}

xdslSeltEchoOpen OBJECT-TYPE
        SYNTAX                   OCTET STRING
        ACCESS                   read-only
        STATUS                   mandatory
        DESCRIPTION      
         "This object provides the echo response reference measured on an open
         circuit for the specified line.
         When the data is not available, an empty string will be returned.

         The echo response is represented by a scale factor and an array of
         normalized complex numbers ai+j*bi, where i is the subcarrier index.
         It is represented as ECHOi = (scale/2^31)*((ai+j*bi)/2^31),
         with ai and bi 4 bytes signed integers in the range (-2^31+1) to
         (+2^31-1). The special value -2^31 indicates that no measurement is
         available for the carrier or that the measurement is out of range.
         The scale factor is a 4 bytes unsigned integer. The scale factor
         must be chosen such that: max(|ai|,|bi|) over all i is equal to 2^31-1.

         The echo response is coded as a bitmap defined as follows:
         OCTETS 0,1,2,3: INTEGER(0..4294967295), contains the scale factor to apply
         to the echo response values.
         OCTETS 4,5: INTEGER (0..4096), index of the start carrier of the band.
         OCTETS 6,7: INTEGER (0..4096), index of the stop carrier of the band.
         OCTETS 8,9,10,11: INTEGER , contains the ai for the first carrier
         of the band (start carrier).
         OCTETS 12,13,14,15: INTEGER , contains the bi for the first carrier
         of the band (start carrier).
         OCTETS 16..L: ai and bi for the next carrier and so on until the stop
         carrier of the band.
         ALCATEL NOTE:
             ACCESS:   NA                  USAGE:    NA
             PERSIST:  NA                  INSRVMOD: NA
             RANGE:    NA                  DEFVALUE: NA
             UNITS:    NA                  SPARSE:   NA
             DESCR:    This object is not supported. "
::= {xdslXtucSeltDataEntry 6}

xdslSeltEchoShort OBJECT-TYPE
        SYNTAX                   OCTET STRING
        ACCESS                   read-only
        STATUS                   mandatory
        DESCRIPTION      
         "This object provides the echo response reference measured on a short
         circuit for the specified line.
         When the data is not available, an empty string will be returned.

         The echo response is represented by a scale factor and an array of
         normalized complex numbers ai+j*bi, where i is the subcarrier index.
         It is represented as ECHOi = (scale/2^31)*((ai+j*bi)/2^31),
         with ai and bi 4 bytes signed integers in the range (-2^31+1) to
         (+2^31-1). The special value -2^31 indicates that no measurement is
         available for the carrier or that the measurement is out of range.
         The scale factor is a 4 bytes unsigned integer. The scale factor
         must be chosen such that: max(|ai|,|bi|) over all i is equal to 2^31-1.

         The echo response is coded as a bitmap defined as follows:
         OCTETS 0,1,2,3: INTEGER(0..4294967295), contains the scale factor to apply
         to the echo response values.
         OCTETS 4,5: INTEGER (0..4096), index of the start carrier of the band.
         OCTETS 6,7: INTEGER (0..4096), index of the stop carrier of the band.
         OCTETS 8,9,10,11: INTEGER , contains the ai for the first carrier
         of the band (start carrier).
         OCTETS 12,13,14,15: INTEGER , contains the bi for the first carrier
         of the band (start carrier).
         OCTETS 16..L: ai and bi for the next carrier and so on until the stop
         carrier of the band.
         ALCATEL NOTE:
             ACCESS:   NA                  USAGE:    NA
             PERSIST:  NA                  INSRVMOD: NA
             RANGE:    NA                  DEFVALUE: NA
             UNITS:    NA                  SPARSE:   NA
             DESCR:    This object is not supported. "
::= {xdslXtucSeltDataEntry 7}

xdslSeltEchoLoad OBJECT-TYPE
        SYNTAX                   OCTET STRING
        ACCESS                   read-only
        STATUS                   mandatory
        DESCRIPTION      
         "This object provides the echo response reference measured on a reference
         impedance for the specified line.
         When the data is not available, an empty string will be returned.

         The echo response is represented by a scale factor and an array of
         normalized complex numbers ai+j*bi, where i is the subcarrier index.
         It is represented as ECHOi = (scale/2^31)*((ai+j*bi)/2^31),
         with ai and bi 4 bytes signed integers in the range (-2^31+1) to
         (+2^31-1). The special value -2^31 indicates that no measurement is
         available for the carrier or that the measurement is out of range.
         The scale factor is a 4 bytes unsigned integer. The scale factor
         must be chosen such that: max(|ai|,|bi|) over all i is equal to 2^31-1.

         The echo response is coded as a bitmap defined as follows:
         OCTETS 0,1,2,3: INTEGER(0..4294967295), contains the scale factor to apply
         to the echo response values.
         OCTETS 4,5: INTEGER (0..4096), index of the start carrier of the band.
         OCTETS 6,7: INTEGER (0..4096), index of the stop carrier of the band.
         OCTETS 8,9,10,11: INTEGER , contains the ai for the first carrier
         of the band (start carrier).
         OCTETS 12,13,14,15: INTEGER , contains the bi for the first carrier
         of the band (start carrier).
         OCTETS 16..L: ai and bi for the next carrier and so on until the stop
         carrier of the band.
         ALCATEL NOTE:
             ACCESS:   NA                  USAGE:    NA
             PERSIST:  NA                  INSRVMOD: NA
             RANGE:    NA                  DEFVALUE: NA
             UNITS:    NA                  SPARSE:   NA
             DESCR:    This object is not supported. "
::= {xdslXtucSeltDataEntry 8}

xdslSeltUncalEchoMeasTimeUsed  OBJECT-TYPE
        SYNTAX                  INTEGER  
        ACCESS                  read-only
        STATUS                  mandatory  
        DESCRIPTION             
          "Reports the actual SELT measurement time used by the modems
           for the latest Uncalibrated Echo measurement (Uncalibrated Echo
           and Uncalibrated Echo Variance)
           Valid range: 0 .. 240 in steps of 1, unit is seconds.
           Value (255) : parameter is not available.  
           This value is only valid when the measurement is in state 'success'.
         ALCATEL NOTE:
             ACCESS:   NA                  USAGE:    NA
             PERSIST:  NA                  INSRVMOD: NA
             RANGE:    0..240,255          DEFVALUE: NA
             UNITS:    NA                  SPARSE:   NA
             DESCR:    NA "
::= {xdslXtucSeltDataEntry 9}

xdslSeltQLNoiseMeasTimeUsed  OBJECT-TYPE
        SYNTAX                  INTEGER  
        ACCESS                  read-only
        STATUS                  mandatory  
        DESCRIPTION             
          "Reports the actual SELT measurement time used by the modems
           for the latest Quiet Line Noise measurement 
           Valid range: 0 .. 240 in steps of 1, unit is seconds. 
           Value (255) : parameter is not available. 
           This value is only valid when the measurement is in state 'success'.
         ALCATEL NOTE:
             ACCESS:   NA                  USAGE:    NA
             PERSIST:  NA                  INSRVMOD: NA
             RANGE:    0..240,255          DEFVALUE: NA
             UNITS:    NA                  SPARSE:   NA
             DESCR:    NA "
::= {xdslXtucSeltDataEntry 10}

xdslSeltSelectedPsdTypeUsed OBJECT-TYPE
        SYNTAX                  SeltSelectedPsdType  
        ACCESS                  read-only
        STATUS                  mandatory  
        DESCRIPTION             
         "Reports the actual Psd type that was used during the last
          SELT Echo measurement.
          The possible values are: 
            - selectedPsdTypeConfigVdsl2 (1): The VDSL2 modem line configuration
              data was used to limit the SELT excitation signal.
            - selectedPsdTypeConfigVdsl1 (2): The VDSL1 modem line configuration
              data was used to limit the SELT excitation signal.
            - selectedPsdTypeConfigAdsl1or2 (3): The ADSL2 or ADSL1 modem line 
              configuration data was used to limit the SELT excitation signal. 
            - selectedPsdTypeConfigAdsl2Plus (4): The ADSL2+ modem line 
              configuration data was used to limit the SELT excitation signal.
            - selectedPsdTypeConfigReAdsl2 (5): The READSL2+ modem line 
              configuration data was used to limit the SELT excitation signal
            - selectedPsdTypePreDefVdsl2 (6): The predefined VDSL2 profile was
              used to construct the SELT excitation signal.
            - selectedPsdTypePreDefVdsl1 (7): The predefined VDSL1 profile was
              used to construct the SELT excitation signal.
            - selectedPsdTypePreDefAllBandsVdsl2 (8): The predefined all bands
              VDSL2 profile was used to construct the SELT excitation signal.
            - selectedPsdTypePreDefAllBandsAdsl1 (9): The predefined all 
              bands ADSL1 profile was used to construct the SELT excitation
              signal.
            - selectedPsdTypePreDefAllBandsAdsl2Plus (10): The predefined all
              bands ADSL2+ profile was used to construct the SELT excitation
              signal.
            - selectedPsdTypePreDefVdsl2RegionA (11): The predefined VDSL2 profile
              consistent with Annex A of G.993.2 was used to construct the SELT 
              excitation signal.
            - selectedPsdType8dConfigVdsl2 (12): The VDSL2 profile 8d and VDSL2 modem
              line configuration data was used to construct the SELT excitation signal.
            - selectedPsdTypeUnknownNotSupported (255): parameter is not available.
          This value is only valid when the measurement is in the
          state 'success'.
         ALCATEL NOTE:
             ACCESS:   NA                  USAGE:    NA
             PERSIST:  NA                  INSRVMOD: NA
             RANGE:    NA                  DEFVALUE: NA
             UNITS:    NA                  SPARSE:   NA
             DESCR:    NA "
::= {xdslXtucSeltDataEntry 11}

xdslSeltUncalEchoMinSnrUsed   OBJECT-TYPE
        SYNTAX                  INTEGER  
        ACCESS                  read-only
        STATUS                  mandatory  
        DESCRIPTION             
         "Reports the actual minimal SNR achieved by the last SELT Echo 
          measurement.
            - INTEGER(+0,+120), in steps of 1, unit is dB.
            - Value (255) : parameter is not available.
          This value is only valid when the measurement is in the state 
          'success'.
         ALCATEL NOTE:
             ACCESS:   NA                  USAGE:    NA
             PERSIST:  NA                  INSRVMOD: NA
             RANGE:    0..120,255          DEFVALUE: NA
             UNITS:    NA                  SPARSE:   NA
             DESCR:    NA "
::= {xdslXtucSeltDataEntry 12}

xdslSeltFailedErrorCode OBJECT-TYPE
        SYNTAX                  INTEGER  
        ACCESS                  read-only
        STATUS                  mandatory  
        DESCRIPTION             
         "Reports the reason why a SELT test was failed.
          The possible values are: 
             - 0 = Unknown Error Reason
             - 1 = Proxy did not finished the measurement in given timeframe.
             - 255 = parameter is not available
          This value is only valid when the measurement is in the state 
          'failed'.
         ALCATEL NOTE:
             ACCESS:   NA                  USAGE:    NA
             PERSIST:  NA                  INSRVMOD: NA
             RANGE:    0..1,255            DEFVALUE: NA
             UNITS:    NA                  SPARSE:   NA
             DESCR:    NA "
::= {xdslXtucSeltDataEntry 13}

xdslSeltAGCUsed OBJECT-TYPE
        SYNTAX                  INTEGER  
        ACCESS                  read-only
        STATUS                  mandatory  
        DESCRIPTION             
         " Reports the AGC that was used for the last SELT Echo measurement.
          INTEGER(-100,+100), in dB
          Value (255) : parameter is not available.
          This value is only valid when the measurement is in the state
          'success'.
         ALCATEL NOTE:
             ACCESS:   NA                  USAGE:    NA
             PERSIST:  NA                  INSRVMOD: NA
             RANGE:    -100..100,255       DEFVALUE: NA
             UNITS:    NA                  SPARSE:   NA
             DESCR:    NA "
::= {xdslXtucSeltDataEntry 14}

xdslSeltCarrierSpacingUsed    OBJECT-TYPE
        SYNTAX                  SeltCarrierSpacingType  
        ACCESS                  read-only  
        STATUS                  mandatory  
        DESCRIPTION             
         "This object provide the actual carrier spacing used for the SELT 
           measurement.
          UnknownNotSupported (255) : parameter is not available.
         ALCATEL NOTE:
             ACCESS:   NA                  USAGE:    NA
             PERSIST:  NA                  INSRVMOD: NA
             RANGE:    NA                  DEFVALUE: NA
             UNITS:    NA                  SPARSE:   NA
             DESCR:    This object is not supported "
::= {xdslXtucSeltDataEntry 15}

xdslXturInventoryTable  OBJECT-TYPE
        SYNTAX          SEQUENCE OF XdslXturInventoryEntry
        ACCESS          not-accessible
        STATUS          mandatory
        DESCRIPTION
        "This table provides one row for each XTU-R, containing the
         inventory data of that XTU-R. When not in showtime, the previous 
         inventory data values will be returned. If no value is available,
         an empty string will be returned.

         ALCATEL NOTE:
             TABLESIZE: DEP [number of XDSL lines]                    
             DESCR:     NA                   "
::= {xdslXturInventory 1}

xdslXturInventoryEntry  OBJECT-TYPE
        SYNTAX          XdslXturInventoryEntry
        ACCESS          not-accessible
        STATUS          mandatory
        DESCRIPTION
        "An entry in the xdslXturInventoryTable.

         Row creation : Entries for all XDSL lines belonging to a board are 
                        created when the board becomes operational.
         Row deletion : Entries for all XDSL lines belonging to a board are 
                        deleted when the board becomes unavailable. "
        INDEX          {ifIndex}
::= {xdslXturInventoryTable 1}
  
XdslXturInventoryEntry ::=
        SEQUENCE {
            xdslXturInvModemVendorID                  OCTET STRING,
            xdslXturInvSystemSerialNumber             OCTET STRING,
            xdslXturInvSystemVendorID                 OCTET STRING,
            xdslXturInvSystemVersionNumber            OCTET STRING,
            xdslXturInvSelfTestResults                OCTET STRING
        }
    
xdslXturInvModemVendorID               OBJECT-TYPE
        SYNTAX     OCTET STRING (SIZE (0..16))
        ACCESS     read-only
        STATUS     mandatory
        DESCRIPTION
        "The vendor ID retrieved during handshaking is considered as the
         vendor ID of the XTU-R modem. The binary vendor identification field
         is a binary string of N bytes. This string is converted, nibble by
         nibble, in a hexadecimal format resulting in an ASCII text string of
         2*N characters, i.e. each byte of the vendor ID code is represented by
         2 hexadecimal characters.
         The vendor ID is composed as follows:
            - for ANSI & ETSI: 2 bytes vendor specific code
            - for ITU-T: 8 bytes code, composed of
                * T.35 country code (2 bytes)
                * provider code (4 bytes)
                * vendor-specific information (2 bytes)

         ALCATEL NOTE:
             ACCESS:   NA                  USAGE:    NA
             PERSIST:  NO                  INSRVMOD: NA
             RANGE:    NA                  DEFVALUE: ''H
             UNITS:    ASCII characters    SPARSE:   NA
             DESCR:    NA "
::= { xdslXturInventoryEntry 1 }

xdslXturInvSystemSerialNumber          OBJECT-TYPE
        SYNTAX          OCTET STRING (SIZE (0..32))
        ACCESS          read-only
        STATUS          mandatory
        DESCRIPTION
        "The unique vendor specific string that identifies the vendor
         equipment, and which is retrieved via the XDSL EOC. The value of the
         serial number is vendor discretionary.
         The serial number stored in the XTU-R consists of 32 bytes (see
         G.992.1/2) and is mapped straightforward onto this MIB object (see 
         also RFC2662).
         As the XTU-R serial number already consists of alphanumerical
         characters, no conversion is needed to make the value humanly 
         readable.

         ALCATEL NOTE:
             ACCESS:   NA                  USAGE:    NA
             PERSIST:  NO                  INSRVMOD: NA
             RANGE:    NA                  DEFVALUE: ''H
             UNITS:    ASCII characters    SPARSE:   NA
             DESCR:    NA "
::= { xdslXturInventoryEntry 2 }

xdslXturInvSystemVendorID              OBJECT-TYPE
        SYNTAX          OCTET STRING (SIZE (0..16))
        ACCESS          read-only
        STATUS          mandatory
        DESCRIPTION
        "The vendor ID retrieved via the XDSL EOC is considered as the vendor
         ID of the XTU-R assembly (CPE). The binary vendor identification field
         is a binary string of N bytes. This string is converted, nibble by
         nibble, in a hexadecimal format resulting in an ASCII text string of
         2*N characters, i.e. each byte of the vendor ID code is represented by
         2 hexadecimal characters.
         The vendor ID is composed as follows:
           - for ANSI & ETSI: 2 bytes vendor specific code
           - for ITU-T: 8 bytes code, composed of
               * T.35 country code (2 bytes)
               * provider code (4 bytes)
               * vendor-specific information (2 bytes)

         ALCATEL NOTE:
             ACCESS:   NA                  USAGE:    NA
             PERSIST:  NO                  INSRVMOD: NA
             RANGE:    NA                  DEFVALUE: ''H
             UNITS:    ASCII characters    SPARSE:   NA
             DESCR:    NA "
 ::= { xdslXturInventoryEntry 3 }

 xdslXturInvSystemVersionNumber        OBJECT-TYPE
        SYNTAX          OCTET STRING (SIZE (0..34))
        ACCESS          read-only
        STATUS          mandatory
        DESCRIPTION
        "The vendor specific version number retrieved via the XDSL EOC.
         The binary version number field is a binary string of N bytes. This
         string is converted, nibble by nibble, in a hexadecimal format
         resulting in an ASCII text string of 2*N characters, i.e. each byte of
         the version number code is represented by 2 hexadecimal characters.
         The format and length of the XTU-R version number is vendor
         discretionary.
         This number will be truncated in case its length exceeds 17 bytes.
         Alcatel note: The maximum size of 34 allows to store the complete
         contents of the version number returned by the Alcatel XTU-R.

         ALCATEL NOTE:
             ACCESS:   NA                  USAGE:    NA
             PERSIST:  NO                  INSRVMOD: NA
             RANGE:    NA                  DEFVALUE: ''H
             UNITS:    ASCII characters    SPARSE:   NA
             DESCR:    NA "
::= { xdslXturInventoryEntry 4 }

xdslXturInvSelfTestResults             OBJECT-TYPE
        SYNTAX          OCTET STRING (SIZE (0..8))
        ACCESS          read-only
        STATUS          mandatory
        DESCRIPTION
        "Self test results value retrieved via the the XDSL EOC. This
         parameter is a N-bytes binary code. This string is converted, nibble
         by nibble, in a hexadecimal format resulting in an ASCII text string
         of 2*N characters, i.e. each byte of the self test results code is
         represented by 2 hexadecimal characters.
         The most significant octet (= first octet) is 00hex if the self test
         passed and 01hex if the self test failed. The interpretation of the 
         other octets is vendor discretionary.

         ALCATEL NOTE:
             ACCESS:   NA                  USAGE:    NA
             PERSIST:  NO                  INSRVMOD: NA
             RANGE:    NA                  DEFVALUE: ''H
             UNITS:    ASCII characters    SPARSE:   NA
             DESCR:    NA "
::= { xdslXturInventoryEntry 5 }

xdslXtucInventoryTable OBJECT-TYPE
        SYNTAX     SEQUENCE OF XdslXtucInventoryEntry
        ACCESS     not-accessible
        STATUS     mandatory
        DESCRIPTION
        "This table provides one row for each XTU-C, containing the
         inventory data of that XTU-C. If no value is available an empty string 
         will be returned.
         ALCATEL NOTE:
             TABLESIZE: DEP [number of XDSL lines]                    
             DESCR:    NA "
::= {xdslXtucInventory 1}

xdslXtucInventoryEntry OBJECT-TYPE
        SYNTAX     XdslXtucInventoryEntry
        ACCESS     not-accessible
        STATUS     mandatory
        DESCRIPTION
        "An entry in the xdslXtucInventoryTable.
         Row creation : Entries for all XDSL lines belonging to a board are 
                        created when the board becomes operational.
         Row deletion : Entries for all XDSL lines belonging to a board are 
                             deleted when the board becomes unavailable. "
        INDEX      {ifIndex}
::= {xdslXtucInventoryTable 1}

XdslXtucInventoryEntry ::=
        SEQUENCE {
        xdslXtucInvSystemSerialNumber    OCTET STRING,
        xdslXtucInvSystemVendorID        OCTET STRING,
        xdslXtucInvSystemVersionNumber   OCTET STRING,
        xdslXtucInvModemVendorID         OCTET STRING,
        xdslXtucInvModemSwVersionNumber  DisplayString
        }
 
xdslXtucInvSystemSerialNumber OBJECT-TYPE
        SYNTAX     OCTET STRING (SIZE (0..32))
        ACCESS     read-only
        STATUS     mandatory
        DESCRIPTION
        "The unique vendor specific string that identifies the vendor equipment.
         The value of the serial number is vendor discretionary.
         The serial number stored in the XTU-C consists of 32 bytes (see
         G.992.1/2) and is mapped straightforward onto this MIB object (see
         also RFC2662).
         As the XTU-C serial number already consists of alphanumerical 
         characters, no conversion is needed to make the value humanly
         readable.
         ALCATEL NOTE:
             ACCESS:   NA                  USAGE:    NA
             PERSIST:  NA                  INSRVMOD: NA
             RANGE:    NA                  DEFVALUE: NA
             UNITS:    NA                  SPARSE:   NA
             DESCR:    This object is not supported. "
::= { xdslXtucInventoryEntry 1 }

xdslXtucInvSystemVendorID OBJECT-TYPE
        SYNTAX     OCTET STRING (SIZE (0..16))
        ACCESS     read-only
        STATUS     mandatory
        DESCRIPTION
        "The vendor ID of the XTU-C assembly. The binary vendor identification
         field is a binary string of N bytes. This string is converted, nibble
         by nibble, in a hexadecimal format resulting in an ASCII text string
         of 2*N characters, i.e. each byte of the vendor ID code is
         represented by 2 hexadecimal characters.
         The vendor ID is composed as follows:
           - for ANSI & ETSI: 2 bytes vendor specific code
           - for ITU-T: 8 bytes code, composed of
               * T.35 country code (2 bytes)
               * provider code (4 bytes)
               * vendor-specific information (2 bytes)
         ALCATEL NOTE:
             ACCESS:   NA                  USAGE:    NA
             PERSIST:  NA                  INSRVMOD: NA
             RANGE:    NA                  DEFVALUE: NA
             UNITS:    NA                  SPARSE:   NA
             DESCR:    This object is not supported. "
::= { xdslXtucInventoryEntry 2 }

xdslXtucInvSystemVersionNumber OBJECT-TYPE
        SYNTAX     OCTET STRING (SIZE (0..34))
        ACCESS     read-only
        STATUS     mandatory
        DESCRIPTION
        "The vendor specific version number. The binary version number field
         is a binary string of N bytes. This string is converted, nibble by
         nibble, in a hexadecimal format resulting in an ASCII text string of
         2*N characters, i.e. each byte of the version number code
         is represented by 2 hexadecimal characters.
         The format and length of the XTU-C version number is vendor
         discretionary.
         This number will be truncated in case its length exceeds 17 bytes.
         Alcatel note: The maximum size of 34 allows to store the complete
         content of the version number returned by the Alcatel XTU-C.
         ALCATEL NOTE:
             ACCESS:   NA                  USAGE:    NA
             PERSIST:  NA                  INSRVMOD: NA
             RANGE:    NA                  DEFVALUE: NA
             UNITS:    NA                  SPARSE:   NA
             DESCR:    This object is not supported. "
::= { xdslXtucInventoryEntry 3 }

xdslXtucInvModemVendorID OBJECT-TYPE
        SYNTAX     OCTET STRING (SIZE (0..16))
        ACCESS     read-only
        STATUS     mandatory
        DESCRIPTION
        "The vendor ID of the XTU-C modem. The binary vendor identification
         field is a binary string of N bytes. This string is converted, nibble
         by nibble, in a  hexadecimal format resulting in an ASCII text string
         of 2*N characters, i.e. each byte of the vendor ID code is represented
         by 2 hexadecimal characters.
         The vendor ID is composed as follows:
           - for ANSI & ETSI: 2 bytes vendor specific code
           - for ITU-T: 8 bytes code, composed of
               * T.35 country code (2 bytes)
               * provider code (4 bytes)
               * vendor-specific information (2 bytes)
         ALCATEL NOTE:
             ACCESS:   NA                  USAGE:    NA
             PERSIST:  NA                  INSRVMOD: NA
             RANGE:    NA                  DEFVALUE: NA
             UNITS:    NA                  SPARSE:   NA
             DESCR:    This object is not supported. "
::= { xdslXtucInventoryEntry 4 }

xdslXtucInvModemSwVersionNumber OBJECT-TYPE
        SYNTAX     DisplayString (SIZE (0..32))
        ACCESS     read-only
        STATUS     mandatory
        DESCRIPTION
        "Identifies the XTU-C modem software-version number. 
         The first three characters are reserved for the abbreviated vendor name.
         The fourth character is a space separator.
         The remaining 28 characters are modem vendor specific.
         This is intended to be used by the Alcatel-Lucent NA5530 
         Network Analyzer only.
         ALCATEL NOTE:
             ACCESS:   NA                  USAGE:    NA
             PERSIST:  NO                  INSRVMOD: NA
             RANGE:    NA                  DEFVALUE: ''H
             UNITS:    NA                  SPARSE:   NA
             DESCR:    NA "
::= { xdslXtucInventoryEntry 5 }

xdslLineTcaThresholdTable              OBJECT-TYPE
        SYNTAX          SEQUENCE OF XdslLineTcaThresholdEntry
        ACCESS          not-accessible
        STATUS          mandatory
        DESCRIPTION
        "The XDSL line TCA threshold table, containing the thresholds for
         the TCA's for the XDSL line (both near-end and far-end.

         ALCATEL NOTE:
             TABLESIZE: DEP [number of XDSL lines]                    
             DESCR:     NA                   "
::= { xdslLineTcaThreshold  1 }

xdslLineTcaThresholdEntry              OBJECT-TYPE
        SYNTAX          XdslLineTcaThresholdEntry
        ACCESS          not-accessible
        STATUS          mandatory
        DESCRIPTION
        "An entry in the XDSL line TCA threshold table.

         Row creation : Entries for all XDSL lines belonging to a board are 
                        created by the system when the board is planned.
         Row deletion : Entries for all XDSL lines belonging to a board are 
                        deleted by the system when the board is unplanned. "
        INDEX          {ifIndex }
::= { xdslLineTcaThresholdTable  1 }

XdslLineTcaThresholdEntry ::=
        SEQUENCE {
            xdslLineTcaEnable                         INTEGER,
            xdslLineIntervalESsTcaThreshold           INTEGER,
            xdslLineIntervalSESsTcaThreshold          INTEGER,
            xdslLineIntervalUASsTcaThreshold          INTEGER,
            xdslLine1DayESsTcaThreshold               INTEGER,
            xdslLine1DaySESsTcaThreshold              INTEGER,
            xdslLine1DayUASsTcaThreshold              INTEGER,
            xdslFarEndLineIntervalESsTcaThreshold     INTEGER,
            xdslFarEndLineIntervalSESsTcaThreshold    INTEGER,
            xdslFarEndLineIntervalUASsTcaThreshold    INTEGER,
            xdslFarEndLine1DayESsTcaThreshold         INTEGER,
            xdslFarEndLine1DaySESsTcaThreshold        INTEGER,
            xdslFarEndLine1DayUASsTcaThreshold        INTEGER,
            xdslLineIntervalLEFTRsTcaThreshold         INTEGER,
            xdslLine1DayLEFTRsTcaThreshold             INTEGER,
            xdslFarEndLineIntervalLEFTRsTcaThreshold   INTEGER,
            xdslFarEndLine1DayLEFTRsTcaThreshold       INTEGER
        }

xdslLineTcaEnable       OBJECT-TYPE
        SYNTAX          INTEGER {
                            enabled(1),
                            disabled(2) 
                        }
        ACCESS          read-write
        STATUS          mandatory
        DESCRIPTION
        "This variable allows the manager to enable/disable the reporting of
         TCA's for this XDSL line.

         ALCATEL NOTE:
             ACCESS:   NA                  USAGE:    OPT
             PERSIST:  YES                 INSRVMOD: YES
             RANGE:    NA                  DEFVALUE: disabled
             UNITS:    NA                  SPARSE:   NA
             DESCR:    NA "
::= { xdslLineTcaThresholdEntry 1 }

xdslLineIntervalESsTcaThreshold        OBJECT-TYPE
        SYNTAX          INTEGER(0..900)
        ACCESS          read-write
        STATUS          mandatory
        DESCRIPTION
        "XDSL TCA threshold for Errored Seconds at the near end. 
         A value of zero means that the threshold is disabled.

         ALCATEL NOTE:
             ACCESS:   NA                  USAGE:    OPT
             PERSIST:  YES                 INSRVMOD: YES
             RANGE:    NA                  DEFVALUE: 0
             UNITS:    NA                  SPARSE:   NA
             DESCR:    NA "
::= { xdslLineTcaThresholdEntry  2 }

xdslLineIntervalSESsTcaThreshold       OBJECT-TYPE
        SYNTAX          INTEGER(0..900)
        ACCESS          read-write
        STATUS          mandatory
        DESCRIPTION
        "XDSL TCA threshold for Severely Errored Seconds at the near end.
         A value of zero means that the threshold is disabled.

         ALCATEL NOTE:
             ACCESS:   NA                  USAGE:    OPT
             PERSIST:  YES                 INSRVMOD: YES
             RANGE:    NA                  DEFVALUE: 0
             UNITS:    NA                  SPARSE:   NA
             DESCR:    NA "
::= { xdslLineTcaThresholdEntry  3 }

xdslLineIntervalUASsTcaThreshold       OBJECT-TYPE
        SYNTAX          INTEGER(0..900)
        ACCESS          read-write
        STATUS          mandatory
        DESCRIPTION
        "XDSL TCA threshold for Unavailable Seconds at the near end.
         A value of zero means that the threshold is disabled.

         ALCATEL NOTE:
             ACCESS:   NA                  USAGE:    OPT
             PERSIST:  YES                 INSRVMOD: YES
             RANGE:    NA                  DEFVALUE: 0
             UNITS:    NA                  SPARSE:   NA
             DESCR:    NA "
::= { xdslLineTcaThresholdEntry  4 }

xdslLine1DayESsTcaThreshold            OBJECT-TYPE
        SYNTAX          INTEGER(0..86400)
        ACCESS          read-write
        STATUS          mandatory
        DESCRIPTION
        "XDSL TCA threshold for Errored Seconds at the near end. 
         A value of zero means that the threshold is disabled.

         ALCATEL NOTE:
             ACCESS:   NA                  USAGE:    OPT
             PERSIST:  YES                 INSRVMOD: YES
             RANGE:    NA                  DEFVALUE: 0
             UNITS:    NA                  SPARSE:   NA
             DESCR:    NA "
::= { xdslLineTcaThresholdEntry  5 }

xdslLine1DaySESsTcaThreshold           OBJECT-TYPE
        SYNTAX          INTEGER(0..86400)
        ACCESS          read-write
        STATUS          mandatory
        DESCRIPTION
        "XDSL TCA threshold for Severely Errored Seconds at the near end.
         A value of zero means that the threshold is disabled.

         ALCATEL NOTE:
             ACCESS:   NA                  USAGE:    OPT
             PERSIST:  YES                 INSRVMOD: YES
             RANGE:    NA                  DEFVALUE: 0
             UNITS:    NA                  SPARSE:   NA
             DESCR:    NA "
::= { xdslLineTcaThresholdEntry  6 }

xdslLine1DayUASsTcaThreshold           OBJECT-TYPE
        SYNTAX          INTEGER(0..86400)
        ACCESS          read-write
        STATUS          mandatory
        DESCRIPTION
        "XDSL TCA threshold for Unavailable Seconds at the near end. 
         A value of zero means that the threshold is disabled.

         ALCATEL NOTE:
             ACCESS:   NA                  USAGE:    OPT
             PERSIST:  YES                 INSRVMOD: YES
             RANGE:    NA                  DEFVALUE: 0
             UNITS:    NA                  SPARSE:   NA
             DESCR:    NA "
::= { xdslLineTcaThresholdEntry  7 }

xdslFarEndLineIntervalESsTcaThreshold  OBJECT-TYPE
        SYNTAX          INTEGER(0..900)
        ACCESS          read-write
        STATUS          mandatory
        DESCRIPTION
        "XDSL TCA threshold for Errored Seconds at the far end. 
         A value of zero means that the threshold is disabled.

         ALCATEL NOTE:
             ACCESS:   NA                  USAGE:    OPT
             PERSIST:  YES                 INSRVMOD: YES
             RANGE:    NA                  DEFVALUE: 0
             UNITS:    NA                  SPARSE:   NA
             DESCR:    NA "
::= { xdslLineTcaThresholdEntry  8 }

xdslFarEndLineIntervalSESsTcaThreshold OBJECT-TYPE
        SYNTAX          INTEGER(0..900)
        ACCESS          read-write
        STATUS          mandatory
        DESCRIPTION
        "XDSL TCA threshold for Severely Errored Seconds at the far end.
         A value of zero means that the threshold is disabled.

         ALCATEL NOTE:
             ACCESS:   NA                  USAGE:    OPT
             PERSIST:  YES                 INSRVMOD: YES
             RANGE:    NA                  DEFVALUE: 0
             UNITS:    NA                  SPARSE:   NA
             DESCR:    NA "
::= { xdslLineTcaThresholdEntry  9 }

xdslFarEndLineIntervalUASsTcaThreshold OBJECT-TYPE
        SYNTAX          INTEGER(0..900)
        ACCESS          read-write
        STATUS          mandatory
        DESCRIPTION
        "XDSL TCA threshold for Unavailable Seconds at the far end. 
         A value of zero means that the threshold is disabled.

         ALCATEL NOTE:
             ACCESS:   NA                  USAGE:    OPT
             PERSIST:  YES                 INSRVMOD: YES
             RANGE:    NA                  DEFVALUE: 0
             UNITS:    NA                  SPARSE:   NA
             DESCR:    NA "
::= { xdslLineTcaThresholdEntry  10 }

xdslFarEndLine1DayESsTcaThreshold      OBJECT-TYPE
        SYNTAX          INTEGER(0..86400)
        ACCESS          read-write
        STATUS          mandatory
        DESCRIPTION
        "XDSL TCA threshold for Errored Seconds at the far end. 
         A value of zero means that the threshold is disabled.

         ALCATEL NOTE:
             ACCESS:   NA                  USAGE:    OPT
             PERSIST:  YES                 INSRVMOD: YES
             RANGE:    NA                  DEFVALUE: 0
             UNITS:    NA                  SPARSE:   NA
             DESCR:    NA "
::= { xdslLineTcaThresholdEntry  11 }

xdslFarEndLine1DaySESsTcaThreshold     OBJECT-TYPE
        SYNTAX          INTEGER(0..86400)
        ACCESS          read-write
        STATUS          mandatory
        DESCRIPTION
        "XDSL TCA threshold for Severely Errored Seconds at the far end.
         A value of zero means that the threshold is disabled.

         ALCATEL NOTE:
             ACCESS:   NA                  USAGE:    OPT
             PERSIST:  YES                 INSRVMOD: YES
             RANGE:    NA                  DEFVALUE: 0
             UNITS:    NA                  SPARSE:   NA
             DESCR:    NA "
::= { xdslLineTcaThresholdEntry  12 }

xdslFarEndLine1DayUASsTcaThreshold OBJECT-TYPE
        SYNTAX          INTEGER(0..86400)
        ACCESS          read-write
        STATUS          mandatory
        DESCRIPTION
        "XDSL TCA threshold for Unavailable Seconds at the far end. 
         A value of zero means that the threshold is disabled.

         ALCATEL NOTE:
             ACCESS:   NA                  USAGE:    OPT
             PERSIST:  YES                 INSRVMOD: YES
             RANGE:    NA                  DEFVALUE: 0
             UNITS:    NA                  SPARSE:   NA
             DESCR:    NA "
::= { xdslLineTcaThresholdEntry  13 }

xdslLineIntervalLEFTRsTcaThreshold        OBJECT-TYPE
        SYNTAX          INTEGER(0..900)
        ACCESS          read-write
        STATUS          mandatory
        DESCRIPTION
        "XDSL TCA threshold for LEFTR Seconds at the near end. 
         A value of zero means that the threshold is disabled.

         ALCATEL NOTE:
             ACCESS:   NA                  USAGE:    OPT
             PERSIST:  YES                 INSRVMOD: YES
             RANGE:    NA                  DEFVALUE: 0
             UNITS:    NA                  SPARSE:   NA
             DESCR:    NA "
::= { xdslLineTcaThresholdEntry  14 }

xdslLine1DayLEFTRsTcaThreshold             OBJECT-TYPE
        SYNTAX          INTEGER(0..86400)
        ACCESS          read-write
        STATUS          mandatory
        DESCRIPTION
        "XDSL TCA threshold for LEFTR Seconds at the near end. 
         A value of zero means that the threshold is disabled.

         ALCATEL NOTE:
             ACCESS:   NA                  USAGE:    OPT
             PERSIST:  YES                 INSRVMOD: YES
             RANGE:    NA                  DEFVALUE: 0
             UNITS:    NA                  SPARSE:   NA
             DESCR:    NA "
::= { xdslLineTcaThresholdEntry  15 }

xdslFarEndLineIntervalLEFTRsTcaThreshold   OBJECT-TYPE
        SYNTAX          INTEGER(0..900)
        ACCESS          read-write
        STATUS          mandatory
        DESCRIPTION
        "XDSL TCA threshold for LEFTR Seconds at the far end. 
         A value of zero means that the threshold is disabled.

         ALCATEL NOTE:
             ACCESS:   NA                  USAGE:    OPT
             PERSIST:  YES                 INSRVMOD: YES
             RANGE:    NA                  DEFVALUE: 0
             UNITS:    NA                  SPARSE:   NA
             DESCR:    NA "
::= { xdslLineTcaThresholdEntry  16 }

xdslFarEndLine1DayLEFTRsTcaThreshold       OBJECT-TYPE
        SYNTAX          INTEGER(0..86400)
        ACCESS          read-write
        STATUS          mandatory
        DESCRIPTION
        "XDSL TCA threshold for LEFTR Seconds at the far end. 
         A value of zero means that the threshold is disabled.

         ALCATEL NOTE:
             ACCESS:   NA                  USAGE:    OPT
             PERSIST:  YES                 INSRVMOD: YES
             RANGE:    NA                  DEFVALUE: 0
             UNITS:    NA                  SPARSE:   NA
             DESCR:    NA "
::= { xdslLineTcaThresholdEntry  17 }

xdslLinkUpTable         OBJECT-TYPE
        SYNTAX          SEQUENCE OF XdslLinkUpEntry
        ACCESS          not-accessible
        STATUS          mandatory
        DESCRIPTION
        "The xDSL Link Up record table contains for each line the latest
         link-up timestamp and the latest link-down timestamp along with other
         operational and configuration parameters.

         ALCATEL NOTE:
             TABLESIZE: DEP [number of XDSL lines]                    
             DESCR:     NA                  
          "
::= { xdslLinkUp  1 }

xdslLinkUpEntry         OBJECT-TYPE
        SYNTAX          XdslLinkUpEntry
        ACCESS          not-accessible
        STATUS          mandatory
        DESCRIPTION
        "An entry in the xDSL Link Up table.

         Row creation : Entries for all XDSL kines belonging to a board are 
                        created when the board becomes operational.
         Row deletion : Entries for all XDSL lines belonging to a board are 
                        deleted when the board becomes unavailable. "
        INDEX          {ifIndex }
::= { xdslLinkUpTable  1 }

XdslLinkUpEntry ::=
        SEQUENCE {
            xdslLinkUpTimestampDown                   Gauge,
            xdslLinkUpTimestampUp                     Gauge,
            xdslLinkUpActualBitrateUpstream           INTEGER,
            xdslLinkUpActualBitrateDownstream         INTEGER,
            xdslLinkUpActualNoiseMarginUpstream       INTEGER,
            xdslLinkUpActualNoiseMarginDownstream     INTEGER,
            xdslLinkUpAttenuationUpstream             INTEGER,
            xdslLinkUpAttenuationDownstream           INTEGER,
            xdslLinkUpAttainableBitrateUpstream       INTEGER,
            xdslLinkUpAttainableBitrateDownstream     INTEGER,
            xdslLinkUpMaxBitrateUpstream              INTEGER,
            xdslLinkUpMaxBitrateDownstream            INTEGER,
            xdslLinkUpThresholdBitrateUpstream        INTEGER,
            xdslLinkUpThresholdBitrateDownstream      INTEGER,
            xdslLinkUpMaxDelayUpstream                INTEGER,
            xdslLinkUpMaxDelayDownstream              INTEGER,
            xdslLinkUpTargetNoiseMarginUpstream       INTEGER,
            xdslLinkUpTargetNoiseMarginDownstream     INTEGER
        }

xdslLinkUpTimestampDown OBJECT-TYPE
        SYNTAX          Gauge 
        ACCESS          read-only
        STATUS          mandatory
        DESCRIPTION
        "This object contains the latest link down timestamp. It gives the
         network time in seconds (start counting since January 1, 1900) when
         the line went latest out of service.

         ALCATEL NOTE:
             ACCESS:   NA                  USAGE:    NA
             PERSIST:  NO                  INSRVMOD: NA
             RANGE:    NA                  DEFVALUE: 0
             UNITS:    seconds             SPARSE:   NA
             DESCR:    NA "
::= { xdslLinkUpEntry 1 }

xdslLinkUpTimestampUp   OBJECT-TYPE
        SYNTAX          Gauge 
        ACCESS          read-only
        STATUS          mandatory
        DESCRIPTION
        "This object contains the latest link up timestamp. It gives the 
         network time in seconds (start counting since January 1, 1900) when 
         the line came latest in showtime and remained in showtime for at least
         10 seconds (recorded time is time of entering showtime + 10 seconds).
        
         ALCATEL NOTE:
             ACCESS:   NA                  USAGE:    NA
             PERSIST:  NO                  INSRVMOD: NA
             RANGE:    NA                  DEFVALUE: 0
             UNITS:    seconds             SPARSE:   NA
             DESCR:    NA "
::= { xdslLinkUpEntry 2 }

xdslLinkUpActualBitrateUpstream        OBJECT-TYPE
        SYNTAX          INTEGER 
        ACCESS          read-only
        STATUS          mandatory
        DESCRIPTION
        "When the modem is in showtime: 
           - and RTX is not in use, then this object gives the actual net data 
             rate for the upstream fast or interleaved channel data flow.
           - and RTX is in use, then this object gives the actual expected 
             throughput for the upstream retransmission channel data flow.
         The data is retrieved when the lines come in showtime and remains in 
         showtime for at least 10 seconds. 
         A value 0 means that no data is available.
 
         ALCATEL NOTE:
             ACCESS:   NA                  USAGE:    NA
             PERSIST:  NO                  INSRVMOD: NA
             RANGE:    0..262143           DEFVALUE: 0
             UNITS:    kbits/sec           SPARSE:   NA
             DESCR:    NA "
::= { xdslLinkUpEntry 3 }

xdslLinkUpActualBitrateDownstream      OBJECT-TYPE
        SYNTAX          INTEGER 
        ACCESS          read-only
        STATUS          mandatory
        DESCRIPTION
        "When the modem is in showtime: 
           - and RTX is not in use, then this object gives the actual net data 
             rate for the downstream fast or interleaved channel data flow.
           - and RTX is in use, then this object gives the actual expected 
             throughput for the downstream retransmission channel data flow.
         The data is retrieved when the line comes in showtime and remains in 
         showtime for at least 10 seconds. 
         A value 0 means that no data is available.

         ALCATEL NOTE:
             ACCESS:   NA                  USAGE:    NA
             PERSIST:  NO                  INSRVMOD: NA
             RANGE:    0..262143           DEFVALUE: 0
             UNITS:    kbits/sec           SPARSE:   NA
             DESCR:    NA "
::= { xdslLinkUpEntry 4 }

xdslLinkUpActualNoiseMarginUpstream    OBJECT-TYPE
        SYNTAX          INTEGER 
        ACCESS          read-only
        STATUS          mandatory
        DESCRIPTION
        "This object gives the realised noise margin for the upstream 
         direction.
         The data is retrieved when the line comes in showtime and remains in 
         showtime for at least 10 seconds. 
         It is represented as 1/10 * xdslLinkUpActualNoiseMarginUpstream, with
         a range of (-64 .. 63 dB).
         A value 0 means that no data is available.

         ALCATEL NOTE:
             ACCESS:   NA                  USAGE:    NA
             PERSIST:  NO                  INSRVMOD: NA
             RANGE:    -640..630           DEFVALUE: 0
             UNITS:    dB / 10             SPARSE:   NA
             DESCR:    NA "
::= { xdslLinkUpEntry 5 }

xdslLinkUpActualNoiseMarginDownstream  OBJECT-TYPE
        SYNTAX          INTEGER 
        ACCESS          read-only
        STATUS          mandatory
        DESCRIPTION
        "This object gives the realised noise margin for the downstream 
         direction.
         The data is retrieved when the line comes in showtime and remains in 
         showtime for at least 10 seconds. 
         It is represented as 1/10 * xdslLinkUpActualNoiseMarginDownstream, 
         with a range of (-64 .. 63 dB).
         A value 0 means that no data is available.

         ALCATEL NOTE:
             ACCESS:   NA                  USAGE:    NA
             PERSIST:  NO                  INSRVMOD: NA
             RANGE:    -640..630           DEFVALUE: 0
             UNITS:    dB / 10             SPARSE:   NA
             DESCR:    NA "
::= { xdslLinkUpEntry 6 }

xdslLinkUpAttenuationUpstream          OBJECT-TYPE
        SYNTAX          INTEGER 
        ACCESS          read-only
        STATUS          mandatory
        DESCRIPTION
        "This object gives the measured difference in dB between the power
         received by the near-end receiver and the signal power transmitted by  
         the far-end transmitter. Only power over those tones carrying data is 
         taken into account.
         It corresponds with xdslLineSignalAttenuationUpstream in the 
         xdslLineOperDataTable.
         It is represented as 1/10 * xdslLinkUpAttenuationUpstream, with a 
         range of (0 .. 127 dB).
         The data is retrieved when the line comes in showtime and remains in 
         showtime for at least 10 seconds. 
         A value 0 means that no data is available.

         ALCATEL NOTE:
             ACCESS:   NA                  USAGE:    NA
             PERSIST:  NO                  INSRVMOD: NA
             RANGE:    0..1270             DEFVALUE: 0
             UNITS:    dB / 10             SPARSE:   NA
             DESCR:    NA "
::= { xdslLinkUpEntry 7 }

xdslLinkUpAttenuationDownstream        OBJECT-TYPE
        SYNTAX          INTEGER 
        ACCESS          read-only
        STATUS          mandatory
        DESCRIPTION
        "This object gives the measured difference in dB between the power
         received by the far-end receiver and the signal power transmitted by  
         the near-end transmitter. Only power over those tones carrying data is 
         taken into account.
         It corresponds with xdslFarEndLineSignalAttenuationDownstream in the 
         xdslFarEndLineOperDataTable.
         It is represented as 1/10 * xdslLinkUpAttenuationDownstream, with a 
         range of (0 .. 127 dB).
         The data is retrieved when the line comes in showtime and remains in 
         showtime for at least 10 seconds. 
         A value 0 means that no data is available.

         ALCATEL NOTE:
             ACCESS:   NA                  USAGE:    NA
             PERSIST:  NO                  INSRVMOD: NA
             RANGE:    0..1270             DEFVALUE: 0
             UNITS:    dB / 10             SPARSE:   NA
             DESCR:    NA "
::= { xdslLinkUpEntry 8 }

xdslLinkUpAttainableBitrateUpstream    OBJECT-TYPE
        SYNTAX          INTEGER 
        ACCESS          read-only
        STATUS          mandatory
        DESCRIPTION
        " When the modem is in showtime :
           - and RTX is not in use, then this object contains the maximum 
             attainable net data rate the modem can support on the corresponding 
             channel in the upstream direction. 
           - and RTX is in use, then this object contains the maximum 
             attainable expected throughput the modem can support on the 
             corresponding channel. 
         The data is retrieved when the line comes in showtime and remains in 
         showtime for at least 10 seconds. 
         A value 0 means that no data is available.

         ALCATEL NOTE:
             ACCESS:   NA                  USAGE:    NA
             PERSIST:  NO                  INSRVMOD: NA
             RANGE:    0..262143           DEFVALUE: 0
             UNITS:    kbits/sec           SPARSE:   NA
             DESCR:    NA "
::= { xdslLinkUpEntry 9 }

xdslLinkUpAttainableBitrateDownstream  OBJECT-TYPE
        SYNTAX          INTEGER 
        ACCESS          read-only
        STATUS          mandatory
        DESCRIPTION
        " When the modem is in showtime :
           - and RTX is not in use, then this object contains the maximum 
             attainable net data rate the modem can support on the corresponding 
             channel in the downstream direction. 
           - and RTX is in use, then this object contains the maximum 
             attainable expected throughput the modem can support on the 
             corresponding channel. 
         The data is retrieved when the line comes in showtime and remains in 
         showtime for at least 10 seconds. 
         A value 0 means that no data is available.

         ALCATEL NOTE:
             ACCESS:   NA                  USAGE:    NA
             PERSIST:  NO                  INSRVMOD: NA
             RANGE:    0..262143           DEFVALUE: 0
             UNITS:    kbits/sec           SPARSE:   NA
             DESCR:    NA "
::= { xdslLinkUpEntry 10 }

xdslLinkUpMaxBitrateUpstream           OBJECT-TYPE
        SYNTAX          INTEGER 
        ACCESS          read-only
        STATUS          mandatory
        DESCRIPTION
        "This object contains the configured maximum bitrate for the upstream 
         data flow. 
         It corresponds with the data configured in xdslMaxBitrateUpstream of 
         the xdslLineServiceProfileTable in the XDSL-MIB.
         A value 0 means that no data is available (or rtx mode is in use). 

         ALCATEL NOTE:
             ACCESS:   NA                  USAGE:    NA
             PERSIST:  NO                  INSRVMOD: NA
             RANGE:    0..262143           DEFVALUE: 0
             UNITS:    kbits/sec           SPARSE:   NA
             DESCR:    NA "
::= { xdslLinkUpEntry 11 }

xdslLinkUpMaxBitrateDownstream         OBJECT-TYPE
        SYNTAX          INTEGER 
        ACCESS          read-only
        STATUS          mandatory
        DESCRIPTION
        "This object contains the configured maximum bitrate for the downstream
         data flow. 
         It corresponds with the data configured in xdslMaxBitrateDownstream of
         the xdslLineServiceProfileTable in the XDSL-MIB.
         A value 0 means that no data is available (or rtx mode is in use).
 
         ALCATEL NOTE:
             ACCESS:   NA                  USAGE:    NA
             PERSIST:  NO                  INSRVMOD: NA
             RANGE:    0..262143           DEFVALUE: 0
             UNITS:    kbits/sec           SPARSE:   NA
             DESCR:    NA "
::= { xdslLinkUpEntry 12 }

xdslLinkUpThresholdBitrateUpstream     OBJECT-TYPE
        SYNTAX          INTEGER 
        ACCESS          read-only
        STATUS          mandatory
        DESCRIPTION
        "This object contains the configured threshold bitrate for the upstream 
         data flow. 
         When the actual bitrate as recorded in xdslLinkUpActualBitrateUpstream 
         is lower than this threshold value, a near-end - Bitrate Threshold 
         Alarm is raised.  
         It corresponds with the data configured in xdslPlannedBitrateUpstream
         of the xdslLineServiceProfileTable in the XDSL-MIB.
         A value 0 means that no data is available (or rtx mode is in use).

         ALCATEL NOTE:
             ACCESS:   NA                  USAGE:    NA
             PERSIST:  NO                  INSRVMOD: NA
             RANGE:    0..262143           DEFVALUE: 0
             UNITS:    kbits/sec           SPARSE:   NA
             DESCR:    NA "
::= { xdslLinkUpEntry 13 }

xdslLinkUpThresholdBitrateDownstream   OBJECT-TYPE
        SYNTAX          INTEGER 
        ACCESS          read-only
        STATUS          mandatory
        DESCRIPTION
        "This object contains the configured threshold bitrate for the 
         downstream data flow. 
         When the actual bitrate as recorded in 
         xdslLinkUpActualBitrateDownstream is lower than this threshold value,
         a far-end - Bitrate Threshold Alarm is raised.  
         It corresponds with the data configured in 
         xdslPlannedBitrateDownUpstream of the xdslLineServiceProfileTable in
         the XDSL_MIB
         A value 0 means that no data is available (or rtx mode is in use).

         ALCATEL NOTE:
             ACCESS:   NA                  USAGE:    NA
             PERSIST:  NO                  INSRVMOD: NA
             RANGE:    0..262143           DEFVALUE: 0
             UNITS:    kbits/sec           SPARSE:   NA
             DESCR:    NA "
::= { xdslLinkUpEntry 14 }

xdslLinkUpMaxDelayUpstream             OBJECT-TYPE
        SYNTAX          INTEGER 
        ACCESS          read-only
        STATUS          mandatory
        DESCRIPTION
        "This object contains the configured maximum interleaving delay for the 
         upstream data flow. 
         It corresponds with the data configured in 
         xdslMaxInterleavingDelayUpstream of the 
         adslLineServiceProfileChannelTable in the XDSL-MIB.
         A value 0 means that no data is available (or rtx mode is in use).

         ALCATEL NOTE:
             ACCESS:   NA                  USAGE:    NA
             PERSIST:  NO                  INSRVMOD: NA
             RANGE:    0..63               DEFVALUE: 0
             UNITS:    milliseconds        SPARSE:   NA
             DESCR:    NA "
::= { xdslLinkUpEntry 15 }

xdslLinkUpMaxDelayDownstream           OBJECT-TYPE
        SYNTAX          INTEGER 
        ACCESS          read-only
        STATUS          mandatory
        DESCRIPTION
        "This object contains the configured maximum interleaving delay for the 
         downstream data flow. 
         It corresponds with the data configured in 
         xdslMaxInterleavingDelayDownstream of the 
         xdslLineServiceProfileChannelTable in the XDSL-MIB.
         A value 0 means that no data is available (or rtx mode is in use).

         ALCATEL NOTE:
             ACCESS:   NA                  USAGE:    NA
             PERSIST:  NO                  INSRVMOD: NA
             RANGE:    0..63               DEFVALUE: 0
             UNITS:    milliseconds        SPARSE:   NA
             DESCR:    NA "
::= { xdslLinkUpEntry 16 }

xdslLinkUpTargetNoiseMarginUpstream    OBJECT-TYPE
        SYNTAX          INTEGER 
        ACCESS          read-only
        STATUS          mandatory
        DESCRIPTION
        "This object contains the configured target noise margin for the 
         upstream data flow. 
         It corresponds with the data configured in 
         xdslLineTargetNoiseMarginUpstream of the xdslLineSpectrumProfileTable
         in the XDSL-MIB.
         It is represented as 1/10 * xdslLinkUpTargetNoiseMarginUpstream, with
         a range of (0..31 dB).
         A value 0 means that no data is available.

         ALCATEL NOTE:
             ACCESS:   NA                  USAGE:    NA
             PERSIST:  NO                  INSRVMOD: NA
             RANGE:    0..310              DEFVALUE: 0
             UNITS:    dB / 10             SPARSE:   NA
             DESCR:    NA "
::= { xdslLinkUpEntry 17 }

xdslLinkUpTargetNoiseMarginDownstream  OBJECT-TYPE
        SYNTAX          INTEGER 
        ACCESS          read-only
        STATUS          mandatory
        DESCRIPTION
        "This object contains the configured target noise margin for the 
         downstream data flow. 
         It corresponds with the data configured in 
         xdslLineTargetNoiseMarginDownstream of the 
         xdslLineSpectrumProfileTable in the XDSL-MIB.
         It is represented as 1/10 * xdslLinkUpTargetNoiseMarginDownstream,
         with a range of (0..31 dB).
         A value 0 means that no data is available.

         ALCATEL NOTE:
             ACCESS:   NA                  USAGE:    NA
             PERSIST:  NO                  INSRVMOD: NA
             RANGE:    0..310              DEFVALUE: 0
             UNITS:    dB / 10             SPARSE:   NA
             DESCR:    NA "
::= { xdslLinkUpEntry 18 }

xdslLinkUpTimestamp     OBJECT-TYPE
        SYNTAX          Gauge 
        ACCESS          read-write
        STATUS          mandatory
        DESCRIPTION
        "This object contains the timestamp set by the manager.
         The manager sets this timestamp to the time of the previous collection
         period. 
         The timestamp is expressed as the number of seconds encountered since
         January 1, 1900.  

         ALCATEL NOTE:
             ACCESS:   NA                  USAGE:    NA
             PERSIST:  NO                  INSRVMOD: YES
             RANGE:    NA                  DEFVALUE: NA
             UNITS:    seconds             SPARSE:   NA
             DESCR:    NA "
::= { xdslLinkUp  2 }

xdslLinkUpLineBitmapTable              OBJECT-TYPE
        SYNTAX          SEQUENCE OF XdslLinkUpLineBitmapEntry
        ACCESS          not-accessible
        STATUS          mandatory
        DESCRIPTION
        "The xDSL Link-up Line Bitmap table has an entry for each xDSL board.
         It gives for each board a bitmap with the lines for which an entry is
         changed in the xdslLinkUpTable in the time span between the 
         time provided by the manager (xdslLinkUpTimestamp) and the actual
         time.

         ALCATEL NOTE:
             TABLESIZE: DEP [number of XDSL boards]                    
             DESCR:     NA                   "
::= { xdslLinkUp  3 }

xdslLinkUpLineBitmapEntry              OBJECT-TYPE
        SYNTAX  XdslLinkUpLineBitmapEntry
        ACCESS  not-accessible
        STATUS  mandatory
        DESCRIPTION
        "An entry in the xDSL Link-up Line Bitmap table.

         Row creation : An entry for a board is created when the board becomes
                        operational.
         Row deletion : The entry for a board is deleted when the board becomes
                        unavailable. "
        INDEX          {eqptSlotId}
::= { xdslLinkUpLineBitmapTable  1 }

XdslLinkUpLineBitmapEntry ::=
        SEQUENCE {   
            xdslLinkUpLineBitmap                 OCTET STRING
        }

xdslLinkUpLineBitmap OBJECT-TYPE
        SYNTAX          OCTET STRING  
        ACCESS          read-only
        STATUS          mandatory
        DESCRIPTION
        "Bitmap whereby each bit represents a line on an xDSL board.
 
         A bit is set for a line, when the timestamp provided by the manager 
         (xdslLinkUpTimestamp) is lower (earlier in time) than the link up or 
         link down timestamp recorded in xdslLinkUpTimestampUp or
         xdslLinkUpTimestampDown of the xdslLinkUpTable for that line.
 
         The lines are identified in the bitmap as follows :   
                      MSB                         LSB
           octet  1 :   8   7   6   5   4   3   2   1
           octet  2 :  16  15  14  13  12  11   10  9
           octet  3 :  24  ..  ..          
           ..
           octet  6 :  48  47  46  45  44  43  42  41 
           octet  7 :  56  55  54  53  52  51  50  49 
           octet  8 :  64  63  62  61  60  59  58  57 
           octet  9 :  72  71  70  69  68  67  66  65

         ALCATEL NOTE:
             ACCESS:   NA                  USAGE:    NA
             PERSIST:  NO                  INSRVMOD: NA
             RANGE:    9                   DEFVALUE: NA
             UNITS:    octets              SPARSE:   NA
             DESCR:    NA "
::= { xdslLinkUpLineBitmapEntry  1 }

xdslDpboProfileIndexNext       OBJECT-TYPE
        SYNTAX          AsamNextProfileIndex
        ACCESS          read-only
        STATUS          mandatory
        DESCRIPTION     
        "This object contains an appropriate value to be used for 
         xdslDpboProfileIndex when creating entries in the
         xdslDpboProfileTable. 
         The value 0 indicates that no unassigned entries are available. To 
         obtain the xdslDpboProfileIndex value for a new entry, the
         manager issues a management protocol retrieval operation to obtain the
         current value of this object.  After each retrieval, the agent should
         modify the value to the next unassigned index.

         ALCATEL NOTE:
             ACCESS:   NA                  USAGE:    NA
             PERSIST:  NO                  INSRVMOD: NA
             RANGE:    0..50               DEFVALUE: 1
             UNITS:    NA                  SPARSE:   NA
             DESCR:    NA "
::= {xdslDpboProfile 1}

xdslDpboProfileMaxIndex        OBJECT-TYPE
        SYNTAX          AsamMaxProfileIndex
        ACCESS          read-only
        STATUS          mandatory
        DESCRIPTION
        "This object represents the maximum number of xdslDpboProfiles
         that can be created. The object xdslDpboProfileIndexNext will 
         have values ranging from 0 to the value represented by this object.

         ALCATEL NOTE:
             ACCESS:   NA                  USAGE:    NA
             PERSIST:  NO                  INSRVMOD: NA
             RANGE:    50..50              DEFVALUE: 50
             UNITS:    NA                  SPARSE:   NA
             DESCR:    NA "
::= {xdslDpboProfile 2}

xdslDpboProfileTable           OBJECT-TYPE
        SYNTAX          SEQUENCE OF XdslDpboProfileEntry
        ACCESS          not-accessible
        STATUS          mandatory
        DESCRIPTION     
        "This table contains the Dpbo related parameters of the modem
         configuration. One entry in this table reflects a profile which
         can be used to configure the modem for a physical line.

         ALCATEL NOTE:
             TABLESIZE: 50                   
             DESCR:     NA                   "
::= {xdslDpboProfile 3}

xdslDpboProfileEntry           OBJECT-TYPE
        SYNTAX          XdslDpboProfileEntry
        ACCESS          not-accessible
        STATUS          mandatory
        DESCRIPTION     
        "Each entry consists of a list of line related parameters that serve 
         to configure Dpbo. A profile can be created in one step with
         all necessary parameter values and xdslDpboProfileRowStatus
         set to createAndGo.
         It can also be created in several steps by specifying values of a few
         objects in each step. The xdslDpboProfileRowStatus is set to
         createAndWait in the first step and to Active in the last step.

         Row creation : An entry is created when the manager requests to create
                        a Dpbo profile.
         Row deletion : An entry is deleted when the manager requests to delete
                        a Dpbo profile. "
        INDEX          {xdslDpboProfileIndex}
::= {xdslDpboProfileTable 1}

XdslDpboProfileEntry ::=
        SEQUENCE {
            xdslDpboProfileIndex                AsamProfileIndex,
            xdslDpboProfileName                 AsamProfileName,
            xdslDpboProfileVersionNbr           INTEGER,
            xdslDpboProfileUsedStatus           AsamProfileRefCount,
            xdslDpboElectricalLength            INTEGER,
            xdslDpboCableModelParamA            INTEGER,
            xdslDpboCableModelParamB            INTEGER,
            xdslDpboCableModelParamC            INTEGER,
            xdslDpboMinUsableSignalLevel        INTEGER,
            xdslDpboMinFrequency                INTEGER,
            xdslDpboMaxFrequency                INTEGER,
            xdslDpboAssumedExchangePsdMask      ExchangePsdShapeType,
            xdslDpboCustomPsdMaskDownstream     DpboCustomPsdShapeType,
            xdslDpboMaxUsableFrequencyControl   INTEGER,
            xdslDpboRemoteSideElectricalLength  INTEGER,
            xdslDpboOffset                      INTEGER,
            xdslDpboProfileRowStatus            RowStatus,
            xdslDpboProfileModifyStatus         INTEGER
        }

xdslDpboProfileIndex           OBJECT-TYPE
        SYNTAX          AsamProfileIndex
        ACCESS          not-accessible
        STATUS          mandatory
        DESCRIPTION     
        "This object is used to uniquely identify an entry in this table.
         It is used by the line configuration table and by the board
         Configuration table to identify a row of the table. The max value of
         this object is limited to xdslDpboProfileMaxIndex value.
         In addition, special index values are defined to identify temporary
         entries in this table used to contain the modifications performed on
         an existing profile. The index value of such an entry is obtained by
         adding a fixed offset to the corresponding index. The value of this
         offset is contained in xdslDpboProfileIndexOffset. A temporary
         entry exists only during the profile modification, it is created at
         xdslDpboProfileModifyStatus = modifyStart and is deleted at
         modifyCancel or modifyComplete. It can only be accessed during the
         modification to retrieve the updated parameters values of a profile.
         The nominal entry contains the original profile settings and is not
         updated until the profile modification is completed and validated.
         The offset entries are read only, all write operations must be
         performed using the nominal index.
         The getnext can be used to retrieve the nominal dpbo profile
         entries and does not return the temporary profiles entries at the
         special offset index values.

         ALCATEL NOTE:
             ACCESS:   NA                  USAGE:    NA
             PERSIST:  YES                 INSRVMOD: NA
             RANGE:    1..50               DEFVALUE: NA
             UNITS:    NA                  SPARSE:   NA
             DESCR:    NA "
::= {xdslDpboProfileEntry 1}

xdslDpboProfileName            OBJECT-TYPE
        SYNTAX          AsamProfileName
        ACCESS          read-write
        STATUS          mandatory
        DESCRIPTION     
        "A textual name identifying this profile. This name has to be unique.

         ALCATEL NOTE:
             ACCESS:   NA                  USAGE:    MAND
             PERSIST:  YES                 INSRVMOD: YES
             RANGE:    NA                  DEFVALUE: NA
             UNITS:    NA                  SPARSE:   NA
             DESCR:    NA "
::= {xdslDpboProfileEntry 2}

xdslDpboProfileVersionNbr      OBJECT-TYPE
        SYNTAX          INTEGER
        ACCESS          read-write
        STATUS          mandatory
        DESCRIPTION     
        "The manager can associate a version number to the profile. It is set
         to 1 when the profile is first created and will be incremented by the
         manager when the profile is modified.

         ALCATEL NOTE:
             ACCESS:   NA                  USAGE:    OPT
             PERSIST:  YES                 INSRVMOD: YES
             RANGE:    NA                  DEFVALUE: NA
             UNITS:    NA                  SPARSE:   NA
             DESCR:    NA "
        DEFVAL          {1}
::= {xdslDpboProfileEntry 3}

xdslDpboProfileUsedStatus      OBJECT-TYPE
        SYNTAX          AsamProfileRefCount
        ACCESS          read-only
        STATUS          mandatory
        DESCRIPTION
        "Indicates the number of entities using this profile. If the reference
         count is greater than 0, then this profile is 'in use', and may NOT be
         deleted. If the value is 0, then this profile is 'not in use', and can
         be deleted.

         ALCATEL NOTE:
             ACCESS:   NA                  USAGE:    NA
             PERSIST:  NO                  INSRVMOD: NA
             RANGE:    NA                  DEFVALUE: 0
             UNITS:    NA                  SPARSE:   NA
             DESCR:    NA "
::= {xdslDpboProfileEntry 4}

xdslDpboElectricalLength       OBJECT-TYPE
        SYNTAX          INTEGER
        ACCESS          read-write   
        STATUS          mandatory
        DESCRIPTION
        "Specifies the electrical length of the loop segment from the exchange
         to the remote flexibility point. If set to 0 dB, all DPBO parameters
         are ignored except xdslDpboCustomPsdMaskDownstream. This parameter
         matches the DPBOESEL parameter described in ITU-T G.997.1
         Range: 0 to 255.9 dB with 0,1 dB steps.
         The electrical length is represented as
         1/10 * xdslDpboElectricalLength.

         ALCATEL NOTE:
             ACCESS:   NA                  USAGE:    OPT
             PERSIST:  YES                 INSRVMOD: YES
             RANGE:    0..2559             DEFVALUE: NA
             UNITS:    dB / 10             SPARSE:   NA
             DESCR:    NA "
        DEFVAL          {0}           
::= {xdslDpboProfileEntry 5}

xdslDpboCableModelParamA       OBJECT-TYPE
        SYNTAX          INTEGER
        ACCESS          read-write   
        STATUS          mandatory
        DESCRIPTION
        "Specifies the DPBO Cable Model parameter A. This parameter matches the
         DPBOESCMA parameter described in ITU-T G.997.1
         Range: -1 to 1.5 with 2^-8 steps.
         The cable model parameter A is represented as
         2^-8 * xdslDpboCableModelParamA.

         ALCATEL NOTE:
             ACCESS:   NA                  USAGE:    OPT
             PERSIST:  YES                 INSRVMOD: YES
             RANGE:    -256..384           DEFVALUE: NA
             UNITS:    1 / 2^8             SPARSE:   NA
             DESCR:    NA "
        DEFVAL          {0}           
::= {xdslDpboProfileEntry 6}

xdslDpboCableModelParamB       OBJECT-TYPE
        SYNTAX          INTEGER
        ACCESS          read-write   
        STATUS          mandatory
        DESCRIPTION
        "Specifies the DPBO Cable Model parameter B. This parameter matches the
         DPBOESCMB parameter described in ITU-T G.997.1
         Range: -1 to 1.5 Hz^-0.5 with 2^-8 Hz^-0.5 steps.
         The cable model parameter B is represented as
         2^-8 * xdslDpboCableModemParamB.

         ALCATEL NOTE:
             ACCESS:   NA                  USAGE:    OPT
             PERSIST:  YES                 INSRVMOD: YES
             RANGE:    -256..384           DEFVALUE: NA
             UNITS:    Hz^-0.5 / 2^8       SPARSE:   NA
             DESCR:    NA "
        DEFVAL          {0}           
::= {xdslDpboProfileEntry 7}

xdslDpboCableModelParamC       OBJECT-TYPE
        SYNTAX          INTEGER
        ACCESS          read-write   
        STATUS          mandatory
        DESCRIPTION
        "Specifies the DPBO Cable Model parameter C. This parameter matches the
         DPBOESCMC parameter described in ITU-T G.997.1
         Range: -1 to 1.5 Hz^-1 with 2^-8 Hz^-1 steps.
         The cable model parameter C is represented as
         2^-8 * xdslDpboCableModelParamC.

         ALCATEL NOTE:
             ACCESS:   NA                  USAGE:    OPT
             PERSIST:  YES                 INSRVMOD: YES
             RANGE:    -256..384           DEFVALUE: NA
             UNITS:    Hz^-1 / 2^8         SPARSE:   NA
             DESCR:    NA "
        DEFVAL          {0}           
::= {xdslDpboProfileEntry 8}

xdslDpboMinUsableSignalLevel       OBJECT-TYPE
        SYNTAX          INTEGER
        ACCESS          read-write   
        STATUS          mandatory
        DESCRIPTION
        "Specifies the DPBO_minimum usable signal level. This parameter is used
         to determine the maximum usable frequency. Above this frequency DPBO
         shaping is not applied anymore. This parameter matches the DPBOMUS
         parameter described in ITU-T G.997.1
         Note: this parameter refers to a mask level.
         Range: -140 to 0 dBm/Hz with 0,1 dBm/Hz steps.
         The minimum usable signal is represented as
         1/10 * xdslDpboMinUsableSignalLevel.

         ALCATEL NOTE:
             ACCESS:   NA                  USAGE:    OPT
             PERSIST:  YES                 INSRVMOD: YES
             RANGE:    -1400..0            DEFVALUE: NA
             UNITS:    dBm/Hz / 10         SPARSE:   NA
             DESCR:    NA "
        DEFVAL          {-1275}
::= {xdslDpboProfileEntry 9}

xdslDpboMinFrequency       OBJECT-TYPE
        SYNTAX          INTEGER
        ACCESS          read-write   
        STATUS          mandatory
        DESCRIPTION
        "Specifies the frequency range over which DPBO shaping is applied. If
         xdslDpboMinFrequency is equal to xdslDpboMaxFrequency all DBPO
         parameters are ignored except  xdslDpboCustomPsdMaskDownstream. This
         parameter matches the DPBOFMIN parameter described in ITU-T G.997.1
         Limitation: Minimum Frequency <= Maximum Frequency
         Range: 0 to 30000 kHz with 1 kHz steps.

         ALCATEL NOTE:
             ACCESS:   NA                  USAGE:    OPT
             PERSIST:  YES                 INSRVMOD: YES
             RANGE:    0..30000            DEFVALUE: NA
             UNITS:    kHz                 SPARSE:   NA
             DESCR:    NA "
        DEFVAL          {0}           
::= {xdslDpboProfileEntry 10}

xdslDpboMaxFrequency       OBJECT-TYPE
        SYNTAX          INTEGER
        ACCESS          read-write
        STATUS          mandatory
        DESCRIPTION
        "Specifies the frequency range over which DPBO shaping is applied.If
         xdslDpboMinFrequency is equal to xdslDpboMaxFrequency all DBPO
         parameters are ignored except  xdslDpboCustomPsdMaskDownstream. This
         parameter matches the DPBOFMAX parameter described in ITU-T G.997.1
         Limitation: Minimum Frequency <= Maximum Frequency
         Range: 0 to 30000 kHz with 1 kHz steps.

         ALCATEL NOTE:
             ACCESS:   NA                  USAGE:    OPT
             PERSIST:  YES                 INSRVMOD: YES
             RANGE:    0..30000            DEFVALUE: NA
             UNITS:    kHz                SPARSE:   NA
             DESCR:    NA "
        DEFVAL          {30000}           
::= {xdslDpboProfileEntry 11}

xdslDpboAssumedExchangePsdMask       OBJECT-TYPE
        SYNTAX          ExchangePsdShapeType
        ACCESS          read-write   
        STATUS          mandatory
        DESCRIPTION
        "Specifies the Assumed Exchange PSD mask to be protected by the DPBO
         shaping mechanism at the remote flexibility point. This parameter
         matches the DPBOEPSD parameter described in ITU-T G.997.1
         A number of 2 to 16 PSD points can be specified.
         The successive PSD points must have increasing (>/=) frequencies.
         It is allowed that for two successive PSD points, different PSD
         levels are defined at a same frequency (brickwall).
         The custom PSD Shape is coded as a variable length octet string
         defined as follows:
         OCTET 0: reserved (set to 0)
         OCTETS 1..2: INTEGER (0..30000), frequency of the first PSD point
         expressed in kHz. The value is defined as MSB-LSB (big-endian).
         OCTETS 3..4: INTEGER (0..1275), -10*PSD level (in dBm/Hz) of the
         first PSD point. The value is defined as MSB-LSB (big-endian).
         Only PSD values within the standard range from -95 to 0 dBm/Hz are
         guaranteed.
         OCTETS 5..8: define the frequency and PSD level of PSD point 2.
         ....        up to
         OCTETS 4*N-3..4*N: define the frequency and PSD level of the last PSD
         point N with N<=16.

         ALCATEL NOTE:
             ACCESS:   NA                  USAGE:    OPT
             PERSIST:  YES                 INSRVMOD: YES
             RANGE:    0..65               DEFVALUE: NA
             UNITS:    OCTETS              SPARSE:   NA
             DESCR:    NA "
        DEFVAL              {'00000003B6000403B60004039D005002D5008A01BA008A016D0450016D065601D108A001DE09C402520BBA03200C3C03B6753003B6'H}
::= {xdslDpboProfileEntry 12} 

xdslDpboCustomPsdMaskDownstream       OBJECT-TYPE
        SYNTAX          DpboCustomPsdShapeType
        ACCESS          read-write   
        STATUS          mandatory
        DESCRIPTION
        "Specifies PSD breakpoints of DPBO Mode Independent Custom PSD Mask.
         A number of 2 to 32 PSD breakpoints can be specified. This parameter
         matches the PSDMASKds parameter described in ITU-T G.997.1
         This set of breakpoints may contain two subsets :
         The first sub-set defines the DPBO Custom PSD Mask. It matches the
         DPBOPSDMASKds parameter described in ITU-T G.997.1
         The second sub-set (if any), defines the DPBO Minimum Override Mask.
         It matches the DPBOLFO parameter described in ITU-T G.997.1
         The successive PSD points of each sub-set must have
         increasing (>/=) frequencies.
         It is allowed that for two successive PSD points, different PSD
         levels are defined at a same frequency (brickwall).
         The second sub-set starts at the first breakpoint whose frequency is
         lower than the frequency of the previous breakpoint.
         The DPBO Mode Independent Custom PSD Shape is coded as a variable
         length octet string defined as follows:
         OCTET 0: reserved (set to 0)
         OCTETS 1..2: INTEGER (0..30000), frequency of the first PSD point
         expressed in kHz. The value is defined as MSB-LSB (big-endian).
         OCTETS 3..4: INTEGER (0..1275), -10*PSD level (in dBm/Hz) of the first
         PSD point. The value is defined as MSB-LSB (big-endian).
         Only PSD values within the standard range from -95 to 0 dBm/Hz are
         guaranteed.
         OCTETS 5..8: define the frequency and PSD level of PSD point 2.
         ....        up to
         OCTETS 4*N-3..4*N: define the frequency and PSD level of the last PSD
         point N with N<=32.
         ALCATEL NOTE:
             ACCESS:   NA                  USAGE:    OPT
             PERSIST:  YES                 INSRVMOD: YES
             RANGE:    0..129              DEFVALUE: NA
             UNITS:    OCTETS              SPARSE:   NA
             DESCR:    NA "
        DEFVAL              {''H}
::= {xdslDpboProfileEntry 13}

xdslDpboMaxUsableFrequencyControl       OBJECT-TYPE
        SYNTAX          INTEGER
        ACCESS          read-write   
        STATUS          mandatory
        DESCRIPTION
        "This parameter specifies the electrical length to be used for the
         computation of the DPBO Maximum Usable Frequency. It enables a more
         flexible control of the computation of the DPBO maximum usable
         frequency compared to the requirements.
         Range: 0 to 255.9 dB with 0,1 dB steps, plus value 300 dB used as
         special value.
         Special value 300 dB indicates that maximum usable frequency is
         directly calculated using standard DPBO algorithm.
         The maximum usable frequency control is represented as
         1/10 * xdslDpboMufControl.

         ALCATEL NOTE:
             ACCESS:   NA                  USAGE:    OPT
             PERSIST:  YES                 INSRVMOD: YES
             RANGE:    0..2559, 3000       DEFVALUE: NA
             UNITS:    dB / 10             SPARSE:   NA
             DESCR:    NA "
        DEFVAL          {3000}           
::= {xdslDpboProfileEntry 14} 

xdslDpboRemoteSideElectricalLength       OBJECT-TYPE
        SYNTAX          INTEGER
        ACCESS          read-write   
        STATUS          mandatory
        DESCRIPTION
        "Specifies the extra DPBO remote side electrical length parameter. If
         this parameter is set different from 0dB it modifies the standard DPBO
         algorithm defined in ITU-T G.997.1 by adding an extra term, function
         of this parameter, used to perfom equal FEXT DPBO.
         Range: 0 to 255.99 dB with 0,01 dB steps.
         The remote side electrical length is represented as
         1/100 * xdslDpboRemoteSideElectricalLength.

         ALCATEL NOTE:
             ACCESS:   NA                  USAGE:    OPT
             PERSIST:  YES                 INSRVMOD: YES
             RANGE:    0..25599            DEFVALUE: NA
             UNITS:    dB / 100            SPARSE:   NA
             DESCR:    NA "
        DEFVAL          {0}           
::= {xdslDpboProfileEntry 15} 

xdslDpboOffset       OBJECT-TYPE
        SYNTAX          INTEGER
        ACCESS          read-write   
        STATUS          mandatory
        DESCRIPTION
        "Specifies the additional extra DPBO Offset parameter used for further
         fine-tuning of the 'Predicted attenuated exchange PSD Mask'. When
         configured with special value 0 dB this parameter is disabled.
         Range: -256 to 255.9 dB with 0,1 dB steps.
         The dpbo offset is represented as
         1/10 * xdslDpboOffset.

         ALCATEL NOTE:
             ACCESS:   NA                  USAGE:    OPT
             PERSIST:  YES                 INSRVMOD: YES
             RANGE:    -2560..2559         DEFVALUE: NA
             UNITS:    dB / 10             SPARSE:   NA
             DESCR:    NA "
        DEFVAL          {0}
::= {xdslDpboProfileEntry 16} 

xdslDpboProfileRowStatus       OBJECT-TYPE
        SYNTAX          RowStatus
        ACCESS          read-write
        STATUS          mandatory
        DESCRIPTION 
        "This object is used to create a new row or delete an existing row in
         this table. The usage is as per standard semantics of 'RowStatus'
         defined in SNMPv2-TC.
            o Both 'createAndGo' and 'createAndWait' options of row creation
              are supported.
            o The entry associated with a Profile that is being used may
              not be deleted.

         ALCATEL NOTE:
             ACCESS:   NA                  USAGE:    MAND
             PERSIST:  YES                 INSRVMOD: YES
             RANGE:    NA                  DEFVALUE: NA
             UNITS:    NA                  SPARSE:   NA
             DESCR:    NA "
::= {xdslDpboProfileEntry 17}

xdslDpboProfileModifyStatus OBJECT-TYPE
        SYNTAX          INTEGER {
                            modifyStart (1),
                            modifyCancel (2),
                            modifyComplete (3)
                        }
        ACCESS          read-write
        STATUS          mandatory 
        DESCRIPTION 
        "This variable is used to modify a Dpbo profile after
         it has been created.
         The following values are defined:
          - modifyStart (1): set by the manager to enable the
            modification of the parameters of the Dpbo profile.
          - modifyCancel (2): set by the manager to stop the profile
            modification and cancel all changes. The original profile
            settings are maintained.
          - modifyComplete (3): used by the manager to activate the
            changes and replace the old profile. The modification of the
            dpbo profile parameters (other than name, version) 
            is disabled.
            The system will also set the 
            xdslDpboProfileModifyStatus value to 'modifyComplete'
            after a modifyCancel request from the manager.
           See xdslDpboProfileIndex about the retrieval of the
           original or the updated profile setting values during the profile
           modification.

         ALCATEL NOTE:
             ACCESS:   NA                  USAGE:    OPT
             PERSIST:  YES                 INSRVMOD: YES
             RANGE:    NA                  DEFVALUE: NA
             UNITS:    NA                  SPARSE:   NA
             DESCR:    NA "
        DEFVAL          {modifyComplete}
 ::= {xdslDpboProfileEntry 18}

xdslDpboProfileMappingTable    OBJECT-TYPE
        SYNTAX          SEQUENCE OF XdslDpboProfileMappingEntry
        ACCESS          not-accessible
        STATUS          mandatory
        DESCRIPTION
        "The (conceptual) listing the profile name to profile Index
         Mapping.

         ALCATEL NOTE:
             TABLESIZE: 50                    
             DESCR:     NA                           "
::= {xdslDpboProfile 4}

xdslDpboProfileMappingEntry    OBJECT-TYPE
      SYNTAX            XdslDpboProfileMappingEntry
      ACCESS            not-accessible
      STATUS            mandatory
      DESCRIPTION
        "An entry (conceptual row) representing the profile Name to Index
         Mapping.

         Row creation : When an entry is created in the 
                        xdslDpboProfileTable, an entry is created in
                        this table.
         Row deletion : When an entry is deleted from the
                        xdslDpboProfileTable, the entry is deleted from
                        this table. "
      INDEX            {xdslDpboProfileMappingName}
::= { xdslDpboProfileMappingTable 1 }

XdslDpboProfileMappingEntry ::=
        SEQUENCE {
            xdslDpboProfileMappingName        AsamProfileName,
            xdslDpboProfileMappingIndex       AsamProfileIndex
        }

xdslDpboProfileMappingName     OBJECT-TYPE
        SYNTAX          AsamProfileName
        ACCESS          not-accessible
        STATUS          mandatory
        DESCRIPTION
        "The Dpbo profile name.

         ALCATEL NOTE:
             ACCESS:   NA                  USAGE:    NA
             PERSIST:  NO                  INSRVMOD: NA
             RANGE:    NA                  DEFVALUE: NA
             UNITS:    NA                  SPARSE:   NA
             DESCR:    NA "
::= { xdslDpboProfileMappingEntry 1 }

xdslDpboProfileMappingIndex    OBJECT-TYPE
        SYNTAX          AsamProfileIndex
        ACCESS          read-only
        STATUS          mandatory
        DESCRIPTION
        "The Index of the corresponding Dpbo profile.

         ALCATEL NOTE:
             ACCESS:   NA                  USAGE:    NA
             PERSIST:  NO                  INSRVMOD: NA
             RANGE:    1..50               DEFVALUE: NA
             UNITS:    NA                  SPARSE:   NA
             DESCR:    NA "
::= { xdslDpboProfileMappingEntry 2 }

xdslDpboProfileIndexOffset     OBJECT-TYPE
        SYNTAX          AsamMaxProfileIndex
        ACCESS          read-only
        STATUS          mandatory
        DESCRIPTION
        "This object represents the offset to be added to an existing Dpbo
         profile index during a modification in order to access the temporary
         profile entry that contains the updates being done on that profile, 
         see xdslDpboProfileIndex.

         ALCATEL NOTE:
             ACCESS:   NA                  USAGE:    NA
             PERSIST:  NO                  INSRVMOD: NA
             RANGE:    1000                DEFVALUE: 1000
             UNITS:    NA                  SPARSE:   NA
             DESCR:    NA "
::= {xdslDpboProfile 5}

xdslBoardConfTable       OBJECT-TYPE
        SYNTAX          SEQUENCE OF XdslBoardConfEntry
        ACCESS          not-accessible
        STATUS          mandatory
        DESCRIPTION     
        "This table contains per board configuration information about the
         modem.

         ALCATEL NOTE:
             TABLESIZE: DEP [number of XDSL boards]                    
             DESCR:     NA                   "
::= {xdslBoard 1}

xdslBoardConfEntry       OBJECT-TYPE
        SYNTAX          XdslBoardConfEntry
        ACCESS          not-accessible
        STATUS          mandatory
        DESCRIPTION     
        "An entry in the xdslBoardConfTable contains per board configuration
         information about the modem.

         Row creation : Entry for a board is created by the system when the
                        board is planned.
         Row deletion : Entry for a board is deleted by the system when the
                        board is unplanned. "
        INDEX          {eqptSlotId}
::= {xdslBoardConfTable 1}

XdslBoardConfEntry ::=
        SEQUENCE {
            xdslBoardDpboProfileNbr                 AsamProfilePointer
        }
        
xdslBoardDpboProfileNbr              OBJECT-TYPE
        SYNTAX          AsamProfilePointer
        ACCESS          read-write
        STATUS          mandatory
        DESCRIPTION     
        "This object identifies the row of the xdslDpboProfileTable
         which defines the valid dpbo profile for the board.

         ALCATEL NOTE:
             ACCESS:   NA                  USAGE:    OPT
             PERSIST:  YES                 INSRVMOD: YES
             RANGE:    0..50               DEFVALUE: 0
             UNITS:    NA                  SPARSE:   NA
             DESCR:    NA "
        DEFVAL          {0}
::= {xdslBoardConfEntry 1}

xdslLineOverruleTable         OBJECT-TYPE
        SYNTAX          SEQUENCE OF XdslLineOverruleEntry
        ACCESS          not-accessible
        STATUS          mandatory
        DESCRIPTION
        "The xDSL Overrule record table contains configuration parameters which
         overrule the corresponding parameters defined in spectrum- or service- 
         profile attached to this line.

         ALCATEL NOTE:
             TABLESIZE: DEP [number of XDSL lines]                    
             DESCR:     NA                   "
::= { xdslLineOverruleData  1 }

xdslLineOverruleEntry         OBJECT-TYPE
        SYNTAX          XdslLineOverruleEntry
        ACCESS          not-accessible
        STATUS          mandatory
        DESCRIPTION
        "An entry in the xDSL Line Overrule table.

         Row creation : An entry is created when the manager requests to create
                        an Overrule Record.
         Row deletion : An entry is deleted when the manager requests to delete
                        an Overrule Record. "
        INDEX          {ifIndex }
::= { xdslLineOverruleTable  1 }

XdslLineOverruleEntry ::=
        SEQUENCE {
            xdslOverruleRowStatus                         RowStatus,
            xdslOverruleModifyStatus                      INTEGER,
            xdslOverruleMaxBitrateDownstreamChannel1      INTEGER, 
            xdslOverruleMaxBitrateUpstreamChannel1        INTEGER,
            xdslOverruleMaxIntDelayDownstreamChannel1     INTEGER,
            xdslOverruleMaxIntDelayUpstreamChannel1       INTEGER,
            xdslOverruleMinImpNoiseProtDownstreamChannel1 INTEGER,
            xdslOverruleMinImpNoiseProtUpstreamChannel1   INTEGER,
            xdslOverruleTargetNoiseMarginDownstream       INTEGER,
            xdslOverruleTargetNoiseMarginUpstream         INTEGER,
            xdslOverruleMaxNomPsdLevelDownstream          INTEGER,
            xdslOverruleMaxNomPsdLevelUpstream            INTEGER,
            xdslOverruleCarrierMaskDownstream             OCTET STRING,
            xdslOverruleCarrierMaskUpstream               OCTET STRING,
            xdslOverruleNoisePsdModeDownstream            INTEGER,
            xdslOverruleNoisePsdDownstream                NoisePsdDownType,
            xdslOverruleNoisePsdModeUpstream              INTEGER,
            xdslOverruleNoisePsdUpstream                  NoisePsdUpType,
            xdslOverruleRtxModeDownstream                 RtxMode,
            xdslOverruleRtxModeUpstream                   RtxMode,
            xdslOverruleRtxMaxNetDataRateDownstream       INTEGER,
            xdslOverruleRtxMaxNetDataRateUpstream         INTEGER,
            xdslOverruleRtxMaxExpThrptDownstream          INTEGER,
            xdslOverruleRtxMaxExpThrptUpstream            INTEGER,
            xdslOverruleRtxMinInpShineDownstream          INTEGER,
            xdslOverruleRtxMinInpShineUpstream            INTEGER,
            xdslOverruleRtxMinInpReinDownstream           INTEGER,
            xdslOverruleRtxMinInpReinUpstream             INTEGER,
            xdslOverruleRtxMinDelayDownstream             INTEGER,
            xdslOverruleRtxMinDelayUpstream               INTEGER,
            xdslOverruleRtxMaxDelayDownstream             INTEGER,
            xdslOverruleRtxMaxDelayUpstream               INTEGER,
            xdslOverruleRtxShineRatioDownstream           INTEGER,
            xdslOverruleRtxShineRatioUpstream             INTEGER,
            xdslOverruleRtxLeftrThresholdDownstream      INTEGER,
            xdslOverruleRtxLeftrThresholdUpstream        INTEGER
        }

xdslOverruleRowStatus           OBJECT-TYPE
        SYNTAX          RowStatus
        ACCESS          read-write
        STATUS          mandatory
        DESCRIPTION 
        "This object is used to create a new row or delete an existing row in
         this table. The usage is as per standard semantics of 'RowStatus'
         defined in SNMPv2-TC.
            o Both 'createAndGo' and 'createAndWait' options of row creation
              are supported.
            o The entry associated with a Line that is not being configured
              may not be created.

         ALCATEL NOTE:
             ACCESS:   NA                  USAGE:    MAND
             PERSIST:  YES                 INSRVMOD: YES
             RANGE:    NA                  DEFVALUE: NA
             UNITS:    NA                  SPARSE:   NA
             DESCR:    NA "
::= {xdslLineOverruleEntry 1}

xdslOverruleModifyStatus         OBJECT-TYPE
        SYNTAX          INTEGER {
                            modifyStart (1),
                            modifyCancel (2),
                            modifyComplete (3)
                        }
        ACCESS          read-write
        STATUS          mandatory 
        DESCRIPTION 
        "This variable is used to modify a Overrule-record after
         it has been created.
         The following values are defined:
          - modifyStart (1): set by the manager to enable the
            modification of the parameters of the Overrule-record.
          - modifyCancel (2): set by the manager to stop the Overrule-record
            modification and cancel all changes. The original Overrule-record
            settings are maintained.
          - modifyComplete (3): used by the manager to activate the
            changes and replace the old Overrule-record. The modification of 
            the Overrule-record parameters is disabled.
            The system will also set the xdslOverruleModifyStatus value to 
            'modifyComplete' after a modifyCancel request from the manager.

         ALCATEL NOTE:
             ACCESS:   NA                  USAGE:    OPT
             PERSIST:  YES                 INSRVMOD: YES
             RANGE:    NA                  DEFVALUE: NA
             UNITS:    NA                  SPARSE:   NA
             DESCR:    NA "
        DEFVAL          {modifyComplete}
 ::= {xdslLineOverruleEntry 2}

xdslOverruleMaxBitrateDownstreamChannel1       OBJECT-TYPE
        SYNTAX          INTEGER
        ACCESS          read-write
        STATUS          mandatory
        DESCRIPTION     
        "This object contains the maximum allowed bit rate of bearer 1 which 
         will overrule the xdslMaxBitrateDownstream of the 
         xdslLineServiceProfile attached to this line.
         Parameter value -1 indicates that the original ServiceProfile 
         parameter will not be overruled. 

         ALCATEL NOTE:
             ACCESS:   NA                  USAGE:    OPT
             PERSIST:  YES                 INSRVMOD: NO
             RANGE:    -1,0..262143        DEFVALUE: NA
             UNITS:    kbits/sec           SPARSE:   NA
             DESCR:    NA "
        DEFVAL         {-1}
::= { xdslLineOverruleEntry 3}

xdslOverruleMaxBitrateUpstreamChannel1       OBJECT-TYPE
        SYNTAX          INTEGER
        ACCESS          read-write
        STATUS          mandatory
        DESCRIPTION     
        "This object contains the maximum allowed bit rate of bearer 1 which 
         will overrule the xdslMaxBitrateUpstream of the xdslLineServiceProfile
         attached to this line.
         Parameter value -1 indicates that the original ServiceProfile 
         parameter will not be overruled. 

         ALCATEL NOTE:
             ACCESS:   NA                  USAGE:    OPT
             PERSIST:  YES                 INSRVMOD: NO
             RANGE:    -1,0..262143        DEFVALUE: NA
             UNITS:    kbits/sec           SPARSE:   NA
             DESCR:    NA "
        DEFVAL         {-1}
::= { xdslLineOverruleEntry 4}

xdslOverruleMaxIntDelayDownstreamChannel1     OBJECT-TYPE
        SYNTAX          INTEGER
        ACCESS          read-write
        STATUS          mandatory
        DESCRIPTION     
        "This object contains the maximum for the delay, of bearer 1, in
         the given direction which will overrule the 
         xdslMaxInterleavingDelayDownstream of the xdslLineServiceProfile 
         attached to this line.         
         The value 1 is used to specify that fast or pseudo fast latency
         (i.e. no interleaving) must be used.
         The value -1 indicates that the original ServiceProfile parameter
         will not be overruled.

         ALCATEL NOTE:
             ACCESS:   NA                  USAGE:    OPT
             PERSIST:  YES                 INSRVMOD: NO
             RANGE:    -1,1..63            DEFVALUE: NA
             UNITS:    milliseconds        SPARSE:   NA
             DESCR:    NA "
        DEFVAL         {-1}
::= { xdslLineOverruleEntry 5}

xdslOverruleMaxIntDelayUpstreamChannel1       OBJECT-TYPE
        SYNTAX          INTEGER
        ACCESS          read-write
        STATUS          mandatory
        DESCRIPTION     
        "This object contains the maximum for the delay, of bearer 1, in 
         the given direction which will overrule the 
         xdslMaxInterleavingDelayUpstream of the xdslLineServiceProfile 
         attached to this line.         
         The value 1 is used to specify that fast or pseudo fast latency
         (i.e. no interleaving) must be used.
         The value -1 indicates that the original ServiceProfile parameter will
         not be overruled.

         ALCATEL NOTE:
             ACCESS:   NA                  USAGE:    OPT
             PERSIST:  YES                 INSRVMOD: NO
             RANGE:    -1,1..63            DEFVALUE: NA
             UNITS:    milliseconds        SPARSE:   NA
             DESCR:    NA "
        DEFVAL         {-1}
::= { xdslLineOverruleEntry 6}

xdslOverruleMinImpNoiseProtDownstreamChannel1    OBJECT-TYPE
        SYNTAX          INTEGER
        ACCESS          read-write
        STATUS          mandatory
        DESCRIPTION     
        "This object defines the minimum impulse noise protection, of bearer 1, 
         for the given direction which will overrule the 
         xdslMinImpNoiseProtDownstream of the xdslLineServiceProfile attached
         to this line. 
         It is expressed in symbols. Range: 0 to 16 symbols in steps of 0.1.
         It is represented as 1/10 * xdslOverruleMinImpNoiseProtDownstreamChannel1
         The value -1 indicates that the original ServiceProfile parameter will
         not be overruled.

         ALCATEL NOTE:
             ACCESS:   NA                  USAGE:    OPT
             PERSIST:  YES                 INSRVMOD: NA
             RANGE:    -1,0..160           DEFVALUE: NA
             UNITS:    0.1 symbols         SPARSE:   NA
             DESCR:    NA "
        DEFVAL         {-1}
::= { xdslLineOverruleEntry 7}

xdslOverruleMinImpNoiseProtUpstreamChannel1     OBJECT-TYPE
        SYNTAX          INTEGER
        ACCESS          read-write
        STATUS          mandatory
        DESCRIPTION     
        "This object defines the minimum impulse noise protection, of bearer 1, 
         for the given direction which will overrule the 
         xdslMinImpNoiseProtUpstream of the xdslLineServiceProfile attached to 
         this line. 
         It is expressed in symbols. Range: 0 to 16 symbols in steps of 0.1.
         It is represented as 1/10 * xdslOverruleMinImpNoiseProtUpstreamChannel1
         The value -1 indicates that the original ServiceProfile parameter will
         not be overruled.

         ALCATEL NOTE:
             ACCESS:   NA                  USAGE:    OPT
             PERSIST:  YES                 INSRVMOD: NO
             RANGE:    -1,0..160           DEFVALUE: NA
             UNITS:    0.1 symbols         SPARSE:   NA
             DESCR:    NA "
        DEFVAL         {-1}
::= { xdslLineOverruleEntry 8}

xdslOverruleTargetNoiseMarginDownstream    OBJECT-TYPE
        SYNTAX          INTEGER
        ACCESS          read-write
        STATUS          mandatory
        DESCRIPTION     
        "This object defines the target noise margin for the given direction
         which will overrule the xdslTargetNoiseMarginDownstream of the
         xdslLineSpectrumProfile attached to this line. 
         Used at startup for all rate adaptation modes. This is the Noise
         Margin the XTU-R receiver shall achieve, relative to a BER of 1E-7 or 
         better for each of the downstream bearer channels, to successfully
         complete initialization. It is expressed in dB.
         Range: 0 to 31 dB with 0,1 dB steps.
         It is represented as 1/10 * xdslOverruleTargetNoiseMarginDownstream.
         The value -1 indicates that the original SpectrumProfile parameter 
         will not be overruled.

         ALCATEL NOTE:
             ACCESS:   NA                  USAGE:    OPT
             PERSIST:  YES                 INSRVMOD: NA
             RANGE:    -1,0..310           DEFVALUE: NA
             UNITS:    dB / 10             SPARSE:   NA
             DESCR:    NA "
        DEFVAL         {-1}
::= { xdslLineOverruleEntry 9}

xdslOverruleTargetNoiseMarginUpstream      OBJECT-TYPE
        SYNTAX          INTEGER
        ACCESS          read-write
        STATUS          mandatory    
        DESCRIPTION     
        "This object defines the target noise margin for the given direction
         which will overrule the xdslTargetNoiseMarginUpstream of the
         xdslLineSpectrumProfile attached to this line.
         Used at startup for all rate adaptation modes. This is the Noise 
         Margin the XTU-C receiver shall achieve, relative to a BER of 1E-7 or 
         better for each of the upstream bearer channels, to successfully
         complete initialization. It is expressed in dB.
         Range: 0 to 31 dB with 0,1 dB steps.
         It is represented as 1/10 * xdslOverruleTargetNoiseMarginUpstream.
         The value -1 indicates that the original SpectrumProfile parameter 
         will not be overruled.

         ALCATEL NOTE:
             ACCESS:   NA                  USAGE:    OPT
             PERSIST:  YES                 INSRVMOD: YES
             RANGE:    -1,0..310           DEFVALUE: NA
             UNITS:    dB / 10             SPARSE:   NA
             DESCR:    NA "
        DEFVAL         {-1}           
::= { xdslLineOverruleEntry 10}

xdslOverruleMaxNomPsdLevelDownstream     OBJECT-TYPE
        SYNTAX          INTEGER
        ACCESS          read-write
        STATUS          mandatory
        DESCRIPTION     
        "This object specifies a maximum PSD level for the given direction
         which will overrule the MaxPsdLevelDownstream (of all flavors) of
         the xdslLineSpectrumProfile attached to this line.
         This object specifies a maximum PSD level for downstream, flat over
         the passband as an additional restriction to the PSD shape.
         Range is -95.5 to 0 dBm/Hz, in steps of 0.1 dB, the maximum 
         value '0' meaning 'no constraint'.
         It is represented as 1/10* xdslOverruleMaxNomPsdLevelDownstream.
         In case the corresponding DSL standard imposes a more stringent value
         for this parameter, the configured value will be ignored and the
         standard value will apply.
         If the given value is above the limits for a certain DSL-flavor, then 
         the value used to overrule for this flavor is clanmped to his max 
         allowed value.
         The value 1 indicates that the original SpectrumProfile parameters will
         not be overruled.

         ALCATEL NOTE:
             ACCESS:   NA                  USAGE:    OPT
             PERSIST:  YES                 INSRVMOD: YES
             RANGE:    -955..0,1           DEFVALUE: NA
             UNITS:    dBm/Hz * 1/10       SPARSE:   NA
             DESCR:    NA "
        DEFVAL         {1}
::= { xdslLineOverruleEntry 11}

xdslOverruleMaxNomPsdLevelUpstream     OBJECT-TYPE
        SYNTAX          INTEGER
        ACCESS          read-write
        STATUS          mandatory
        DESCRIPTION     
        "This object specifies a maximum PSD level for the given direction
         which will overrule the MaxPsdLevelUpstream (of all flavors) of
         the xdslLineSpectrumProfile attached to this line.
         This object specifies a maximum PSD level for upstream, flat over the
         passband as an additional restriction to the PSD shape.
         Range is -95.5 to 0 dBm/Hz, , in steps of 0.1 dB, the maximum 
         value '0' meaning 'no constraint'.
         It is represented as 1/10* xdslOverruleMaxNomPsdLevelUpstream.
         In case the corresponding DSL standard imposes a more stringent value
         for this parameter, the configured value will be ignored and the
         standard value will apply.
         If the given value is above the limits for a certain DSL-flavor, then 
         the value used to overrule for this flavor is clanmped to his max 
         allowed value.
         The value 1 indicates that the original SpectrumProfile parameters 
         will not be overruled.

         ALCATEL NOTE:
             ACCESS:   NA                  USAGE:    OPT
             PERSIST:  YES                 INSRVMOD: YES
             RANGE:    -955..0,1           DEFVALUE: NA
             UNITS:    dBm/Hz * 1/10       SPARSE:   NA
             DESCR:    NA "
        DEFVAL         {1}
::= { xdslLineOverruleEntry 12}

xdslOverruleCarrierMaskDownstream        OBJECT-TYPE
        SYNTAX          OCTET STRING (SIZE (64))
        ACCESS          read-write
        STATUS          mandatory
        DESCRIPTION     
        "This object defines the carrier mask for the given direction
         which will overrule the xdslLineCarrierMaskDownstream of the
         xdslLineSpectrumProfile attached to this line.
         The downstream carrier mask pattern is a bitlist of 512 bits, each bit
         corresponding to one frequency carrier of the DMT modem system. 
         Carrier 0 is represented by the most significant bit of the map, 
         carrier 511 is represented by the least significant bit of the map.
         A carrier is suppressed by setting its corresponding bit to 1.
         Pilot tones may not be suppressed. If one of the masked carrier is
         defined as a pilot tone in the applicable DSL standard, the modem will 
         not initialize.
         The masking of carriers that are not used in the downstream direction
         or that are not used by the XDSL operational mode will be ignored.
         Carriers 0 to 255 are used for all ADSL/ADSL2 operational modes except 
         for ADSL2 Plus which uses carriers 0 to 511.
         The carrier mask is not used in VDSL mode and will be ignored.
         The value 'all ones' indicates that the original SpectrumProfile 
         parameter will not be overruled.

         ALCATEL NOTE:
             ACCESS:   NA                  USAGE:    OPT
             PERSIST:  YES                 INSRVMOD: YES
             RANGE:    NA                  DEFVALUE: NA
             UNITS:    NA                  SPARSE:   NA
             DESCR:    NA "
        DEFVAL                           
         { 'FFFFFFFFFFFFFFFFFFFFFFFFFFFFFFFFFFFFFFFFFFFFFFFFFFFFFFFFFFFFFFFFFFFFFFFFFFFFFFFFFFFFFFFFFFFFFFFFFFFFFFFFFFFFFFFFFFFFFFFFFFFFFFFF'H}
::= { xdslLineOverruleEntry 13}

xdslOverruleCarrierMaskUpstream            OBJECT-TYPE
        SYNTAX          OCTET STRING (SIZE (8))
        ACCESS          read-write
        STATUS          mandatory
        DESCRIPTION     
        "This object defines the carrier mask for the given direction
         which will overrule the xdslLineCarrierMaskUpstream of the
         xdslLineSpectrumProfile attached to this line.
         The upstream carrier mask pattern is a bitlist of 64 bits, each bit
         corresponding to one frequency carrier of the DMT modem system. 
         Carrier 0 is represented by the most significant bit of the map, 
         carrier 63 is represented by the least significant bit of the map.
         An upstream carrier is suppressed by setting its corresponding bit to
         1.
         Pilot tones may not be suppressed. If one of the masked carrier is 
         defined as a pilot tone in the applicable DSL standard, the modem will
         not initialize.
         The masking of carriers that are not used in the upstream direction
         or that are not used by the XDSL operational mode will be ignored.
         Carriers 0 to 63 are used for all ADSL/ADSL2 operational modes.
         The carrier mask is not used in VDSL mode and will be ignored.
         The value 'all ones' indicates that the original SpectrumProfile 
         parameter will not be overruled.

         ALCATEL NOTE:
             ACCESS:   NA                  USAGE:    OPT
             PERSIST:  YES                 INSRVMOD: YES
             RANGE:    NA                  DEFVALUE: NA
             UNITS:    NA                  SPARSE:   NA
             DESCR:    NA "
        DEFVAL {'FFFFFFFFFFFFFFFF'H }
::= { xdslLineOverruleEntry 14}

xdslOverruleNoisePsdModeDownstream           OBJECT-TYPE
        SYNTAX          INTEGER {
                            noOverrule (1),
                            overruleVirtualNoise (2),
                            overruleArtificialNoise (3)
                        }
        ACCESS          read-write
        STATUS          mandatory
        DESCRIPTION 
        "This object is used to specify how the xdslOverruleNoisePsdModeDownstream
         parameter must be interpreted. Below values are possible:
            o noOverrule: Nor Virtual, nor artificial noise is overruled.
            o overruleVirtualNoise: The xdslOverruleNoisePsdModeDownstream
              will be used to overrule the virtual noise.
            o overruleArtificialNoise: The xdslOverruleNoisePsdModeDownstream
              will be used to overrule the artificial noise.
         Remark : - In case overruleVirtualNoise mode is selected and 
                  xdslOverruleNoisePsdDownstream is empty, the parameter 
                  vdsl2VirtualNoiseSnrmModeDownstream in the Spectrum profile 
                  must be overruled towards the proxy with snrmMode1
                  - In case overruleVirtualNoise mode is selected and 
                  xdslOverruleNoisePsdDownstream is not-empty, the parameter 
                  vdsl2VirtualNoiseSnrmModeDownstream in the Spectrum profile 
                  must be overruled towards the proxy with snrmMode2

         ALCATEL NOTE:
             ACCESS:   NA                  USAGE:    MAND
             PERSIST:  YES                 INSRVMOD: YES
             RANGE:    NA                  DEFVALUE: NA
             UNITS:    NA                  SPARSE:   NA
             DESCR:    NA "
        DEFVAL {1}
::= { xdslLineOverruleEntry 15}

xdslOverruleNoisePsdDownstream         OBJECT-TYPE
        SYNTAX          NoisePsdDownType
        ACCESS          read-write
        STATUS          mandatory
        DESCRIPTION     
        "This object defines the transmitter-referred noise level for the 
         given direction which will overrule the vdsl2VirtualNoisePsdDownstream
         or xdslLineArtificialNoisePsdDownstream of the xdslLineSpectrumProfile
         attached to this line.
         This object specifies the transmitter-referred noise level for
         determining the SNR margin in the corresponding downstream bands.
         A number of 2 to 32 Noise PSD points can be specified downstream.
         The successive PSD points must have increasing (>/=) frequencies.
         It is allowed that for two successive PSD points, different PSD
         levels are defined at a same frequency (brickwall).
         Noise PSD points are defined in the range -140dBm/Hz..-40 dBm/Hz.
         A special value (-167,5 dBm/Hz) states no virtual noise has to be
         Applied on this frequency.
         The Noise PSD Shape is coded as a variable length octet string 
         defined as follows:
           Octet 0: reserved 
           Octet 1..3: defines PSD point #1

           OCTETS 1..2: INTEGER (0..30000), frequency of PSD point #1,
             expressed in kHz. The value is defined as MSB-LSB (big-endian).
           OCTET 3: INTEGER (0..200,255), -2*(40 + PSD level) (in dBm/Hz) of
             PSD point#1.
           OCTETS 4..6: define the frequency and PSD level of PSD point #2.
             ....        up to
           OCTETS 3*N-2..3*N: define the frequency and PSD level of the last PSD
           point #N with N<=32.
         When this parameter is used then vdsl2virtualNoiseSnrmModeDownstream is set
         to snrmMode2 otherwise set to snrmMode1.
         An empty sequence means that no noise shall be used.

         ALCATEL NOTE:
             ACCESS:   NA                  USAGE:    OPT
             PERSIST:  YES                 INSRVMOD: YES
             RANGE:    0..97               DEFVALUE: NA
             UNITS:    octets              SPARSE:   NA
             DESCR:    NA "
        DEFVAL {''H }
::= { xdslLineOverruleEntry 16}

xdslOverruleNoisePsdModeUpstream           OBJECT-TYPE
        SYNTAX          INTEGER {
                            noOverrule (1),
                            overruleVirtualNoise (2),
                            overruleRxRefVirtualNoise (3)
                        }
        ACCESS          read-write
        STATUS          mandatory
        DESCRIPTION 
        "This object is used to specify how the xdslOverruleNoisePsdUpstream
         parameter must be interpreted. Below values are possible:
            o noOverrule: No overrule of the virtual noise configuration of the 
                          spectrum profile.
            o overruleVirtualNoise: The virtual noise configuration of the spectrum 
                          profile is overruled.
                  - In case xdslOverruleNoisePsdUpstream is empty, the parameter 
                    vdsl2VirtualNoiseSnrmModeUpstream in the Spectrum profile will
                    be overruled with snrmMode1
                  - In case xdslOverruleNoisePsdUpstream is not empty, the parameter
                    vdsl2VirtualNoiseSnrmModeUpstream in the Spectrum profile will 
                    be overruled with snrmMode2 and xdslOverruleNoisePsdUpstream 
                    will be used as transmitter referred noise PSD.
         o overruleRxRefVirtualNoise: The virtual noise configuration of the spectrum
                          profile is overruled.
                  - In case xdslOverruleNoisePsdUpstream is empty, the parameter   
                    vdsl2VirtualNoiseSnrmModeUpstream in the Spectrum profile will be 
                    overruled with snrmMode1
                  - In case xdslOverruleNoisePsdUpstream is not empty, the parameter  
                    vdsl2VirtualNoiseSnrmModeUpstream in the Spectrum profile will be  
                    overruled with snrmMode3 and xdslOverruleNoisePsdUpstream will be
                    used as receiver referred noise PSD.

         ALCATEL NOTE:
             ACCESS:   NA                  USAGE:    MAND
             PERSIST:  YES                 INSRVMOD: YES
             RANGE:    NA                  DEFVALUE: NA
             UNITS:    NA                  SPARSE:   NA
             DESCR:    NA "
        DEFVAL {1}
::= { xdslLineOverruleEntry 17}

xdslOverruleNoisePsdUpstream         OBJECT-TYPE
        SYNTAX          NoisePsdUpType
        ACCESS          read-write
        STATUS          mandatory
        DESCRIPTION     
        " This object defines the upstream transmitter or receiver referred 
          noise PSD, which will overrule vdsl2VirtualNoisePsdUpstream of the 
          xdslLineSpectrumProfile in case xdslOverruleNoisePsdModeUpstream is 
          set to overruleVirtualNoise or overruleRxRefVirtualNoise.
         A number of 2 to 16 Noise PSD points can be specified upstream
         The successive PSD points must have increasing (>/=) frequencies.
         It is allowed that for two successive PSD points, different PSD
         levels are defined at a same frequency (brickwall).
         Noise PSD points are defined in the range -140dBm/Hz..-40dBm/Hz.
         A special value (-167,5 dBm/Hz) states no noise has to be applied.
         The custom Noise PSD Shape is coded as a variable length octet string
         defined as follows:
           Octet 0: reserved 
           Octet 1..3: defines PSD point #1
             OCTETS 1..2: INTEGER (0..30000), frequency of PSD point #1,
             expressed in kHz. The value is defined as MSB-LSB (big-endian).
             OCTET 3: INTEGER (0..200,255), -2*(40 + PSD level) (in dBm/Hz) of
             PSD point#1.
             OCTETS 4..6: define the frequency and PSD level of PSD point #2.
             ....        up to
             OCTETS 3*N-2..3*N: define the frequency and PSD level of the last 
             PSD point #N with N<=16.
         An empty sequence means that no noise shall be used.

         ALCATEL NOTE:
             ACCESS:   NA                  USAGE:    OPT
             PERSIST:  YES                 INSRVMOD: YES
             RANGE:    0..49               DEFVALUE: NA
             UNITS:    NA                  SPARSE:   NA
             DESCR:    NA "
        DEFVAL {''H }
::= { xdslLineOverruleEntry 18}

xdslOverruleRtxModeDownstream OBJECT-TYPE
        SYNTAX      RtxMode 
        ACCESS      read-write
        STATUS      mandatory
        DESCRIPTION
        "This parameter allows the manager to enable the RTX feature in 
         downstream direction on lines supporting RTX which will overrule the 
         xdslRtxModeDownstream parameter in the RTX-profile.  As long as the 
         feature has not been enabled, the other RTX parameters will have 
         no effect on this line.

         ALCATEL NOTE:
             ACCESS:   NA                  USAGE:    NA
             PERSIST:  YES                 INSRVMOD: NA
             RANGE:    NA                  DEFVALUE: rtxNoOverrule
             UNITS:    NA                  SPARSE:   NA
             DESCR:    NA "
::= { xdslLineOverruleEntry 19}

xdslOverruleRtxModeUpstream OBJECT-TYPE
        SYNTAX      RtxMode
        ACCESS      read-write
        STATUS      mandatory
        DESCRIPTION
        "This parameter allows the manager to enable the RTX feature in 
         upstream direction on lines supporting RTX which will overrule the 
         xdslRtxModeUpstream parameter in the RTX-profile.  As long as the 
         feature has not been enabled, the other RTX parameters will have 
         no effect on this line.

         ALCATEL NOTE:
             ACCESS:   NA                  USAGE:    NA
             PERSIST:  YES                 INSRVMOD: NA
             RANGE:    NA                  DEFVALUE: rtxNoOverrule
             UNITS:    NA                  SPARSE:   NA
             DESCR:    NA "
::= { xdslLineOverruleEntry 20}

xdslOverruleRtxMaxNetDataRateDownstream OBJECT-TYPE
        SYNTAX      INTEGER 
        ACCESS      read-write
        STATUS      mandatory
        DESCRIPTION
        "This object defines the maximum net data rate for the downstream 
         direction, which will overrule the xdslRtxMaxNetDataRateDownstream of
         the RtxProfile when xdslOverruleRtxModeDownstream is different from
         rtxForbidden.
         Parameter value -1 indicates that the original RtxProfile parameter 
         will not be overruled.

         ALCATEL NOTE:
             ACCESS:   NA                  USAGE:    NA
             PERSIST:  YES                 INSRVMOD: NA
             RANGE:    -1,0..262143        DEFVALUE: -1
             UNITS:    kbits/sec           SPARSE:   NA
             DESCR:    NA "
::= { xdslLineOverruleEntry 21}

xdslOverruleRtxMaxNetDataRateUpstream OBJECT-TYPE
        SYNTAX      INTEGER 
        ACCESS      read-write
        STATUS      mandatory
        DESCRIPTION
        "This object defines the maximum net data rate for the upstream 
         direction, which will overrule the xdslRtxMaxNetDataRateUpstream of 
         the RtxProfile when xdslOverruleRtxModeUpstream is different from
         rtxForbidden.
         Parameter value -1 indicates that the original RtxProfile parameter 
         will not be overruled.

         ALCATEL NOTE:
             ACCESS:   NA                  USAGE:    NA
             PERSIST:  YES                 INSRVMOD: NA
             RANGE:    -1,0..262143        DEFVALUE: -1
             UNITS:    kbits/sec           SPARSE:   NA
             DESCR:    NA "
::= { xdslLineOverruleEntry 22}

xdslOverruleRtxMaxExpThrptDownstream OBJECT-TYPE
        SYNTAX      INTEGER 
        ACCESS      read-write
        STATUS      mandatory
        DESCRIPTION
        "This object defines the maximum expected throughput for the downstream 
         direction, which will overrule the xdslRtxMaxExpThrptDownstream of the 
         RtxProfile when xdslOverruleRtxModeDownstream is different from
         rtxForbidden.
         Parameter value -1 indicates that the original RtxProfile parameter 
         will not be overruled.

         ALCATEL NOTE:
             ACCESS:   NA                  USAGE:    NA
             PERSIST:  YES                 INSRVMOD: NA
             RANGE:    -1,0..262143        DEFVALUE: -1
             UNITS:    kbits/sec           SPARSE:   NA
             DESCR:    NA "
::= { xdslLineOverruleEntry 23}

xdslOverruleRtxMaxExpThrptUpstream OBJECT-TYPE
        SYNTAX      INTEGER 
        ACCESS      read-write
        STATUS      mandatory
        DESCRIPTION
        "This object defines the maximum expected throughput for the upstream 
         direction, which will overrule the xdslRtxMaxExpThrptUpstream of the 
         RtxProfile when xdslOverruleRtxModeUpstream is different from
         rtxForbidden.
         Parameter value -1 indicates that the original RtxProfile parameter 
         will not be overruled.

         ALCATEL NOTE:
             ACCESS:   NA                  USAGE:    NA
             PERSIST:  YES                 INSRVMOD: NA
             RANGE:    -1,0..262143        DEFVALUE: -1
             UNITS:    kbits/sec           SPARSE:   NA
             DESCR:    NA "
::= { xdslLineOverruleEntry 24}

xdslOverruleRtxMinInpShineDownstream OBJECT-TYPE
        SYNTAX      INTEGER 
        ACCESS      read-write
        STATUS      mandatory
        DESCRIPTION
        "This object defines the minimum impulse noise protection against 
         SHINE, for the downstream direction, which will overrule the 
         xdslRtxMinInpShineDownstream of the RtxProfile when 
         xdslOverruleRtxModeDownstream is different from rtxForbidden.
         It is expressed in DMT symbols with a subcarrier spacing of 4.3125kHz.
         Parameter value -1 indicates that the original RtxProfile parameter 
         will not be overruled.

         ALCATEL NOTE:
             ACCESS:   NA                  USAGE:    NA
             PERSIST:  YES                 INSRVMOD: NA
             RANGE:    -1,0..63            DEFVALUE: -1
             UNITS:    symbols             SPARSE:   NA
             DESCR:    NA "
::= { xdslLineOverruleEntry 25}

xdslOverruleRtxMinInpShineUpstream OBJECT-TYPE
        SYNTAX      INTEGER 
        ACCESS      read-write
        STATUS      mandatory
        DESCRIPTION
        "This object defines the minimum impulse noise protection against 
         SHINE, for the upstream direction, which will overrule the 
         xdslRtxMinInpShineUpstream of the RtxProfile when 
         xdslOverruleRtxModeUpstream is different from rtxForbidden.
         It is expressed in DMT symbols with a subcarrier spacing of 4.3125kHz.
         Parameter value -1 indicates that the original RtxProfile parameter 
         will not be overruled.

         ALCATEL NOTE:
             ACCESS:   NA                  USAGE:    NA
             PERSIST:  YES                 INSRVMOD: NA
             RANGE:    -1,0..63            DEFVALUE: -1
             UNITS:    symbols             SPARSE:   NA
             DESCR:    NA "
::= { xdslLineOverruleEntry 26}

xdslOverruleRtxMinInpReinDownstream OBJECT-TYPE
        SYNTAX      INTEGER 
        ACCESS      read-write
        STATUS      mandatory
        DESCRIPTION
        "This object defines the minimum impulse noise protection against 
         REIN, for the downstream direction, which will overrule the 
         xdslRtxMinInpReinDownstream of the RtxProfile when 
         xdslOverruleRtxModeDownstream is different from rtxForbidden.
         It is expressed in DMT symbols with a subcarrier spacing of 4.3125kHz.
         Parameter value -1 indicates that the original RtxProfile parameter 
         will not be overruled.

         ALCATEL NOTE:
             ACCESS:   NA                  USAGE:    NA
             PERSIST:  YES                 INSRVMOD: NA
             RANGE:    -1,0..7             DEFVALUE: -1
             UNITS:    symbols             SPARSE:   NA
             DESCR:    NA "
::= { xdslLineOverruleEntry 27}

xdslOverruleRtxMinInpReinUpstream OBJECT-TYPE
        SYNTAX      INTEGER 
        ACCESS      read-write
        STATUS      mandatory
        DESCRIPTION
        "This object defines the minimum impulse noise protection against 
         REIN, for the downstream direction, which will overrule the 
         xdslRtxMinInpReinUpstream of the RtxProfile when 
         xdslOverruleRtxModeUpstream is different from rtxForbidden.
         It is expressed in DMT symbols with a subcarrier spacing of 4.3125kHz.
         Parameter value -1 indicates that the original RtxProfile parameter 
         will not be overruled.

         ALCATEL NOTE:
             ACCESS:   NA                  USAGE:    NA
             PERSIST:  YES                 INSRVMOD: NA
             RANGE:    -1,0..7             DEFVALUE: -1
             UNITS:    symbols             SPARSE:   NA
             DESCR:    NA "
::= { xdslLineOverruleEntry 28}

xdslOverruleRtxMinDelayDownstream OBJECT-TYPE
        SYNTAX      INTEGER 
        ACCESS      read-write
        STATUS      mandatory
        DESCRIPTION
        "This object contains the minimum instantaneous delay allowed (only due 
         to the effect of the retransmission) for the downstream direction, 
         which will overrule the xdslRtxMinDelayDownstream of the RtxProfile 
         when xdslOverruleRtxModeDownstream is different from rtxForbidden.
         Parameter value -1 indicates that the original RtxProfile parameter 
         will not be overruled.

         ALCATEL NOTE:
             ACCESS:   NA                  USAGE:    NA
             PERSIST:  YES                 INSRVMOD: NA
             RANGE:    -1,0..63            DEFVALUE: -1
             UNITS:    milliseconds        SPARSE:   NA
             DESCR:    NA "
::= { xdslLineOverruleEntry 29}

xdslOverruleRtxMinDelayUpstream OBJECT-TYPE
        SYNTAX      INTEGER 
        ACCESS      read-write
        STATUS      mandatory
        DESCRIPTION
        "This object contains the minimum instantaneous delay allowed (only due 
         to the effect of the retransmission) for the upstream direction, which 
         will overrule the xdslRtxMinDelayUpstream of the RtxProfile when 
         xdslOverruleRtxModeUpstream is different from rtxForbidden. 
         Parameter value -1 indicates that the original RtxProfile parameter 
         will not be overruled.

         ALCATEL NOTE:
             ACCESS:   NA                  USAGE:    NA
             PERSIST:  YES                 INSRVMOD: NA
             RANGE:    -1,0..63            DEFVALUE: -1
             UNITS:    milliseconds        SPARSE:   NA
             DESCR:    NA "
::= { xdslLineOverruleEntry 30}

xdslOverruleRtxMaxDelayDownstream OBJECT-TYPE
        SYNTAX      INTEGER 
        ACCESS      read-write
        STATUS      mandatory
        DESCRIPTION
        "This object contains the maximum instantaneous delay allowed (only due 
         to the effect of the retransmission) for the downstream direction, which 
         will overrule the xdslRtxMaxDelayDownstream of the RtxProfile when 
         xdslOverruleRtxModeDownstream is different from rtxForbidden.
         Parameter value -1 indicates that the original RtxProfile parameter 
         will not be overruled.

         ALCATEL NOTE:
             ACCESS:   NA                  USAGE:    NA
             PERSIST:  YES                 INSRVMOD: NA
             RANGE:    -1,2..63            DEFVALUE: -1
             UNITS:    milliseconds        SPARSE:   NA
             DESCR:    NA "
::= { xdslLineOverruleEntry 31}

xdslOverruleRtxMaxDelayUpstream OBJECT-TYPE
        SYNTAX      INTEGER 
        ACCESS      read-write
        STATUS      mandatory
        DESCRIPTION
        "This object contains the maximum instantaneous delay allowed (only due 
         to the effect of the retransmission) for the upstream direction, which 
         will overrule the xdslRtxMaxDelayUpstream of the RtxProfile when 
         xdslOverruleRtxModeUpstream is different from rtxForbidden.
         Parameter value -1 indicates that the original RtxProfile parameter 
         will not be overruled.

         ALCATEL NOTE:
             ACCESS:   NA                  USAGE:    NA
             PERSIST:  YES                 INSRVMOD: NA
             RANGE:    -1,2..63            DEFVALUE: -1
             UNITS:    milliseconds        SPARSE:   NA
             DESCR:    NA "
::= { xdslLineOverruleEntry 32}

xdslOverruleRtxShineRatioDownstream OBJECT-TYPE
        SYNTAX      INTEGER 
        ACCESS      read-write
        STATUS      mandatory
        DESCRIPTION
        " This object specifies the SHINE ratio for the downstream direction,
         which will overrule the xdslRtxShineRatioDownstream of the RtxProfile 
         when xdslOverruleRtxModeDownstream is different from rtxForbidden.
         The value ranges from 0 to 0.100 with increments of 0.001.
         Parameter value -1 indicates that the original RtxProfile parameter 
         will not be overruled.

         ALCATEL NOTE:
             ACCESS:   NA                  USAGE:    NA
             PERSIST:  YES                 INSRVMOD: NA
             RANGE:    -1,0..100           DEFVALUE: -1
             UNITS:    1/1000              SPARSE:   NA
             DESCR:    NA "
::= { xdslLineOverruleEntry 33}

xdslOverruleRtxShineRatioUpstream OBJECT-TYPE
        SYNTAX      INTEGER 
        ACCESS      read-write
        STATUS      mandatory
        DESCRIPTION
        "This object specifies the SHINE ratio for the upstream direction,
         which will overrule the xdslRtxShineRatioUpstream of the RtxProfile 
         when xdslOverruleRtxModeUpstream is different from rtxForbidden.
         The value ranges from 0 to 0.100 with increments of 0.001.
         Parameter value -1 indicates that the original RtxProfile parameter 
         will not be overruled.

         ALCATEL NOTE:
             ACCESS:   NA                  USAGE:    NA
             PERSIST:  YES                 INSRVMOD: NA
             RANGE:    -1,0..100           DEFVALUE: -1
             UNITS:    1/1000              SPARSE:   NA
             DESCR:    NA "
::= { xdslLineOverruleEntry 34}

xdslOverruleRtxLeftrThresholdDownstream        OBJECT-TYPE
        SYNTAX          INTEGER
        ACCESS          read-write
        STATUS          mandatory
        DESCRIPTION     
        "This object specifies the threshold for declaring a near-end 'leftr' 
         defect in the downstream direction, which will overrule the 
         xdslRtxLeftrThresholdDownstream of the RtxProfile when 
         xdslOverruleRtxModeDownstream is different from rtxForbidden.
         The value ranges from 0.01 to 0.99 with increments of 0.01.     
         The special value 0 means the ETR shall be used as the default threshold
          for declaring a 'leftr' defect.
         Parameter value -1 indicates that the original RtxProfile parameter 
          will not be overruled.

         ALCATEL NOTE:
             ACCESS:   NA                  USAGE:    OPT
             PERSIST:  YES                 INSRVMOD: NO
             RANGE:    -1,0,1..99          DEFVALUE: -1
             UNITS:    1/100               SPARSE:   NA
             DESCR:    NA "
::= { xdslLineOverruleEntry 35}

xdslOverruleRtxLeftrThresholdUpstream        OBJECT-TYPE
        SYNTAX          INTEGER
        ACCESS          read-write
        STATUS          mandatory
        DESCRIPTION     
        "This object specifies the threshold for declaring a far-end 'leftr' 
         defect in the upstream direction, which will overrule the 
         xdslRtxLeftrThresholdUpstream of the RtxProfile when 
         xdslOverruleRtxModeUpstream is different from rtxForbidden.
         The value ranges from 0.01 to 0.99 with increments of 0.01. 
         The special value 0 means the ETR shall be used as the default threshold
          for declaring a 'leftr' defect.    
         Parameter value -1 indicates that the original RtxProfile parameter 
          will not be overruled.

         ALCATEL NOTE:
             ACCESS:   NA                  USAGE:    OPT
             PERSIST:  YES                 INSRVMOD: NO
             RANGE:    -1,0,1..99          DEFVALUE: -1
             UNITS:    1/100               SPARSE:   NA
             DESCR:    NA "
::= { xdslLineOverruleEntry 36}

xdslErrorDefinitionTable         OBJECT-TYPE
        SYNTAX          SEQUENCE OF XdslErrorDefinitionEntry
        ACCESS          not-accessible
        STATUS          mandatory
        DESCRIPTION
        "The Xdsl Error Definition Table contains mapping between activation
         failure error codes and their textual description.

         ALCATEL NOTE:
             TABLESIZE: DEP [number of XDSL errors]
             DESCR:     NA                   "
::= { xdslError 1 }

xdslErrorDefinitionEntry         OBJECT-TYPE
        SYNTAX          XdslErrorDefinitionEntry
        ACCESS          not-accessible
        STATUS          mandatory
        DESCRIPTION
        "An entry in the xdsl error definition table. "
        INDEX          { xdslErrorCode }
::= { xdslErrorDefinitionTable  1 }

XdslErrorDefinitionEntry ::=
        SEQUENCE {
            xdslErrorCode                          INTEGER,
            xdslErrorCodeDescription               DisplayString
        }

xdslErrorCode               OBJECT-TYPE
        SYNTAX          INTEGER
        ACCESS          read-only
        STATUS          mandatory
        DESCRIPTION 
        "This object contains the error code number.

         ALCATEL NOTE:
             ACCESS:   NA                  USAGE:    OPT
             PERSIST:  YES                 INSRVMOD: NA
             RANGE:    NA                  DEFVALUE: NA
             UNITS:    NA                  SPARSE:   NA
             DESCR:    NA "
::= {xdslErrorDefinitionEntry 1}

xdslErrorCodeDescription           OBJECT-TYPE
        SYNTAX          DisplayString
        ACCESS          read-only
        STATUS          mandatory
        DESCRIPTION 
        "This object contains the textual description of the error code.

         ALCATEL NOTE:
             ACCESS:   NA                  USAGE:    OPT
             PERSIST:  YES                 INSRVMOD: NA
             RANGE:    NA                  DEFVALUE: NA
             UNITS:    NA                  SPARSE:   NA
             DESCR:    NA "
::= {xdslErrorDefinitionEntry 2}

xdslRtxProfileIndexNext       OBJECT-TYPE
        SYNTAX          AsamNextProfileIndex
        ACCESS          read-only
        STATUS          mandatory
        DESCRIPTION     
        "This object contains an appropriate value to be used for 
         xdslRtxProfileIndex when creating entries in the xdslRtxProfileTable. 
         The value 0 indicates that no unassigned entries are available. To 
         obtain the xdslRtxProfileIndex value for a new entry, the
         manager issues a management protocol retrieval operation to obtain the
         current value of this object.  After each retrieval, the agent should
         modify the value to the next unassigned index.

         ALCATEL NOTE:
             ACCESS:   NA                  USAGE:    NA
             PERSIST:  NO                  INSRVMOD: NA
             RANGE:    0..128              DEFVALUE: 1
             UNITS:    NA                  SPARSE:   NA
             DESCR:    NA "
::= {xdslRtxProfile 1}

xdslRtxProfileMaxIndex        OBJECT-TYPE
        SYNTAX          AsamMaxProfileIndex
        ACCESS          read-only
        STATUS          mandatory
        DESCRIPTION
        "This object represents the maximum number of xdslRtxProfiles
         that can be created. The object xdslRtxProfileIndexNext will 
         have values ranging from 0 to the value represented by this object.

         ALCATEL NOTE:
             ACCESS:   NA                  USAGE:    NA
             PERSIST:  NO                  INSRVMOD: NA
             RANGE:    128..128            DEFVALUE: 128
             UNITS:    NA                  SPARSE:   NA
             DESCR:    NA "
::= {xdslRtxProfile 2}

xdslRtxProfileTable           OBJECT-TYPE
        SYNTAX          SEQUENCE OF XdslRtxProfileEntry
        ACCESS          not-accessible
        STATUS          mandatory
        DESCRIPTION     
        "This table contains the RTX related parameters of the modem
         configuration. One entry in this table reflects a profile which
         can be used to configure the modem for a physical line.

         ALCATEL NOTE:
             TABLESIZE: 128                   
             DESCR:     NA                   "
::= {xdslRtxProfile 3}

xdslRtxProfileEntry           OBJECT-TYPE
        SYNTAX          XdslRtxProfileEntry
        ACCESS          not-accessible
        STATUS          mandatory
        DESCRIPTION     
        "Each entry consists of a list of line related parameters that serve 
         to configure RTX. A profile can be created in one step with
         all necessary parameter values and xdslRtxProfileRowStatus
         set to createAndGo.
         It can also be created in several steps by specifying values of a few
         objects in each step. The xdslRtxProfileRowStatus is set to
         createAndWait in the first step and to Active in the last step.

         Row creation : An entry is created when the manager requests to create
                        a Rtx profile.
         Row deletion : An entry is deleted when the manager requests to delete
                        a Rtx profile. "
        INDEX          {xdslRtxProfileIndex}
::= {xdslRtxProfileTable 1}

XdslRtxProfileEntry ::=
        SEQUENCE {
            xdslRtxProfileIndex                AsamProfileIndex,
            xdslRtxProfileName                 AsamProfileName,
            xdslRtxProfileVersionNbr           INTEGER,
            xdslRtxProfileUsedStatus           AsamProfileRefCount,
            xdslRtxModeDownstream              RtxMode,
            xdslRtxModeUpstream                RtxMode,
            xdslRtxMinExpThrptDownstream       INTEGER,
            xdslRtxMinExpThrptUpstream         INTEGER,
            xdslRtxPlanExpThrptDownstream      INTEGER,
            xdslRtxPlanExpThrptUpstream        INTEGER,
            xdslRtxMaxExpThrptDownstream       INTEGER,
            xdslRtxMaxExpThrptUpstream         INTEGER,
            xdslRtxMaxNetDataRateDownstream    INTEGER,
            xdslRtxMaxNetDataRateUpstream      INTEGER,
            xdslRtxMinDelayDownstream          INTEGER,
            xdslRtxMinDelayUpstream            INTEGER,
            xdslRtxMaxDelayDownstream          INTEGER,
            xdslRtxMaxDelayUpstream            INTEGER,
            xdslRtxMinInpShineDownstream       INTEGER,
            xdslRtxMinInpShineUpstream         INTEGER,
            xdslRtxMinInpReinDownstream        INTEGER,
            xdslRtxMinInpReinUpstream          INTEGER,
            xdslRtxReinInterArrTimeDownstream  INTEGER,
            xdslRtxReinInterArrTimeUpstream    INTEGER,
            xdslRtxShineRatioDownstream        INTEGER,
            xdslRtxShineRatioUpstream          INTEGER,
            xdslRtxLeftrThresholdDownstream    INTEGER,
            xdslRtxLeftrThresholdUpstream      INTEGER,
            xdslRtxProfileRowStatus            RowStatus,
            xdslRtxProfileModifyStatus         INTEGER
        }

xdslRtxProfileIndex           OBJECT-TYPE
        SYNTAX          AsamProfileIndex
        ACCESS          not-accessible
        STATUS          mandatory
        DESCRIPTION     
        "This object is used to uniquely identify an entry in this table.
         It is used by the line configuration table to identify a row of 
         the table. The max value of this object is limited to 
         xdslRtxProfileMaxIndex value.
         In addition, special index values are defined to identify temporary
         entries in this table used to contain the modifications performed on
         an existing profile. The index value of such an entry is obtained by
         adding a fixed offset to the corresponding index. The value of this
         offset is contained in xdslRtxProfileIndexOffset. A temporary
         entry exists only during the profile modification, it is created at
         xdslRtxProfileModifyStatus = modifyStart and is deleted at
         modifyCancel or modifyComplete. It can only be accessed during the
         modification to retrieve the updated parameters values of a profile.
         The nominal entry contains the original profile settings and is not
         updated until the profile modification is completed and validated.
         The offset entries are read only, all write operations must be
         performed using the nominal index.
         The getnext can be used to retrieve the nominal Rtx profile
         entries and does not return the temporary profiles entries at the
         special offset index values.

         ALCATEL NOTE:
             ACCESS:   NA                  USAGE:    NA
             PERSIST:  YES                 INSRVMOD: NA
             RANGE:    1..128               DEFVALUE: NA
             UNITS:    NA                  SPARSE:   NA
             DESCR:    NA "
::= {xdslRtxProfileEntry 1}

xdslRtxProfileName            OBJECT-TYPE
        SYNTAX          AsamProfileName
        ACCESS          read-write
        STATUS          mandatory
        DESCRIPTION     
        "A textual name identifying this profile. This name has to be unique.

         ALCATEL NOTE:
             ACCESS:   NA                  USAGE:    MAND
             PERSIST:  YES                 INSRVMOD: YES
             RANGE:    NA                  DEFVALUE: NA
             UNITS:    NA                  SPARSE:   NA
             DESCR:    NA "
::= {xdslRtxProfileEntry 2}

xdslRtxProfileVersionNbr      OBJECT-TYPE
        SYNTAX          INTEGER
        ACCESS          read-write
        STATUS          mandatory
        DESCRIPTION     
        "The manager can associate a version number to the profile. It is set
         to 1 when the profile is first created and will be incremented by the
         manager when the profile is modified.

         ALCATEL NOTE:
             ACCESS:   NA                  USAGE:    OPT
             PERSIST:  YES                 INSRVMOD: YES
             RANGE:    NA                  DEFVALUE: NA
             UNITS:    NA                  SPARSE:   NA
             DESCR:    NA "
        DEFVAL          {1}
::= {xdslRtxProfileEntry 3}

xdslRtxProfileUsedStatus      OBJECT-TYPE
        SYNTAX          AsamProfileRefCount
        ACCESS          read-only
        STATUS          mandatory
        DESCRIPTION
        "Indicates the number of entities using this profile. If the reference
         count is greater than 0, then this profile is 'in use', and may NOT be
         deleted. If the value is 0, then this profile is 'not in use', and can
         be deleted.

         ALCATEL NOTE:
             ACCESS:   NA                  USAGE:    NA
             PERSIST:  NO                  INSRVMOD: NA
             RANGE:    NA                  DEFVALUE: 0
             UNITS:    NA                  SPARSE:   NA
             DESCR:    NA "
::= {xdslRtxProfileEntry 4}

xdslRtxModeDownstream OBJECT-TYPE
        SYNTAX      RtxMode
        ACCESS      read-write
        STATUS      mandatory
        DESCRIPTION
        "This parameter allows the manager to enable the RTX feature in 
         downstream direction on lines supporting RTX.  As long as the 
         feature has not been enabled, the other RTX parameters will have 
         no effect on this line.

         ALCATEL NOTE:
             ACCESS:   NA                  USAGE:    NA
             PERSIST:  YES                 INSRVMOD: NA
             RANGE:    1,2,3,4             DEFVALUE: rtxPreferred
             UNITS:    NA                  SPARSE:   NA
             DESCR:    NA "
::= { xdslRtxProfileEntry 5}

xdslRtxModeUpstream OBJECT-TYPE
        SYNTAX      RtxMode 
        ACCESS      read-write
        STATUS      mandatory
        DESCRIPTION
        "This parameter allows the manager to enable the retransmission feature 
         in upstream direction on lines (only VDSL2) supporting RTX.  As long 
         as the feature has not been enabled, the other RTX parameters will 
         have no effect on this line.

         ALCATEL NOTE:
             ACCESS:   NA                  USAGE:    NA
             PERSIST:  YES                 INSRVMOD: NA
             RANGE:    1,2,3,4             DEFVALUE: rtxPreferred
             UNITS:    NA                  SPARSE:   NA
             DESCR:    NA "
::= { xdslRtxProfileEntry 6}

xdslRtxMinExpThrptDownstream OBJECT-TYPE
        SYNTAX      INTEGER 
        ACCESS      read-write
        STATUS      mandatory
        DESCRIPTION
        "This object contains the minimum expected throughput (bitrate)
         for the downstream direction when xdslRtxModeDownstream is different
         from rtxForbidden.

         ALCATEL NOTE:
             ACCESS:   NA                  USAGE:    NA
             PERSIST:  YES                 INSRVMOD: NA
             RANGE:    0..262143           DEFVALUE: 64
             UNITS:    kbits/sec           SPARSE:   NA
             DESCR:    NA "
::= { xdslRtxProfileEntry 7}

xdslRtxMinExpThrptUpstream OBJECT-TYPE
        SYNTAX      INTEGER 
        ACCESS      read-write
        STATUS      mandatory
        DESCRIPTION
        "This object contains the minimum expected throughput (bitrate)
         for the upstream direction when xdslRtxModeUpstream is different
         from rtxForbidden.

         ALCATEL NOTE:
             ACCESS:   NA                  USAGE:    NA
             PERSIST:  YES                 INSRVMOD: NA
             RANGE:    0..262143           DEFVALUE: 64
             UNITS:    kbits/sec           SPARSE:   NA
             DESCR:    NA "
::= { xdslRtxProfileEntry 8}

xdslRtxPlanExpThrptDownstream OBJECT-TYPE
        SYNTAX      INTEGER 
        ACCESS      read-write
        STATUS      mandatory
        DESCRIPTION
        " This object contains the planned expected throughput (bitrate)
         for the downstream direction when xdslRtxModeDownstream is different
         from rtxForbidden.

         ALCATEL NOTE:
             ACCESS:   NA                  USAGE:    NA
             PERSIST:  YES                 INSRVMOD: NA
             RANGE:    0..262143           DEFVALUE: 128
             UNITS:    kbits/sec           SPARSE:   NA
             DESCR:    NA "
::= { xdslRtxProfileEntry 9}

xdslRtxPlanExpThrptUpstream OBJECT-TYPE
        SYNTAX      INTEGER 
        ACCESS      read-write
        STATUS      mandatory
        DESCRIPTION
        " This object contains the planned expected throughput (bitrate)
         for the upstream direction when xdslRtxModeUpstream is different
         from rtxForbidden.

         ALCATEL NOTE:
             ACCESS:   NA                  USAGE:    NA
             PERSIST:  YES                 INSRVMOD: NA
             RANGE:    0..262143           DEFVALUE: 128
             UNITS:    kbits/sec           SPARSE:   NA
             DESCR:    NA "
::= { xdslRtxProfileEntry 10}

xdslRtxMaxExpThrptDownstream OBJECT-TYPE
        SYNTAX      INTEGER 
        ACCESS      read-write
        STATUS      mandatory
        DESCRIPTION
        " This object contains the maximum expected throughput (bitrate)
         for the downstream direction when xdslRtxModeDownstream is different
         from rtxForbidden.

         ALCATEL NOTE:
             ACCESS:   NA                  USAGE:    NA
             PERSIST:  YES                 INSRVMOD: NA
             RANGE:    0..262143           DEFVALUE: 262143
             UNITS:    kbits/sec           SPARSE:   NA
             DESCR:    NA "
::= { xdslRtxProfileEntry 11}

xdslRtxMaxExpThrptUpstream OBJECT-TYPE
        SYNTAX      INTEGER 
        ACCESS      read-write
        STATUS      mandatory
        DESCRIPTION
        " This object contains the maximum expected throughput (bitrate)
         for the upstream direction when xdslRtxModeUpstream is different
         from rtxForbidden.

         ALCATEL NOTE:
             ACCESS:   NA                  USAGE:    NA
             PERSIST:  YES                 INSRVMOD: NA
             RANGE:    0..262143           DEFVALUE: 262143
             UNITS:    kbits/sec           SPARSE:   NA
             DESCR:    NA "
::= { xdslRtxProfileEntry 12}

xdslRtxMaxNetDataRateDownstream OBJECT-TYPE
        SYNTAX      INTEGER 
        ACCESS      read-write
        STATUS      mandatory
        DESCRIPTION
        "This object contains the maximum net data rate for the downstream 
         direction when xdslRtxModeDownstream is different from rtxForbidden.

         ALCATEL NOTE:
             ACCESS:   NA                  USAGE:    NA
             PERSIST:  YES                 INSRVMOD: NA
             RANGE:    0..262143           DEFVALUE: 262143
             UNITS:    kbits/sec           SPARSE:   NA
             DESCR:    NA "
::= { xdslRtxProfileEntry 13}

xdslRtxMaxNetDataRateUpstream OBJECT-TYPE
        SYNTAX      INTEGER 
        ACCESS      read-write
        STATUS      mandatory
        DESCRIPTION
        "This object contains the maximum net data rate for the upstream 
         direction when xdslRtxModeUpstream is different from rtxForbidden.

         ALCATEL NOTE:
             ACCESS:   NA                  USAGE:    NA
             PERSIST:  YES                 INSRVMOD: NA
             RANGE:    0..262143           DEFVALUE: 262143
             UNITS:    kbits/sec           SPARSE:   NA
             DESCR:    NA "
::= { xdslRtxProfileEntry 14}

xdslRtxMinDelayDownstream OBJECT-TYPE
        SYNTAX      INTEGER 
        ACCESS      read-write
        STATUS      mandatory
        DESCRIPTION
        "This object contains the minimum instantaneous delay allowed (only due 
         to the effect of the retransmission) for the downstream direction when 
         xdslRtxModeDownstream is different from rtxForbidden.

         ALCATEL NOTE:
             ACCESS:   NA                  USAGE:    NA
             PERSIST:  YES                 INSRVMOD: NA
             RANGE:    0..63               DEFVALUE: 0
             UNITS:    milliseconds        SPARSE:   NA
             DESCR:    NA "
::= { xdslRtxProfileEntry 15}

xdslRtxMinDelayUpstream OBJECT-TYPE
        SYNTAX      INTEGER 
        ACCESS      read-write
        STATUS      mandatory
        DESCRIPTION
        "This object contains the minimum instantaneous delay allowed (only due 
         to the effect of the retransmission) for the upstream direction when 
         xdslRtxModeUpstream is different from rtxForbidden. 

         ALCATEL NOTE:
             ACCESS:   NA                  USAGE:    NA
             PERSIST:  YES                 INSRVMOD: NA
             RANGE:    0..63               DEFVALUE: 0
             UNITS:    milliseconds        SPARSE:   NA
             DESCR:    NA "
::= { xdslRtxProfileEntry 16}

xdslRtxMaxDelayDownstream OBJECT-TYPE
        SYNTAX      INTEGER 
        ACCESS      read-write
        STATUS      mandatory
        DESCRIPTION
        "This object contains the maximum instantaneous delay allowed (only due 
         to the effect of the retransmission) for the downstream direction when 
         xdslRtxModeDownstream is different from rtxForbidden. 
         When RTX is used in this direction it invalidates the 
         xdslMaxInterleavingDelayDownstream parameter of the Service profile.

         ALCATEL NOTE:
             ACCESS:   NA                  USAGE:    NA
             PERSIST:  YES                 INSRVMOD: NA
             RANGE:    2..63               DEFVALUE: 12
             UNITS:    milliseconds        SPARSE:   NA
             DESCR:    NA "
::= { xdslRtxProfileEntry 17}

xdslRtxMaxDelayUpstream OBJECT-TYPE
        SYNTAX      INTEGER 
        ACCESS      read-write
        STATUS      mandatory
        DESCRIPTION
        "This object contains the maximum instantaneous delay allowed (only due 
         to the effect of the retransmission) for the upstream direction when 
         xdslRtxModeUpstream is different from rtxForbidden. 
         When RTX is used in this direction it invalidates the 
         xdslMaxInterleavingDelayUpstream parameter of the Service profile.

         ALCATEL NOTE:
             ACCESS:   NA                  USAGE:    NA
             PERSIST:  YES                 INSRVMOD: NA
             RANGE:    2..63               DEFVALUE: 12
             UNITS:    milliseconds        SPARSE:   NA
             DESCR:    NA "
::= { xdslRtxProfileEntry 18}

xdslRtxMinInpShineDownstream OBJECT-TYPE
        SYNTAX      INTEGER 
        ACCESS      read-write
        STATUS      mandatory
        DESCRIPTION
        "This object defines the minimum impulse noise protection against 
         SHINE, for the downstream direction when xdslRtxModeDownstream is 
         different from rtxForbidden.
         It is expressed in DMT symbols with a subcarrier spacing of 4.3125kHz.

         ALCATEL NOTE:
             ACCESS:   NA                  USAGE:    NA
             PERSIST:  YES                 INSRVMOD: NA
             RANGE:    0..63               DEFVALUE: 8
             UNITS:    symbols             SPARSE:   NA
             DESCR:    NA "
::= { xdslRtxProfileEntry 19}

xdslRtxMinInpShineUpstream OBJECT-TYPE
        SYNTAX      INTEGER 
        ACCESS      read-write
        STATUS      mandatory
        DESCRIPTION
        "This object defines the minimum impulse noise protection against 
         SHINE, for the upstream direction when xdslRtxModeUpstream is 
         different from rtxForbidden.
         It is expressed in DMT symbols with a subcarrier spacing of 4.3125kHz.

         ALCATEL NOTE:
             ACCESS:   NA                  USAGE:    NA
             PERSIST:  YES                 INSRVMOD: NA
             RANGE:    0..63               DEFVALUE: 8
             UNITS:    symbols             SPARSE:   NA
             DESCR:    NA "
::= { xdslRtxProfileEntry 20}

xdslRtxMinInpReinDownstream OBJECT-TYPE
        SYNTAX      INTEGER 
        ACCESS      read-write
        STATUS      mandatory
        DESCRIPTION
        "This object defines the minimum impulse noise protection against REIN,
         for the downstream direction when xdslRtxModeDownstream is different
         from rtxForbidden.
         It is expressed in DMT symbols with a subcarrier spacing of 4.3125kHz.

         ALCATEL NOTE:
             ACCESS:   NA                  USAGE:    NA
             PERSIST:  YES                 INSRVMOD: NA
             RANGE:    0..7                DEFVALUE: 0
             UNITS:    symbols             SPARSE:   NA
             DESCR:    NA "
::= { xdslRtxProfileEntry 21}

xdslRtxMinInpReinUpstream OBJECT-TYPE
        SYNTAX      INTEGER 
        ACCESS      read-write
        STATUS      mandatory
        DESCRIPTION
        "This object defines the minimum impulse noise protection against REIN,
         for the upstream direction when xdslRtxModeUpstream is different
         from rtxForbidden.
         It is expressed in DMT symbols with a subcarrier spacing of 4.3125kHz.

         ALCATEL NOTE:
             ACCESS:   NA                  USAGE:    NA
             PERSIST:  YES                 INSRVMOD: NA
             RANGE:    0..7                DEFVALUE: 0
             UNITS:    symbols             SPARSE:   NA
             DESCR:    NA "
::= { xdslRtxProfileEntry 22}

xdslRtxReinInterArrTimeDownstream OBJECT-TYPE
        SYNTAX      INTEGER 
                    {
                      derivedFrom100Hz (1),
                      derivedFrom120Hz (2)
                    }
        ACCESS      read-write
        STATUS      mandatory
        DESCRIPTION
        "This object specifies the inter-arrival time that shall be assumed for 
         REIN protection for the downstream direction when xdslRtxModeDownstream 
         is different from rtxForbidden.

         ALCATEL NOTE:
             ACCESS:   NA                  USAGE:    NA
             PERSIST:  YES                 INSRVMOD: NA
             RANGE:    1,2                 DEFVALUE: 1
             UNITS:    NA                  SPARSE:   NA
             DESCR:    NA "
::= { xdslRtxProfileEntry 23}

xdslRtxReinInterArrTimeUpstream OBJECT-TYPE
        SYNTAX      INTEGER 
                    {
                      derivedFrom100Hz (1),
                      derivedFrom120Hz (2)
                    }
        ACCESS      read-write
        STATUS      mandatory
        DESCRIPTION
        "This object specifies the inter-arrival time that shall be assumed for 
         REIN protection for the upstream direction when xdslRtxModeUpstream is 
         different from rtxForbidden.

         ALCATEL NOTE:
             ACCESS:   NA                  USAGE:    NA
             PERSIST:  YES                 INSRVMOD: NA
             RANGE:    1,2                 DEFVALUE: 1
             UNITS:    NA                  SPARSE:   NA
             DESCR:    NA "
::= { xdslRtxProfileEntry 24}

xdslRtxShineRatioDownstream OBJECT-TYPE
        SYNTAX      INTEGER 
        ACCESS      read-write
        STATUS      mandatory
        DESCRIPTION
        " This object specifies the SHINE ratio for the downstream direction 
         when xdslRtxModeDownstream is different from rtxForbidden.
         The value ranges from 0 to 0.100 with increments of 0.001.

         ALCATEL NOTE:
             ACCESS:   NA                  USAGE:    NA
             PERSIST:  YES                 INSRVMOD: NA
             RANGE:    0..100              DEFVALUE: 10
             UNITS:    1/1000              SPARSE:   NA
             DESCR:    NA "
::= { xdslRtxProfileEntry 25}

xdslRtxShineRatioUpstream OBJECT-TYPE
        SYNTAX      INTEGER 
        ACCESS      read-write
        STATUS      mandatory
        DESCRIPTION
        " This object specifies the SHINE ratio for the upstream direction 
         when xdslRtxModeUpstream is different from rtxForbidden.
         The value ranges from 0 to 0.100 with increments of 0.001.

         ALCATEL NOTE:
             ACCESS:   NA                  USAGE:    NA
             PERSIST:  YES                 INSRVMOD: NA
             RANGE:    0..100              DEFVALUE: 10
             UNITS:    1/1000              SPARSE:   NA
             DESCR:    NA "
::= { xdslRtxProfileEntry 26}

xdslRtxLeftrThresholdDownstream        OBJECT-TYPE
        SYNTAX          INTEGER
        ACCESS          read-write
        STATUS          mandatory
        DESCRIPTION     
        "This parameter specifies the threshold for declaring a near-end 'leftr'
         defect in the downstream direction when xdslRtxModeDownstream is 
         different from rtxForbidden.  
         The value ranges from 0.01 to 0.99 with increments of 0.01.  
         The special value 0 means the ETR shall be used as the default threshold
         for declaring a 'leftr' defect.    

         ALCATEL NOTE:
             ACCESS:   NA                  USAGE:    OPT
             PERSIST:  YES                 INSRVMOD: NO
             RANGE:    0,1..99             DEFVALUE: 0
             UNITS:    1/100               SPARSE:   NA
             DESCR:    NA "
::= { xdslRtxProfileEntry 27}

xdslRtxLeftrThresholdUpstream        OBJECT-TYPE
        SYNTAX          INTEGER
        ACCESS          read-write
        STATUS          mandatory
        DESCRIPTION     
        "This parameter specifies the threshold for declaring a near-end 'leftr' 
         defect in the upstream direction when xdslRtxModeUpstream is different
         from rtxForbidden.  
         The value ranges from 0.01 to 0.99 with increments of 0.01.     
         The special value 0 means the ETR shall be used as the default threshold
         for declaring a 'leftr' defect.    

         ALCATEL NOTE:
             ACCESS:   NA                  USAGE:    OPT
             PERSIST:  YES                 INSRVMOD: NO
             RANGE:    0,1..99             DEFVALUE: 0
             UNITS:    1/100               SPARSE:   NA
             DESCR:    NA "
::= { xdslRtxProfileEntry 28}

xdslRtxProfileRowStatus       OBJECT-TYPE
        SYNTAX          RowStatus
        ACCESS          read-write
        STATUS          mandatory
        DESCRIPTION 
        "This object is used to create a new row or delete an existing row in
         this table. The usage is as per standard semantics of 'RowStatus'
         defined in SNMPv2-TC.
            o Both 'createAndGo' and 'createAndWait' options of row creation
              are supported.
            o The entry associated with a Profile that is being used may
              not be deleted.

         ALCATEL NOTE:
             ACCESS:   NA                  USAGE:    MAND
             PERSIST:  YES                 INSRVMOD: YES
             RANGE:    NA                  DEFVALUE: NA
             UNITS:    NA                  SPARSE:   NA
             DESCR:    NA "
::= { xdslRtxProfileEntry 29}

xdslRtxProfileModifyStatus OBJECT-TYPE
        SYNTAX          INTEGER {
                            modifyStart (1),
                            modifyCancel (2),
                            modifyComplete (3)
                        }
        ACCESS          read-write
        STATUS          mandatory 
        DESCRIPTION 
        "This variable is used to modify a Rtx profile after
         it has been created.
         The following values are defined:
          - modifyStart (1): set by the manager to enable the
            modification of the parameters of the Rtx profile.
          - modifyCancel (2): set by the manager to stop the profile
            modification and cancel all changes. The original profile
            settings are maintained.
          - modifyComplete (3): used by the manager to activate the
            changes and replace the old profile. The modification of the
            Rtx profile parameters (other than name, version) is disabled.
            The system will also set the xdslRtxProfileModifyStatus 
            value to 'modifyComplete'after a modifyCancel request from 
            the manager.
           See xdslRtxProfileIndex about the retrieval of the original 
           or the updated profile setting values during the profile
           modification.

         ALCATEL NOTE:
             ACCESS:   NA                  USAGE:    OPT
             PERSIST:  YES                 INSRVMOD: YES
             RANGE:    NA                  DEFVALUE: NA
             UNITS:    NA                  SPARSE:   NA
             DESCR:    NA "
        DEFVAL          {modifyComplete}
 ::= {xdslRtxProfileEntry 30}

xdslRtxProfileMappingTable    OBJECT-TYPE
        SYNTAX          SEQUENCE OF XdslRtxProfileMappingEntry
        ACCESS          not-accessible
        STATUS          mandatory
        DESCRIPTION
        "The (conceptual) listing the profile name to profile Index
         Mapping.

         ALCATEL NOTE:
             TABLESIZE: 128                    
             DESCR:     NA                           "
::= {xdslRtxProfile 4}

xdslRtxProfileMappingEntry    OBJECT-TYPE
      SYNTAX            XdslRtxProfileMappingEntry
      ACCESS            not-accessible
      STATUS            mandatory
      DESCRIPTION
        "An entry (conceptual row) representing the profile Name to Index
         Mapping.

         Row creation : When an entry is created in the 
                        xdslRtxProfileTable, an entry is created in
                        this table.
         Row deletion : When an entry is deleted from the
                        xdslRtxProfileTable, the entry is deleted from
                        this table. "
      INDEX            {xdslRtxProfileMappingName}
::= { xdslRtxProfileMappingTable 1 }

XdslRtxProfileMappingEntry ::=
        SEQUENCE {
            xdslRtxProfileMappingName        AsamProfileName,
            xdslRtxProfileMappingIndex       AsamProfileIndex
        }

xdslRtxProfileMappingName     OBJECT-TYPE
        SYNTAX          AsamProfileName
        ACCESS          not-accessible
        STATUS          mandatory
        DESCRIPTION
        "The Rtx profile name.

         ALCATEL NOTE:
             ACCESS:   NA                  USAGE:    NA
             PERSIST:  NO                  INSRVMOD: NA
             RANGE:    NA                  DEFVALUE: NA
             UNITS:    NA                  SPARSE:   NA
             DESCR:    NA "
::= { xdslRtxProfileMappingEntry 1 }

xdslRtxProfileMappingIndex    OBJECT-TYPE
        SYNTAX          AsamProfileIndex
        ACCESS          read-only
        STATUS          mandatory
        DESCRIPTION
        "The Index of the corresponding Rtx profile.

         ALCATEL NOTE:
             ACCESS:   NA                  USAGE:    NA
             PERSIST:  NO                  INSRVMOD: NA
             RANGE:    1..128               DEFVALUE: NA
             UNITS:    NA                  SPARSE:   NA
             DESCR:    NA "
::= { xdslRtxProfileMappingEntry 2 }

xdslRtxProfileIndexOffset     OBJECT-TYPE
        SYNTAX          AsamMaxProfileIndex
        ACCESS          read-only
        STATUS          mandatory
        DESCRIPTION
        "This object represents the offset to be added to an existing Rtx
         profile index during a modification in order to access the temporary
         profile entry that contains the updates being done on that profile, 
         see xdslRtxProfileIndex.

         ALCATEL NOTE:
             ACCESS:   NA                  USAGE:    NA
             PERSIST:  NO                  INSRVMOD: NA
             RANGE:    1000                DEFVALUE: 1000
             UNITS:    NA                  SPARSE:   NA
             DESCR:    NA "
::= {xdslRtxProfile 5}

END
