-- orig ASAM_EQPTCORENT_MIB

ASAM-EQUIP-MIB DEFINITIONS ::= BEGIN

   IMPORTS IpAddress,  TimeTicks, 
           Counter                  FROM RFC1155-SMI
           DisplayString, RowStatus,
           TruthValue               FROM SNMPv2-TC
           asam                     FROM SYSTEM-MIB
           OBJECT-TYPE              FROM RFC-1212
           AsamAlarmSeverityType    FROM ASAM-ALARM-MIB
           AsamNextProfileIndex,
           AsamProfileRefCount,
           AsamProfilePointer,
           AsamProfileIndex,
           AsamProfileName,
           NetworkTimeInSeconds     FROM ASAM-TC-MIB;

   asamEquipmentMIB OBJECT IDENTIFIER ::= { asam 23 }
     
   EqptHolderIndex ::= INTEGER (1..255)
   
   EqptHolderIndexOrZero ::= INTEGER (0..255)
   
   EqptSlotIndex ::= INTEGER (1..65535)

   EqptCustAlarmProfileOutputType ::=       INTEGER {
                           triggered(1),    
                           notTriggered(2)} 

   EqptCustAlarmProfilePolarityType ::=       INTEGER {
                             inversed(1), 
                             normal(2)}   

   EqptPortMappingIndex ::= INTEGER (1..255)

   eqptAsam OBJECT IDENTIFIER ::= { asamEquipmentMIB 1 }

   eqptAsamId OBJECT-TYPE
      SYNTAX DisplayString
      ACCESS read-only
      STATUS mandatory
      DESCRIPTION
         "Unique identifier of the system.
          In practice, this attribute contains the serial number of the most
          recently equipped SMAS board within the main shelf.

          Notice however that there are also shelves in which the SMAS is replaced
          by a GFC board (e.g ARAM-B) or even shelves without SMAS/GFC in which 
          the serial number of the ACU is taken.

          This attribute is used internally by the system in case both NTs
          start-up simultaneously to determine whether either the database on
          NT-A or the database on NT-B should be used as the systems database.
          It's not the intention to make this attribute visible to an operator.

          ALCATEL NOTE:
             SUPPORT: YES   INSRVMOD: NA   RANGE: See above
             PERSIST: YES   DEFVALUE: ''   UNITS: -"
      ::= { eqptAsam 1 }

   eqptAsamRestart OBJECT-TYPE
      SYNTAX INTEGER {
         restartWithSelfTest (1),
            
         restartWithoutSelfTest (2),
            
         restartHot (5),
            
         initialValue (255)
      }
      ACCESS read-write
      STATUS mandatory
      DESCRIPTION
         "This attribute is used to restart the system. The persistent data is preserved. 
          Contains previous restart reason, if not available it contains value 255.

          ALCATEL NOTE:
             SUPPORT: YES   INSRVMOD: YES                  RANGE: See above
             PERSIST: YES   DEFVALUE: initialValue (255)   UNITS: -"
      ::= { eqptAsam 2 }
   
   eqptMaxRacksPerAsam OBJECT-TYPE
      SYNTAX INTEGER
      ACCESS read-only
      STATUS mandatory
      DESCRIPTION
         "This object is initialized by the system and specifies the maximum
          number of racks supported by the system.

          ALCATEL NOTE:
             SUPPORT: YES   INSRVMOD: NA   RANGE: 1..7
             PERSIST: NO    DEFVALUE: NA   UNITS: -"
      ::= { eqptAsam 3 }
   
   eqptMaxShelvesPerRack OBJECT-TYPE
      SYNTAX INTEGER
      ACCESS read-only
      STATUS mandatory
      DESCRIPTION
         "This object is initialized by the system and specifies the maximum
          number of shelves which can be equipped within one rack.

          ALCATEL NOTE:
             SUPPORT: YES   INSRVMOD: NA   RANGE: 1..4
             PERSIST: NO    DEFVALUE: NA   UNITS: -"
      ::= { eqptAsam 4 }
   
   eqptMaxSlotsPerShelf OBJECT-TYPE
      SYNTAX INTEGER
      ACCESS read-only
      STATUS mandatory
      DESCRIPTION
         "This object is initialized by the system and specifies the maximum
          number of regular slots supported by one shelf.

          ALCATEL NOTE:
             SUPPORT: YES   INSRVMOD: NA   RANGE: 1..22
             PERSIST: NO    DEFVALUE: NA   UNITS: -"
      ::= { eqptAsam 5 }
   
   eqptHwNumberOfChanges OBJECT-TYPE
      SYNTAX Counter
      ACCESS read-only
      STATUS mandatory
      DESCRIPTION
         "Wrap around counter which indicates the number of configuration or
          status changes in the Equipment MIB objects.  This counter is
          incremented each time any of the summary table objects change.

          ALCATEL NOTE:
             SUPPORT: YES   INSRVMOD: NA   RANGE: See above
             PERSIST: NO    DEFVALUE: 0    UNITS: -"
      ::= { eqptAsam 6 }
   
   eqptProtNumberOfChanges OBJECT-TYPE
      SYNTAX Counter
      ACCESS read-only
      STATUS mandatory
      DESCRIPTION
         "Wrap around counter which indicates the overall number of status
          changes in the equipment protection MIB objects.  This counter is
          incremented each time any of the eqptProtGroupNumberOfChanges
          counters is incremented.
   
          ALCATEL NOTE:
             SUPPORT:YES   INSRVMOD: NA   RANGE: See above
             PERSIST: NO   DEFVALUE: 0    UNITS: -"
      ::= { eqptAsam 7 }

eqptRestartNumberOfChanges OBJECT-TYPE
      SYNTAX Counter
      ACCESS read-only
      STATUS mandatory
      DESCRIPTION
         "Wrap around counter which indicates the overall number of status
          changes in the eqptBoardRestartNumberOfChanges objects in
          eqptBoardTable. This counter is incremented each time any of the
          eqptBoardRestartNumberOfChanges counters is incremented.
   
          ALCATEL NOTE:
             SUPPORT: YES  INSRVMOD: NA   RANGE: See above
             PERSIST: NO   DEFVALUE: 0    UNITS: -"
      ::= { eqptAsam 8 }

   eqptHolderTable OBJECT-TYPE
      SYNTAX SEQUENCE OF EqptHolderEntry
      ACCESS not-accessible
      STATUS mandatory
      DESCRIPTION
         "Equipment holder table, representing the system, the racks and
          the shelves.

          This table contains one row for the system, one row per rack,
          and one row per shelf.

          ALCATEL NOTE:
             SUPPORT: YES  TABLESIZE: DEP as described above"
      ::= { asamEquipmentMIB 2 }
   
   eqptHolderEntry OBJECT-TYPE
      SYNTAX EqptHolderEntry
      ACCESS not-accessible
      STATUS mandatory
      DESCRIPTION
         "An entry of the equipment holder table.

          ALCATEL NOTE:
             SUPPORT: YES"
      INDEX { eqptHolderId }
      ::= { eqptHolderTable 1 }
   
   EqptHolderEntry ::= SEQUENCE {
      eqptHolderId                 EqptHolderIndex,
      eqptHolderClass              INTEGER,
      eqptHolderPlannedType        DisplayString,
      eqptHolderActualType         DisplayString,
      eqptHolderAdminStatus        INTEGER,
      eqptHolderOperStatus         INTEGER,
      eqptHolderOperError          INTEGER,
      eqptHolderAvailStatus        INTEGER,
      eqptHolderDescription        DisplayString, 
      eqptHolderContainerId        INTEGER,
      eqptHolderContainerOffset    INTEGER,
      eqptHolderMode               INTEGER
   }

   eqptHolderId OBJECT-TYPE
      SYNTAX EqptHolderIndex
      ACCESS not-accessible
      STATUS mandatory
      DESCRIPTION
         "Index in equipment holder Table.

          ALCATEL NOTE:
             SUPPORT: YES   INSRVMOD: NA   RANGE: See above
             PERSIST: NO    DEFVALUE: NA   UNITS: -"
      ::= { eqptHolderEntry 1 }

   eqptHolderClass OBJECT-TYPE
      SYNTAX INTEGER {
          mainIqHcl (1),    
                            
          extIq (2),        
          extHcl (3),       
          mainEthernet (4), 
          extEthernet (5)   
      }
      ACCESS read-write
      STATUS mandatory
      DESCRIPTION
         "Classification of shelves. This object has no meaning for the
          system and the rack equipment holders.
   
          Note: for ISAM, only the values mainEthernet (4) and extEthernet (5)
                are allowed.

          ALCATEL NOTE:
             SUPPORT: YES   INSRVMOD: NO   RANGE: 1..5
             PERSIST: YES   DEFVALUE: NA   UNITS: -"
      ::= { eqptHolderEntry 2 }
   
   eqptHolderPlannedType OBJECT-TYPE
      SYNTAX DisplayString
      ACCESS read-write
      STATUS mandatory
      DESCRIPTION
         "A string representing the planned type of equipment holder.
          If the equipment holder is planned, the string consists of a
          mnemonic, identifying the holder type.
          This object is only writable for the entries that represent a shelf.
          Other entries get a value corresponding to the detected equipment
          practice type.
                    
          Following values are valid:
                                                          
          System-types:
          -------------
          LAUS          Large ASAM US market (6 racks, 3 shelves per rack)
          LAEU          Large ASAM EU market (6 racks, 3 shelves per rack)
          LEEU          Large ESAM EU market (7 racks, 4 shelves per rack)
          LEUS          Large ESAM US market (7 racks, 4 shelves per rack)
          LNEU          Large New EquipmentPractise EU market(7 racks, 4 shelves
                        per rack)
          LEWW          Large ESAM World Wide (7 racks, 4 shelves per rack)

          Rack-types:
          -----------
          ALTR-A        ADSL Line Termination Rack version A (US)
          ALTR-E        ADSL Line Termination Rack version E (ETSI 2200mm)
     
          Shelf-types:
          ------------
          <SHELF_MNEMONIC>  A shelf of a specific type.  Refer to the ETSI
                            Configurations and US Configurations documents
                            for the list of shelf types that are supported
                            in a given system release.
   
          NOT_PLANNED       The shelf is not planned.
   
          NOT_ALLOWED       Shelf planning is not allowed in this position.

          ALCATEL NOTE:
             SUPPORT: YES   INSRVMOD: NO              RANGE: See above
             PERSIST: YES   DEFVALUE: 'NOT_PLANNED'   UNITS: -"
      ::= { eqptHolderEntry 3 }
   
   eqptHolderActualType OBJECT-TYPE
      SYNTAX DisplayString
      ACCESS read-only
      STATUS mandatory
      DESCRIPTION
         "A string representing the actual equipment holder type.
   
          Following values are possible: 
   
          <HOLDER_MNEMONIC> Indicates the detected equipment holder-type.
                            Uses same mnemonics as described in object 
                            eqptHolderPlannedType.
   
          EMPTY             Equipment holder is not detected
   
          UNKNOWN           The type of the detected holder is unknown.

          ALCATEL NOTE:
             SUPPORT: YES   INSRVMOD: NA   RANGE: See above
             PERSIST: NO    DEFVALUE: NA   UNITS: -"
      ::= { eqptHolderEntry 4 }
   
   eqptHolderAdminStatus OBJECT-TYPE
      SYNTAX INTEGER {
         unlock(1),
         lock(2)
      }
      ACCESS read-write
      STATUS mandatory
      DESCRIPTION 
         "Used by the administrator to lock or unlock an equipment holder.
          This attribute is only supported for shelves.

          ALCATEL NOTE:
             SUPPORT: YES   INSRVMOD: YES   RANGE: See above
             PERSIST: YES   DEFVALUE: 1     UNITS: -"
      ::= { eqptHolderEntry 5 }
   
   eqptHolderOperStatus OBJECT-TYPE
      SYNTAX INTEGER {
         enabled(1),
         disabled(2)
      }
      ACCESS read-only
      STATUS mandatory
      DESCRIPTION
         "This attribute identifies whether or not the equipment holder is
          capable of performing its normal functions.

          ALCATEL NOTE:
             SUPPORT: YES   INSRVMOD: NA   RANGE: 1..2
             PERSIST: NO    DEFVALUE: NA   UNITS: -"
      ::= { eqptHolderEntry 6 }
   
   eqptHolderOperError OBJECT-TYPE
      SYNTAX INTEGER {
         no-error(1),                   
         type-mismatch(2),            
         holder-missing(3),
         holder-installation-missing(4),   
         defense(15)         
      }
      ACCESS read-only
      STATUS mandatory
      DESCRIPTION
         "This attribute describes for what reason the equipment holder is
          not operational. These values correspond with the alarms that are
          generated in case of a failure.

          ALCATEL NOTE:
             SUPPORT: YES   INSRVMOD: NA   RANGE: 1..4, 15
             PERSIST: NO    DEFVALUE: 1    UNITS: -"
      ::= { eqptHolderEntry 7 }
   
   eqptHolderAvailStatus OBJECT-TYPE
      SYNTAX INTEGER {
          available(1),     
          failed (3),       
          notInstalled (5), 
          offLine (6)       
      }
      ACCESS read-only
      STATUS mandatory
      DESCRIPTION
         "This attribute indicates whether the equipment holder is
          available or not.

          ALCATEL NOTE:
             SUPPORT: YES   INSRVMOD: NA   RANGE: 1, 3, 5, 6
             PERSIST: NO    DEFVALUE: NA   UNITS: -"
      ::= { eqptHolderEntry 8 }
   
   eqptHolderDescription OBJECT-TYPE
      SYNTAX DisplayString (SIZE (0..127))
      ACCESS read-write
      STATUS mandatory
      DESCRIPTION
         "Text-field, which can for instance be used to describe the
          location of the equipment holder.

          ALCATEL NOTE:
             SUPPORT: YES   INSRVMOD: YES   RANGE: See above
             PERSIST: YES   DEFVALUE: ''    UNITS: -"
      ::= { eqptHolderEntry 9 }
   
   eqptHolderContainerId OBJECT-TYPE
      SYNTAX INTEGER
      ACCESS read-only
      STATUS mandatory
      DESCRIPTION
         "This attribute describes in which equipment holder the equipment
          holder is contained.
          This object is only meaningful for racks and shelves, since the
          system itself has no containing equipment holder.

          ALCATEL NOTE:
             SUPPORT: YES   INSRVMOD: NA   RANGE: See above
             PERSIST: NO    DEFVALUE: NA   UNITS: -"
      ::= { eqptHolderEntry 10 }
   
   eqptHolderContainerOffset OBJECT-TYPE
      SYNTAX INTEGER
      ACCESS read-only
      STATUS mandatory
      DESCRIPTION
         "This attribute describes the position of the equipment holder
          in the containing equipment holder.
          This object is only meaningful for racks and shelves, since the
          system itself has no containing equipment holder.

          ALCATEL NOTE:
             SUPPORT: YES   INSRVMOD: NA   RANGE: See above
             PERSIST: NO    DEFVALUE: NA   UNITS: -"
      ::= { eqptHolderEntry 11 }

   eqptHolderMode OBJECT-TYPE
      SYNTAX INTEGER{ 
          ntbntio-supported(1),
          ntbntio-unsupported(2),
          ntio-unsupported(6)
      }
      ACCESS read-write
      STATUS mandatory
      DESCRIPTION  "This attribute identifies the holder mode and is used by
          both the NEP shelf and the ARAM-E shelf:
          ntbntio-supported: this mode works in the same manner as iSAM XD. The
          LSM can only be used on LSM slot. NT in NTB is supported. NTIO is 
          also supported.
          ntbntio-unsupported: In this mode, NTIO & NTB slot can be used as
          LT slot. So, two more LSM can be supported in this mode. Therefore, 
          NTIO/NTB board is not supported 
          ntio-unsupported: This is the only mode supported in ARAM-E shelf.
          In this mode, there are no NTIOs; the dedicated NTIO1 slot can be 
          used for an LSM and NTIO2 slot can be used for a (Front Access) LSM 
          or an Applique. 
        DEFAULTVALUE:  The default Value of the eqptHolderMode depends 
          on the shelf type. In the case of ARAM-E, default will be ntio-unsupported.  
          All other shelves will default to ntbntio-supported mode.

          ALCATEL NOTE:
             SUPPORT: YES   INSRVMOD: NA          RANGE: See above
             PERSIST: Yes   DEFVALUE: See above   UNITS: -"
      ::= { eqptHolderEntry 12 }
   
   eqptBoardTable OBJECT-TYPE
      SYNTAX SEQUENCE OF EqptBoardEntry
      ACCESS not-accessible
      STATUS mandatory
      DESCRIPTION
         "A table representing the slots of all planned shelves. Each slot
          can hold a board of one of the following types: NT, EXT, LSM,
          ACU, CTRL, applique.

          This table has a row for each slot in each planned shelf.

          ALCATEL NOTE:
             SUPPORT: YES   TABLESIZE: DEP as described above"
      ::=  { asamEquipmentMIB 3 }
   
   eqptBoardEntry OBJECT-TYPE
      SYNTAX EqptBoardEntry
      ACCESS not-accessible
      STATUS mandatory
      DESCRIPTION
         "An entry in the eqptBoardTable.

          ALCATEL NOTE:
             SUPPORT: YES"
      INDEX { eqptSlotId }
      ::=  { eqptBoardTable 1 }
   
   EqptBoardEntry ::= SEQUENCE {
      eqptSlotId                         EqptSlotIndex,
      eqptSlotPlannedType                DisplayString,
      eqptSlotActualType                 DisplayString,
      eqptSlotPowerStatus                INTEGER,
      eqptBoardAdminStatus               INTEGER,
      eqptBoardOperStatus                INTEGER,
      eqptBoardOperError                 INTEGER,
      eqptBoardAvailStatus               INTEGER,
      eqptBoardRestart                   INTEGER,
      eqptBoardSwOverruleStatus          INTEGER,
      eqptBoardContainerId               INTEGER,
      eqptBoardContainerOffset           INTEGER,
      eqptBoardInventoryAlcatelCompanyId DisplayString,
      eqptBoardInventoryTypeName         DisplayString,
      eqptBoardInventoryPBACode          DisplayString,
      eqptBoardInventoryFPBACode         DisplayString,
      eqptBoardInventoryICScode          DisplayString,
      eqptBoardInventoryCLEICode         DisplayString,
      eqptBoardInventorySerialNumber     DisplayString,
      eqptBoardInventoryLastFailedTest   OCTET STRING (SIZE(4)),
      eqptSlotPlannedCapabilityProfile   AsamProfilePointer,
      eqptBoardCustAlarmProfile          AsamProfilePointer,
      eqptBoardLastRestartCause          INTEGER,
      eqptBoardLastRestartTime           NetworkTimeInSeconds,
      eqptBoardRestartNumberOfChanges    Counter,
      eqptBoardRelatedMgntEntityIPAddress	 IpAddress,
      eqptBoardRelatedMgntEntityPairedNumber	 INTEGER,
      eqptBoardDualHostIPAddress         IpAddress,
      eqptBoardDualHostLsmLocation       EqptHolderIndexOrZero,
      eqptBoardIfSlotId                  INTEGER
   }
    
   eqptSlotId OBJECT-TYPE
      SYNTAX EqptSlotIndex 
      ACCESS not-accessible
      STATUS mandatory
      DESCRIPTION
         "A unique value to identify a slot position.

          ALCATEL NOTE:
             SUPPORT: YES   INSRVMOD: NA   RANGE: See above
             PERSIST: YES   DEFVALUE: NA   UNITS: -"
      ::= { eqptBoardEntry 1 }
   
   eqptSlotPlannedType OBJECT-TYPE
      SYNTAX DisplayString    
      ACCESS read-write
      STATUS mandatory
      DESCRIPTION
         "A string representing the board (NT, EXT, LSM, ACU, CTRL, Applique) that
          is planned in the slot.  If the board is planned, the string consists
          of a mnemonic that identifies the board-type.
                  
          Following mnemonics are valid:

          <BOARD_MNEMONIC> A board of a specific type.  Refer to the ETSI and
                           US Configurations documents for the list of boards
                           that are supported in a given release.
                           ODM board types are planned with the board mnemonic,
                           they are treated as unmanaged boards.

          EXT_MANAGED      The presence of the LT module can be detected but 
                           it is not managed by this NT in the HYNT module. 
                           The LT type must be planned on the other NT.
   
          UNMANAGED        Unmanaged board: this means that the presence of
                           the board can be detected and that the board can
                           be reset and powered-down but that it is not
                           possible to establish communication with the board
                           in software.
                
          NOT_PLANNED      No board is planned in the slot.

          NOT_ALLOWED      Slot planning is not allowed in this position.

          ALCATEL NOTE:
             SUPPORT: YES   INSRVMOD: YES             RANGE: See above
             PERSIST: YES   DEFVALUE: 'NOT_PLANNED'   UNITS: -"
      ::= { eqptBoardEntry 2 }
    
   eqptSlotActualType OBJECT-TYPE
      SYNTAX DisplayString
      ACCESS read-only
      STATUS mandatory
      DESCRIPTION
         "A string representing the board (NT, EXT, LSM, ACU, CTRL, Applique) that
          is actually present in the slot.
   
          Following values are possible:

          <BOARD_MNEMONIC>  Indicates the detected board-type.  Uses same
                            mnemonics as described in object 
                            eqptSlotPlannedType.
   
          EMPTY             No board plugged within this slot.

          EXT_MANAGED      The presence of the LT module can be detected but 
                           it is not managed by this NT in the HYNT module. 
                           The LT type must be planned on the other NT.
   
          UNMANAGED         The type of the detected board is unknown
                            and the planned board type is UNMANAGED or ODMboardtype.

          UNKNOWN           The type of the detected board is unknown
                            and the planned board type is not UNMANAGED
                            and the planned board type is not EXT_MANAGED.
 
          ALCATEL NOTE:
             SUPPORT: YES   INSRVMOD: NA   RANGE: See above
             PERSIST: NO    DEFVALUE: NA   UNITS: -"
      ::= { eqptBoardEntry 3 }
   
   eqptSlotPowerStatus OBJECT-TYPE
      SYNTAX INTEGER {
         powerUp(1),              
         powerDown(2)         
      }
      ACCESS read-write
      STATUS mandatory
      DESCRIPTION
         "This attribute is used by the operator to power-up or power-down
          an LSM slot. This attribute is not supported for other type of slots.

          ALCATEL NOTE:
             SUPPORT: YES   INSRVMOD: YES   RANGE: 1..2
             PERSIST: YES   DEFVALUE: 1     UNITS: -"
      ::= { eqptBoardEntry 4 }
   
   eqptBoardAdminStatus OBJECT-TYPE
      SYNTAX INTEGER {
         unlock(1),              
         lock(2)         
      }
      ACCESS read-write
      STATUS mandatory
      DESCRIPTION
         "This attribute is used by the operator to lock or unlock the board.

          This attribute is only supported for the following type of boards:
          NT (but notice that the system will refuse a request to lock the NT
          of a simplex system), EXT and LSM (if managed).  This attribute has
          no meaning for an unmanaged or externally managed (EXT_MANAGED) LSM,
          for an ACU, CTRL or for an applique.

          ALCATEL NOTE:
             SUPPORT: YES   INSRVMOD: YES   RANGE: 1..2
             PERSIST: YES   DEFVALUE: 1     UNITS: -"
      ::= { eqptBoardEntry 5 }
   
   eqptBoardOperStatus OBJECT-TYPE
      SYNTAX INTEGER {
         enabled(1),
         disabled(2)
      } 
      ACCESS read-only
      STATUS mandatory
      DESCRIPTION
         "This attribute informs the operator whether the plug-in unit is able
          to perform its normal operation.

          This attribute is supported for all type of boards: NT, EXT, LSM,
          ACU, CTRL, applique.

          ALCATEL NOTE:
             SUPPORT: YES   INSRVMOD: NA   RANGE: 1..2
             PERSIST: NO    DEFVALUE: NA   UNITS: -"
      ::= { eqptBoardEntry 6 }
   
   eqptBoardOperError OBJECT-TYPE
      SYNTAX INTEGER {
         no-error(1),                   
         type-mismatch(2),
         board-missing(3),
         board-installation-missing(4),
         no-planned-board(5),
         waiting-for-sw(6),
         init-boot-failed(7),
         init-download-failed(8),
         init-connection-failed(9),
         init-configuration-failed(10),
         board-reset-protection(11),
         invalid-parameter(12),
         temperature-alarm(13),
         tempshutdown(14),
         defense(15),
         board-not-licensed(16),
         sem-power-fail(17),
         sem-ups-fail(18),
         board-in-incompatible-slot(19),
         unknown-error(255)
      } 
      ACCESS read-only
      STATUS mandatory
      DESCRIPTION
         "This attribute describes for what reason the board is not operational.
          These values correspond with the alarms which are generated in case of
          a failure.

          This attribute is supported for all type of boards: NT, EXT, LSM,
          ACU, CTRL, applique.
          Default value is no-error, replaced by result from startup sequence.

          ALCATEL NOTE:
             SUPPORT: YES   INSRVMOD: NA   RANGE: 1..15, 255
             PERSIST: NO    DEFVALUE: 1    UNITS: -"
      ::= { eqptBoardEntry 7 }
   
   eqptBoardAvailStatus OBJECT-TYPE
      SYNTAX INTEGER {
         available(1),    
         inTest(2),       
         failed(3),       
         powerOff(4),     
         notInstalled(5), 
         offLine(6),      
         dependency(7)    
                          
      } 
      ACCESS read-only
      STATUS mandatory
      DESCRIPTION
         "This attribute provides further information regarding the state
          of the board. It is set to available after a successfull selftest
          of the board (if applicable).

          This attribute is supported for all type of boards: NT, EXT, LSM,
          ACU, CTRL, applique.

          ALCATEL NOTE:
             SUPPORT: YES   INSRVMOD: NA   RANGE: 1..7
             PERSIST: NO    DEFVALUE: NA   UNITS: -"
      ::= { eqptBoardEntry 8 }
   
   eqptBoardRestart OBJECT-TYPE
      SYNTAX INTEGER {
         with-selftest(1),
         without-selftest(2),
         hot-restart(5),
         initialValue (255)
      }
      ACCESS read-write
      STATUS mandatory
      DESCRIPTION
         "Writing a valid value to this object will restart the board in the
          specified mode.

          This attribute is only supported for the following type of boards:
          NT, EXT, managed LSM, ACU, CTRL.  For ACU and CTRL boards, only a
          restart without selftest is supported.
          Contains previous restart reason, if not available it has value 255.

          ALCATEL NOTE:
             SUPPORT: YES   INSRVMOD: YES   RANGE: 1, 2, 5, 255
             PERSIST: YES   DEFVALUE: NA    UNITS: -"
      ::= { eqptBoardEntry 9 }
   
   eqptBoardSwOverruleStatus OBJECT-TYPE
      SYNTAX INTEGER {
         no-overrule(1),
         overrule(2)
      }
      ACCESS read-write
      STATUS mandatory
      DESCRIPTION
         "Used to overrule the default software version for this board.
          This attribute is only supported for managed LSMs.

          ALCATEL NOTE:
             SUPPORT: YES   INSRVMOD: YES   RANGE: 1..2
             PERSIST: NO    DEFVALUE: 1     UNITS: -"
      ::= { eqptBoardEntry 10 }
   
   eqptBoardContainerId OBJECT-TYPE
      SYNTAX INTEGER
      ACCESS read-only
      STATUS mandatory
      DESCRIPTION
         "This attribute describes in which equipment holder the slot
          is contained.

          ALCATEL NOTE:
             SUPPORT: YES  INSRVMOD: NA   RANGE: See above
             PERSIST: NO   DEFVALUE: NA   UNITS: -"
      ::= { eqptBoardEntry 11 }
   
   eqptBoardContainerOffset OBJECT-TYPE
      SYNTAX INTEGER
      ACCESS read-only
      STATUS mandatory
      DESCRIPTION
         "This attribute describes the position of the slot in the  
          containing equipment holder.

          ALCATEL NOTE:
             SUPPORT: YES  INSRVMOD: NA   RANGE: See above
             PERSIST: NO   DEFVALUE: NA   UNITS: -"
      ::= { eqptBoardEntry 12 }
   
   eqptBoardInventoryAlcatelCompanyId OBJECT-TYPE
      SYNTAX DisplayString
      ACCESS read-only
      STATUS mandatory
      DESCRIPTION
         "This attribute represents the company of the board.

          ALCATEL NOTE:
             SUPPORT: YES  INSRVMOD: NA   RANGE: See above
             PERSIST: NO   DEFVALUE: NA   UNITS: -"
      ::= { eqptBoardEntry 13 }
   
   eqptBoardInventoryTypeName OBJECT-TYPE
      SYNTAX DisplayString
      ACCESS read-only
      STATUS mandatory
      DESCRIPTION
         "This attribute represents the name of the board.

          ALCATEL NOTE:
             SUPPORT: YES  INSRVMOD: NA   RANGE: See above
             PERSIST: NO   DEFVALUE: NA   UNITS: -"
      ::= { eqptBoardEntry 14 }
   
   eqptBoardInventoryPBACode OBJECT-TYPE
      SYNTAX DisplayString
      ACCESS read-only
      STATUS mandatory
      DESCRIPTION
         "This attribute represents the Alcatel Printed Board Assembly 
          code of of the board.

          ALCATEL NOTE:
             SUPPORT: YES  INSRVMOD: NA   RANGE: See above
             PERSIST: NO   DEFVALUE: NA   UNITS: -"
      ::= { eqptBoardEntry 15 }
   
   eqptBoardInventoryFPBACode OBJECT-TYPE
      SYNTAX DisplayString
      ACCESS read-only
      STATUS mandatory
      DESCRIPTION
         "This attribute represents the Alcatel Printed Board Assembly 
          code of the board, which also identifies the boot software.

          ALCATEL NOTE:
             SUPPORT: YES  INSRVMOD: NA   RANGE: See above
             PERSIST: NO   DEFVALUE: NA   UNITS: -"
      ::= { eqptBoardEntry 16 }
   
   eqptBoardInventoryICScode OBJECT-TYPE
      SYNTAX DisplayString
      ACCESS read-only
      STATUS mandatory
      DESCRIPTION
         "This attribute represents the Item Change Status iteration 
          code of the board.

          ALCATEL NOTE:
             SUPPORT: YES  INSRVMOD: NA   RANGE: See above
             PERSIST: NO   DEFVALUE: NA   UNITS: -"
      ::= { eqptBoardEntry 17 }
   
   eqptBoardInventoryCLEICode OBJECT-TYPE
      SYNTAX DisplayString
      ACCESS read-only
      STATUS mandatory
      DESCRIPTION
         "This attribute represents the (USA) Common Language Equipment  
          Identification code of the board.

          ALCATEL NOTE:
             SUPPORT: YES  INSRVMOD: NA   RANGE: See above
             PERSIST: NO   DEFVALUE: NA   UNITS: -"
      ::= { eqptBoardEntry 18 }
   
   eqptBoardInventorySerialNumber OBJECT-TYPE
      SYNTAX DisplayString
      ACCESS read-only
      STATUS mandatory
      DESCRIPTION
         "This attribute represents the serial number of the board.
          
          Breakdown of a sample serial number is :

          sample NANT-D serial number is AA1003ZA028

             AA  10    03     ZA028
                 ---  ----  ----------
                  |     |        |-----' Production Plant Code
                  |     |           
                  |     |--------------' Week
                  |
                  |--------------------' Year

          ALCATEL NOTE:
             SUPPORT: YES  INSRVMOD: NA   RANGE: See above
             PERSIST: NO   DEFVALUE: NA   UNITS: -"
      ::= { eqptBoardEntry 19 }
   
   eqptBoardInventoryLastFailedTest OBJECT-TYPE
      SYNTAX OCTET STRING (SIZE(4))
      ACCESS read-only
      STATUS mandatory
      DESCRIPTION
         "Identifies the last failing test by means of 4 numbers, from MSB
          to LSB:
             - Table number (1 byte)
             - Segment number (1 byte)
             - Case number (1 byte)
             - Check number (1 byte)
          As long as there has been no failing selftest, the value of this
          object will be 0.

          ALCATEL NOTE:
             SUPPORT: YES  INSRVMOD: NA   RANGE: See above
             PERSIST: NO   DEFVALUE: NA   UNITS: -"
      ::= { eqptBoardEntry 20 }
   
   eqptSlotPlannedCapabilityProfile OBJECT-TYPE
      SYNTAX AsamProfilePointer
      ACCESS read-write
      STATUS mandatory
      DESCRIPTION
         "A pointer to the capability profile that will be used for this
          slot. Capability profiles are only applicable for LT cards
          that are not EXT_MANAGED and not UNMANAGED, and NTIO cards.
          Planning the profile should always be done at the same moment the
          LT/NTIO is planned. 
       
          ALCATEL NOTE:
             SUPPORT: YES   INSRVMOD: YES   RANGE: See above
             PERSIST: YES   DEFVALUE: 0     UNITS: -"
      ::= { eqptBoardEntry 22 }

   eqptBoardCustAlarmProfile OBJECT-TYPE
      SYNTAX AsamProfilePointer
      ACCESS read-write
      STATUS mandatory
      DESCRIPTION
         "A pointer to the customizable alarms profile that will be used 
          for this board. Profiles are only applicable for REM and SEM boards.

          ALCATEL NOTE:
             SUPPORT: YES   INSRVMOD: YES   RANGE: See above
             PERSIST: YES   DEFVALUE: 0     UNITS: -"
      ::= { eqptBoardEntry 23 }

   eqptBoardLastRestartCause OBJECT-TYPE
      SYNTAX INTEGER {
         poweron(1), 
         unknown(2),
         watchdog(3), 
         coldreset(4), 
         warmreset(5), 
         hotreset(6), 
         hotreload(7), 
         cleandata(8),
         emergencybuild(9),
         poweronreset(10), 
         commitfailure(11) 
      }
      ACCESS read-only
      STATUS mandatory
      DESCRIPTION
         "This attribute gives the last restart cause for board.
          Currently only LSM board can support. Considering future safe,
          only use default value for other board entry.

          ALCATEL NOTE:
             SUPPORT: YES   INSRVMOD: NA        RANGE: See above
             PERSIST: NO    DEFVALUE: unknown   UNITS: -"
      ::= { eqptBoardEntry 24 }

   eqptBoardLastRestartTime OBJECT-TYPE
      SYNTAX NetworkTimeInSeconds
      ACCESS read-only
      STATUS mandatory
      DESCRIPTION
         "This attribute gives the last restart time.
          Currently only LSM board can support. Considering future safe,
          only use default value for other board entry.

          ALCATEL NOTE:
             SUPPORT: YES   INSRVMOD: NA    RANGE: See above
             PERSIST: NO    DEFVALUE: 0     UNITS: -"
      ::= { eqptBoardEntry 25 }

   eqptBoardRestartNumberOfChanges OBJECT-TYPE
      SYNTAX Counter
      ACCESS read-only
      STATUS mandatory
      DESCRIPTION
         "Wrap around counter which indicates the number of restart times.
          This counter is incremented each time eqptBoardLastRestartTime
          changes. Considering future safe, only use default value for
          other board entry.

          ALCATEL NOTE:
             SUPPORT: YES   INSRVMOD: NA    RANGE: See above
             PERSIST: NO    DEFVALUE: 0     UNITS: -"
      ::= { eqptBoardEntry 26 }

   eqptBoardRelatedMgntEntityIPAddress OBJECT-TYPE
      SYNTAX IpAddress
      ACCESS read-only
      STATUS mandatory
      DESCRIPTION
      	 "Network address. It is a public OAM IP address related to xVPS. For
	  single OAM IP is introduced, multi-xVPS boards existing on a same shelf
          may use one single OAM IP. This IP is configured on NT which manages
          these xVPS boards.
          
          ALCATEL NOTE:
          SUPPORT: YES      INSRVMOD: NA    RANGE:
          PERSIST: NO       DEFVALUE: 0     UNITS: -"
      ::= { eqptBoardEntry 27 }

   eqptBoardRelatedMgntEntityPairedNumber OBJECT-TYPE
      SYNTAX INTEGER    
      ACCESS read-only
      STATUS mandatory
      DESCRIPTION
         " For single OAM IP is introduced, one public OAM IP can not identify an
           xVPS, so community string is introduced. Each active xVPS will have
           different community string in one shelf.

          ALCATEL NOTE:
             SUPPORT: YES  INSRVMOD: NA   RANGE:
             PERSIST: NO   DEFVALUE: 0   UNITS: -"
      ::= { eqptBoardEntry 28 }

   eqptBoardDualHostIPAddress OBJECT-TYPE
      SYNTAX IpAddress
      ACCESS read-write
      STATUS mandatory
      DESCRIPTION
      	 "Network address. Only applicable for FD REM connected to dual host.  
	  It is the public OAM IP address of the host connecting the Lsm in this
	  externally managed slot. It is instantiated with default value and
	  can only be set when the planned type is EXT_MANAGED.  
          
          ALCATEL NOTE:
          SUPPORT: YES      INSRVMOD: YES   RANGE:
          PERSIST: YES      DEFVALUE: 0     UNITS: -"
      ::= { eqptBoardEntry 29 }

   eqptBoardDualHostLsmLocation OBJECT-TYPE
      SYNTAX EqptHolderIndexOrZero    
      ACCESS read-write
      STATUS mandatory
      DESCRIPTION
         " Only applicable for FD REM connected to dual host.  
	   It is the Rack/Shelf identifying the location of this 
	   externally managed slot, within the scope of the host connecting
	   the Lsm.  The slot component is implicitly present in the key.
	   It is instantiated with default value and can only be set when
	   the planned type is EXT_MANAGED.  The type corresponds to the 
	   type EqptHolderIndex, except for the fact that this field can
	   be 0, which is the default value.  

          ALCATEL NOTE:
             SUPPORT: YES  INSRVMOD: YES  RANGE: See above
             PERSIST: YES  DEFVALUE: 0    UNITS: -"
      ::= { eqptBoardEntry 30 }
      
   eqptBoardIfSlotId OBJECT-TYPE
      SYNTAX INTEGER
      ACCESS read-only
      STATUS mandatory
      DESCRIPTION
         " This object gives the slot's linear number, which could be
	   used by an external manager to help in mapping a given
	   IfIndex to a physical slot location. It is a numerical value
	   that consists of 6 bits. For a slot that does not carry any
	   interfaces (e.g. applique or NTIO slot), the value is always
	   '0xFF'.
           Note that this linear slot number is persistent across system
	   restarts, i.e. the same linear slot number will be used for
	   the same slot even after a restart of the ISAM system.
	   However, it is not guaranteed that the same linear slot
	   number will used after a migration to a new release.

      ALCATEL NOTE:
         SUPPORT: YES  INSRVMOD: YES  RANGE: See above
         PERSIST: YES  DEFVALUE: 0xFF UNITS: -"
      ::= { eqptBoardEntry 32 }

   eqptShelfSummaryTable OBJECT-TYPE
      SYNTAX SEQUENCE OF EqptShelfSummaryEntry
      ACCESS not-accessible
      STATUS mandatory
      DESCRIPTION
         "Shelf summary table, summarizing slot or board related status
          changes within each shelf.

          This table has one row per planned shelf.

          ALCATEL NOTE:
             SUPPORT: YES   TABLESIZE: DEP as described above."
      ::= { asamEquipmentMIB 4 }
   
   eqptShelfSummaryEntry OBJECT-TYPE
      SYNTAX EqptShelfSummaryEntry
      ACCESS not-accessible
      STATUS mandatory
      DESCRIPTION
         "An entry of the shelf summary table.

          ALCATEL NOTE:
             SUPPORT: YES"
      INDEX { eqptHolderId }
      ::= { eqptShelfSummaryTable 1 }
   
   EqptShelfSummaryEntry ::= SEQUENCE {
      eqptShelfHwNumberOfChanges         Counter,
      eqptShelfSlotSummaryOccupation     OCTET STRING,
      eqptShelfBoardSummaryAdmin         OCTET STRING,
      eqptShelfBoardSummaryAvail         OCTET STRING,
      eqptShelfBoardSummaryOper          OCTET STRING,
      eqptShelfBoardSummaryTypeMismatch  OCTET STRING,
      eqptShelfBoardSummaryAlarm         OCTET STRING
   }
   
   eqptShelfHwNumberOfChanges OBJECT-TYPE
      SYNTAX Counter
      ACCESS read-only
      STATUS mandatory
      DESCRIPTION
         "Wrap around counter which indicates the number of configuration or
          status changes for slots/boards within this shelf. This counter
          is incremented each time any of the summary table objects of this
          shelf changes.

          ALCATEL NOTE:
             SUPPORT: YES  INSRVMOD: NA   RANGE: See above
             PERSIST: NO   DEFVALUE: NA   UNITS: -"
      ::= { eqptShelfSummaryEntry 1 }
   
   eqptShelfSlotSummaryOccupation OBJECT-TYPE
      SYNTAX OCTET STRING (SIZE(8)) 
      ACCESS read-only
      STATUS mandatory
      DESCRIPTION
         "Bitmap of the occupation of slots (0 = empty, 1 = full)
          Applicable for NT, EXT, LSM, ACU, CTRL, applique.

          ALCATEL NOTE:
             SUPPORT: YES  INSRVMOD: NA   RANGE: See above
             PERSIST: NO   DEFVALUE: NA   UNITS: -"
      ::= { eqptShelfSummaryEntry 2 }
   
   eqptShelfBoardSummaryAdmin OBJECT-TYPE
      SYNTAX OCTET STRING (SIZE(8)) 
      ACCESS read-only
      STATUS mandatory
      DESCRIPTION
         "Bitmap of the administrative state of the boards
          (0 = locked, 1 = unlocked).  Applicable for NT, EXT, LSM.

          ALCATEL NOTE:
             SUPPORT: YES  INSRVMOD: NA   RANGE: See above
             PERSIST: NO   DEFVALUE: NA   UNITS: -"
      ::= { eqptShelfSummaryEntry 3 }
   
   eqptShelfBoardSummaryAvail OBJECT-TYPE
      SYNTAX OCTET STRING (SIZE(8)) 
      ACCESS read-only
      STATUS mandatory
      DESCRIPTION
         "Bitmap of the availability state of the boards (0 = not available,
          1 = available).  Applicable for NT, EXT, LSM, ACU, CTRL, applique.

          ALCATEL NOTE:
             SUPPORT: YES  INSRVMOD: NA   RANGE: See above
             PERSIST: NO   DEFVALUE: NA   UNITS: -"
      ::= { eqptShelfSummaryEntry 4 }
   
   eqptShelfBoardSummaryOper OBJECT-TYPE
      SYNTAX OCTET STRING (SIZE(8)) 
      ACCESS read-only
      STATUS mandatory
      DESCRIPTION
         "Bitmap of the operational state of the boards (0 = locked,
          1 = unlocked).  Applicable for NT, EXT, LSM, ACU, CTRL, applique.

          ALCATEL NOTE:
             SUPPORT: YES  INSRVMOD: NA   RANGE: See above
             PERSIST: NO   DEFVALUE: NA   UNITS: -"
      ::= { eqptShelfSummaryEntry 5 }
   
   eqptShelfBoardSummaryTypeMismatch OBJECT-TYPE
      SYNTAX OCTET STRING (SIZE(8)) 
      ACCESS read-only
      STATUS mandatory
      DESCRIPTION
         "Bitmap of the mismatch between the actual board-type and the planned
          board-type (0 = mismatch, 1 = no mismatch).
          Applicable for NT, EXT, LSM, ACU, CTRL, applique.

          ALCATEL NOTE:
             SUPPORT: YES  INSRVMOD: NA   RANGE: See above
             PERSIST: NO   DEFVALUE: NA   UNITS: -"
      ::= { eqptShelfSummaryEntry 6 }
   
   eqptShelfBoardSummaryAlarm OBJECT-TYPE
      SYNTAX OCTET STRING (SIZE(8)) 
      ACCESS read-only
      STATUS mandatory
      DESCRIPTION
         "Bitmap of the boards which generated an alarm (0 = alarm,
          1 = no alarm).  Applicable for NT, EXT, LSM, ACU, CTRL, applique.

          ALCATEL NOTE:
             SUPPORT: YES  INSRVMOD: NA   RANGE: See above
             PERSIST: NO   DEFVALUE: NA   UNITS: -"
      ::= { eqptShelfSummaryEntry 7 }
   
   eqptProt OBJECT IDENTIFIER ::= { asamEquipmentMIB 5 }

   eqptProtNextProtGroupId OBJECT-TYPE
      SYNTAX INTEGER
      ACCESS read-only
      STATUS mandatory
      DESCRIPTION
         "This object contains an appropriate value to be used for
          eqptProtGroupId when creating entries in the eqptProtGroupTable.
          The value 0 indicates that no unassigned entries are available.
          After each retrieval, the agent will modify the value to the
          next unassigned index.

          ALCATEL NOTE:
             SUPPORT: YES   INSRVMOD: YES   RANGE: See above
             PERSIST: NO    DEFVALUE: NA    UNITS: -"
      ::= {eqptProt 1}
   
   eqptProtGroupTable OBJECT-TYPE
      SYNTAX SEQUENCE OF EqptProtGroupEntry
      ACCESS not-accessible
      STATUS mandatory
      DESCRIPTION
         "A table representing groups of protected or protecting elements.
          Only one row for NT protection group which will always be created and  
          cannot be deleted.
          From ISAM R4.1.02 the default created NT protection group will be locked.  
          (before it was unlocked).
          From R3.3 onwards, each LT protection group (comprised of 2 adjacent
          slots LT n and LT n+1, where n is a odd number), also has a row.

          ALCATEL NOTE:
             SUPPORT: YES   TABLESIZE:  DEP as described above "
      ::= { eqptProt 2 }
   
   eqptProtGroupEntry OBJECT-TYPE
      SYNTAX EqptProtGroupEntry
      ACCESS not-accessible
      STATUS mandatory
      DESCRIPTION
         "An entry of the eqptProtGroupTable.

          ALCATEL NOTE:
             SUPPORT: YES"
      INDEX { eqptProtGroupId }
      ::= { eqptProtGroupTable 1 }
   
   EqptProtGroupEntry ::= SEQUENCE {
      eqptProtGroupId                     INTEGER,
      eqptProtGroupType                   INTEGER,
      eqptProtGroupNumberOfChanges        Counter,
      eqptProtGroupSwitchoverCount        Counter,
      eqptProtGroupLastSwitchoverReason   INTEGER,
      eqptProtGroupEpsQuenchfactor        TimeTicks,
      eqptProtGroupAlarmBitmap            INTEGER,
      eqptProtGroupAdminStatus            INTEGER,
      eqptProtGroupAdminProtElement       INTEGER,
      eqptProtGroupOperProtElement        INTEGER,
      eqptProtGroupRowStatus              RowStatus
   }
   
   eqptProtGroupId OBJECT-TYPE
      SYNTAX INTEGER
      ACCESS not-accessible
      STATUS mandatory
      DESCRIPTION
         "A unique value to identify a protection group.
          The value 1 is reserved for the NT protection group,
          which is always present and cannot be deleted.

          ALCATEL NOTE:
             SUPPORT: YES   INSRVMOD: NA   RANGE: See above
             PERSIST: YES   DEFVALUE: NA   UNITS: -"
      ::= { eqptProtGroupEntry 1}
   
   eqptProtGroupType OBJECT-TYPE
      SYNTAX INTEGER {
         one-plus-one(1),
         one-for-N(2)
      }
      ACCESS read-write
      STATUS mandatory
      DESCRIPTION
         "This attributes distinguishes between 1+1 and 1:N protection groups.

          ALCATEL NOTE:
             SUPPORT: YES   INSRVMOD: NA                RANGE: 1..2
             PERSIST: YES   DEFVALUE: one-plus-one(1)   UNITS: -"
      ::= { eqptProtGroupEntry 2 }
   
   eqptProtGroupNumberOfChanges OBJECT-TYPE
      SYNTAX Counter 
      ACCESS read-only
      STATUS mandatory
      DESCRIPTION
         "Wrap around counter which indicates the number of status changes
          in this protection group as well as the status changes for the
          protecting elements within this group:
              eqptProtGroupSwitchoverCount;
              eqptProtGroupLastSwitchoverReason;
              eqptProtGroupAlarmBitmap;
              eqptProtElementStandbyStatus.

          ALCATEL NOTE:
             SUPPORT: YES   INSRVMOD: NA   RANGE: See above
             PERSIST: NO    DEFVALUE: NA   UNITS: -"
      ::= { eqptProtGroupEntry 3 }
   
   eqptProtGroupSwitchoverCount OBJECT-TYPE
      SYNTAX Counter 
      ACCESS read-only
      STATUS mandatory
      DESCRIPTION
         "Wrap around counter for the number of switchovers being performed.

          ALCATEL NOTE:
             SUPPORT: YES   INSRVMOD: NA   RANGE: See above
             PERSIST: YES   DEFVALUE: 0    UNITS: -"
      ::= { eqptProtGroupEntry 4 }
   
   eqptProtGroupLastSwitchoverReason OBJECT-TYPE
      SYNTAX INTEGER {
          noSwitchOver(1),          
          forcedActive(2),          
          boardNotPresent(3),       
          extenderChainFailure(4),  
          linkFailure(5),           
          watchDogTimeOut(6),       
          fileSystemCorrupt(7),     
          configurationMismatch(8), 
          boardUnplanned(9),        
          boardLocked(10),          
          shelfDefense(11),         
          revertiveSwitchOver(12),  
                                    
          lanxFailure(13),          
   	      lanxHwFailure(14),        
                                    
          lanxSdkFailure(15)        
                                    
      }
      ACCESS read-only
      STATUS mandatory
      DESCRIPTION
         "This object contains the reason of the last switch over.

          ALCATEL NOTE:
             SUPPORT: YES   INSRVMOD: NA   RANGE: 1..15
             PERSIST: YES   DEFVALUE: NA   UNITS: -"
      ::= { eqptProtGroupEntry 5 }
   
   eqptProtGroupEpsQuenchfactor OBJECT-TYPE
      SYNTAX TimeTicks 
      ACCESS read-write
      STATUS mandatory
      DESCRIPTION
         "This object contains a timervalue in 1/100 sec. The EpsQuench timer
          is used to prevent continuous switch-overs in case of unstable EPS.
          Value equal to zero means the quenching mechanism is disabled.
          Configuration of the EPS quenchfactor has mainly be foreseen for
          test purposes. Operators should preferably not be able to
          reconfigure the default value.

          ALCATEL NOTE:
             SUPPORT: YES   INSRVMOD: YES       RANGE: See above
             PERSIST: YES   DEFVALUE: 1440000   UNITS: 0.01 seconds"
      DEFVAL { 1440000}   
      ::= { eqptProtGroupEntry 6 }
   
   eqptProtGroupAlarmBitmap OBJECT-TYPE
      SYNTAX INTEGER (1..4294967295) 
      ACCESS read-only
      STATUS mandatory
      DESCRIPTION
         "Status bitmap:
             bit 0 set means No defect at all
             bit 1 : if bit set, Standby degradation alarm is set
                     (excludes bit 0 setting)
             bit 2 .. 31 : reserved for future extensions.

          ALCATEL NOTE:
             SUPPORT: YES   INSRVMOD: NA           RANGE: See above
             PERSIST: NO    DEFVALUE: 0x00000001   UNITS: -"
      ::= { eqptProtGroupEntry 7 }
   
   eqptProtGroupAdminStatus OBJECT-TYPE
      SYNTAX INTEGER {
         unlock(1),
         lock(2)
      } 
      ACCESS read-write
      STATUS mandatory
      DESCRIPTION
         "Used by the administrator to disable or enable protection within
          that protection group.

          ALCATEL NOTE:
             SUPPORT: YES   INSRVMOD: YES         RANGE: 1..2
             PERSIST: YES   DEFVALUE: unlock(1)   UNITS: -"
      ::= { eqptProtGroupEntry 8 }
 
   eqptProtGroupAdminProtElement OBJECT-TYPE
      SYNTAX INTEGER
      ACCESS read-write
      STATUS mandatory
      DESCRIPTION
         "Only supported for 1:N protection groups. In case of a forced
          switchover to the spare element, this attribute is used to specify
          the element to be protected. The value 0 means that no element is
          specified.

          ALCATEL NOTE:
             SUPPORT: YES   INSRVMOD: YES   RANGE: See above
             PERSIST: YES   DEFVALUE: NA    UNITS: -"
      ::= { eqptProtGroupEntry 9 }
   
   eqptProtGroupOperProtElement OBJECT-TYPE
      SYNTAX INTEGER
      ACCESS read-only
      STATUS mandatory
      DESCRIPTION
         "Only supported for 1:N protection groups. Indicates which element
          is currently protected by the spare element. The value 0 means that
          currently the spare element is not protecting any element.

          ALCATEL NOTE:
             SUPPORT: YES   INSRVMOD: NA   RANGE: See above
             PERSIST: NO    DEFVALUE: NA   UNITS: -"
      ::= { eqptProtGroupEntry 10 }
   
   eqptProtGroupRowStatus OBJECT-TYPE
      SYNTAX RowStatus 
      ACCESS read-write
      STATUS mandatory
      DESCRIPTION
         "Entries in the eqptProtGroupTable can only be created at once, by   
          specifying eqptProtGroupRowStatus=createAndGo(4).
          For NT protection group, if all values are valid then the
          entry is made active(1). For LT protection group, if the group
          is in service then the entry is made active(1). If the group
          is not in service then the entry is made notInService(2).
          If the object is set to destroy(6), the entry is deleted.

          ALCATEL NOTE:
             SUPPORT: YES   INSRVMOD: NO for ISAM R3.3   RANGE: See above
             PERSIST: NO    DEFVALUE: active(1)          UNITS: -"
      ::= { eqptProtGroupEntry 11 }
   
   eqptProtElementTable OBJECT-TYPE
      SYNTAX SEQUENCE OF EqptProtElementEntry
      ACCESS not-accessible
      STATUS mandatory
      DESCRIPTION
         "A table representing the protected or protecting elements.
          An element can be either a board or an extension chain. Both are
          identified by the corresponding slot identifier (extension chain
          is identified by slot of corresponding NT board).
          This table has only two rows from ISAM R2.2 to R3.2.
          From R3.3 onwards, this table has a row for each slots in the
          main shelf.

          ALCATEL NOTE:
             SUPPORT: YES   TABLESIZE: DEP as described above "
      ::= { eqptProt 3 }
   
   eqptProtElementEntry OBJECT-TYPE
      SYNTAX EqptProtElementEntry
      ACCESS not-accessible
      STATUS mandatory
      DESCRIPTION
         "An entry of the eqptProtElementTable.

          ALCATEL NOTE:
             SUPPORT: YES"
      INDEX { eqptSlotId }
      ::= { eqptProtElementTable 1 }
   
   EqptProtElementEntry  ::= SEQUENCE {
      eqptProtElementGroupId               INTEGER,
      eqptProtElementType                  INTEGER,      
      eqptProtElementStandbyStatus         INTEGER,
      eqptProtElementRedcyCtrlStatus       INTEGER,
      eqptProtElementRowStatus             RowStatus,
      eqptProtElementStandbyStatuschangeReason INTEGER
   }
   
   eqptProtElementGroupId OBJECT-TYPE
      SYNTAX INTEGER
      ACCESS read-write
      STATUS mandatory
      DESCRIPTION
         "This attributes identifies the protection group to which this
          element belongs.

          ALCATEL NOTE:
             SUPPORT: YES   INSRVMOD: NO for ISAM R3.3   RANGE: See above
             PERSIST: YES   DEFVALUE: NA                 UNITS: -"
      ::= { eqptProtElementEntry 1}                       
   
   eqptProtElementType OBJECT-TYPE
      SYNTAX INTEGER {
         normal(1),
         spare(2)
      }
      ACCESS read-write
      STATUS mandatory
      DESCRIPTION
         "This attribute is used to distinguish between normal elements of
          a protection group and the spare element of a 1:N protection group.

          ALCATEL NOTE:
             SUPPORT: YES   INSRVMOD: NA          RANGE: 1..2
             PERSIST: YES   DEFVALUE: normal(1)   UNITS: -"
      ::= { eqptProtElementEntry 2}                      
                           
   eqptProtElementStandbyStatus OBJECT-TYPE
      SYNTAX INTEGER {
         providing-service(1),       
         hot-standby(2),             
         cold-standby(3),            
         idle(4)                     
      }
      ACCESS read-only
      STATUS mandatory
      DESCRIPTION
         "This attribute reflects the standby status of the protection
          group element.

          ALCATEL NOTE:
             SUPPORT: YES   INSRVMOD: NA   RANGE: 1..4
             PERSIST: NO    DEFVALUE: NA   UNITS: -"
      ::= { eqptProtElementEntry 3}
  
   eqptProtElementRedcyCtrlStatus OBJECT-TYPE
      SYNTAX INTEGER {
         normal(1),
         forced-active(2)
      }
      ACCESS read-write
      STATUS mandatory
      DESCRIPTION
         "This attribute is used to force a switchover between elements of
          a protection group or to keep one of the elements active.

          ALCATEL NOTE:
             SUPPORT: YES   INSRVMOD: YES         RANGE: 1..2
             PERSIST: YES   DEFVALUE: normal(1)   UNITS: -"
      ::= { eqptProtElementEntry 4}
                            
   eqptProtElementRowStatus OBJECT-TYPE
      SYNTAX RowStatus
      ACCESS read-write
      STATUS mandatory
      DESCRIPTION
         "Entries in the eqptProtElementTable can only be created at once,
          by specifying eqptProtEelementRowStatus=createAndGo(4). If all
          values are valid then the entry is made active(1). If the object
          is set to destroy(6), the entry is deleted.

          ALCATEL NOTE:
             SUPPORT: YES   INSRVMOD: NA          RANGE: See above
             PERSIST: NO    DEFVALUE: active(1)   UNITS: -"
      ::= { eqptProtElementEntry 5}

   eqptProtElementStandbyStatuschangeReason OBJECT-TYPE 
      SYNTAX INTEGER {
         none(0),                     
	                                  
         protectionGroupLocked(1),    
         forcedActive(2),             
         peerLinkUnAvailable(3),      
         peerLocked(4),               
         peerNotPlanned(5),           
         peerNotPluggedIn(6),         
         databaseNotInSync(7),        
         lanxDynamicDataNotSynced(8), 
         lanxSdkFailure(9),           
                                      
         lanxRecovSdkFailure(10),     
                                      
         lanxHwFailure(11),           
         lanxDynDataSyncFailure(12),  
                                      
         lanxStaticSyncFailure(13),   
                                      
         lanxPeerCommFailure(14),     
                                      
         lanxFailure(15),             
         linkGroupNotAvailable(16),   
         ltNotEnabled(17),            
         lanxHiGigFailure(18),        
                                      
         lanxReconcileFailure(19),    
                                      
         lanxDiscoveryFailure(20)     
                                      
   }
      ACCESS read-only
      STATUS mandatory
      DESCRIPTION
         "This attribute reflects the reason why the standby status of the protection group element has changed.
          ALCATEL NOTE:
             SUPPORT: YES   INSRVMOD: NA        RANGE: 0..17
             PERSIST: NO    DEFVALUE: none(0)   UNITS: -"
      ::= { eqptProtElementEntry 6}                           
                            
   eqptProfile OBJECT IDENTIFIER ::= { asamEquipmentMIB 6 }

   eqptProfileTable OBJECT-TYPE
      SYNTAX SEQUENCE OF EqptProfileEntry
      ACCESS not-accessible
      STATUS mandatory
      DESCRIPTION
         "A table holding the mapping between the profileId and the corresponding
          profile name.
          This table has a row for every profile in the system.

          ALCATEL NOTE:
             SUPPORT: YES   TABLESIZE: DEP as described above"
      ::=  { eqptProfile 1 }
   
   eqptProfileEntry OBJECT-TYPE
      SYNTAX EqptProfileEntry
      ACCESS not-accessible
      STATUS mandatory
      DESCRIPTION
         "An entry in the eqptProfileTable.

          ALCATEL NOTE:
             SUPPORT: YES"
      INDEX { eqptProfileId }
      ::=  { eqptProfileTable 1 }
   
   EqptProfileEntry ::= SEQUENCE {
      eqptProfileId                      AsamProfileIndex,
      eqptProfileName                    AsamProfileName,
      eqptProfileDescription             DisplayString
   }
    
   eqptProfileId OBJECT-TYPE
      SYNTAX AsamProfileIndex 
      ACCESS read-only
      STATUS mandatory
      DESCRIPTION
         "A value identifying a profile.

          ALCATEL NOTE:
             SUPPORT: YES   INSRVMOD: NA   RANGE: See above
             PERSIST: YES   DEFVALUE: NA   UNITS: -"
      ::= { eqptProfileEntry 1 }

   eqptProfileName OBJECT-TYPE
      SYNTAX AsamProfileName
      ACCESS read-only
      STATUS mandatory
      DESCRIPTION
         "The corresponding name for a given profile id.
          The name corresponding to the ProfileId must also be unique.

          ALCATEL NOTE:
             SUPPORT: YES   INSRVMOD: NA   RANGE: See above
             PERSIST: NO    DEFVALUE: NA   UNITS: -"
      ::= { eqptProfileEntry 2 }

   eqptProfileDescription OBJECT-TYPE
      SYNTAX DisplayString
      ACCESS read-only
      STATUS mandatory
      DESCRIPTION
         "A short description for the given profile, explaining the
          key attributes.

          ALCATEL NOTE:
             SUPPORT: YES   INSRVMOD: NA   RANGE: See above
             PERSIST: NO    DEFVALUE: NA   UNITS: -"
      ::= { eqptProfileEntry 3 }

   eqptProfileApplicabilityTable OBJECT-TYPE
      SYNTAX SEQUENCE OF EqptProfileApplicabilityEntry
      ACCESS not-accessible
      STATUS mandatory
      DESCRIPTION
         "This table lists for every defined profile in the system for
          which boards it is applicable.
          One profile can be applicable for multiple board types.
          Multiple profiles can be applicable for the same board type.

          ALCATEL NOTE:
             SUPPORT: YES   TABLESIZE: DEP as described above"
      ::=  { eqptProfile 2 }
   
   eqptProfileApplicabilityEntry OBJECT-TYPE
      SYNTAX EqptProfileApplicabilityEntry
      ACCESS not-accessible
      STATUS mandatory
      DESCRIPTION
         "An entry in the eqptProfileApplicabilityTable.

          ALCATEL NOTE:
             SUPPORT: YES"
      INDEX { eqptProfileId, eqptBoardType }
      ::=  { eqptProfileApplicabilityTable 1 }
   
   EqptProfileApplicabilityEntry ::= SEQUENCE {
      eqptBoardType                      DisplayString,
      eqptDefaultProfile                 TruthValue
   }
    
   eqptBoardType OBJECT-TYPE
      SYNTAX DisplayString    
      ACCESS read-only
      STATUS mandatory
      DESCRIPTION
         "A string representing the board for which the profile is applicable.

          ALCATEL NOTE:
             SUPPORT: YES   INSRVMOD: NA   RANGE: See above
             PERSIST: NO    DEFVALUE: NA   UNITS: -"
      ::= { eqptProfileApplicabilityEntry 1 }

   eqptDefaultProfile OBJECT-TYPE
      SYNTAX TruthValue    
      ACCESS read-only
      STATUS mandatory
      DESCRIPTION
         "A flag indicating if this is the default profile for a specific
          board type.

          ALCATEL NOTE:
             SUPPORT: YES   INSRVMOD: NA   RANGE: See above
             PERSIST: NO    DEFVALUE: NA   UNITS: -"
      ::= { eqptProfileApplicabilityEntry 2 }

   eqptTestChainTable   OBJECT-TYPE
      SYNTAX         SEQUENCE OF EqptTestChainEntry
      ACCESS         not-accessible
      STATUS         mandatory
      DESCRIPTION
        "A table contains the test chain configuration indicating
         which shelf is connected to the TAP_UP or whether an external
         test head is connected to the TAP_UP. This table has one row
         for each planned shelf.

         ALCATEL NOTE:
            TABLESIZE: DEP as described above"
      ::=  { asamEquipmentMIB 7 }
   
   eqptTestChainEntry   OBJECT-TYPE
      SYNTAX         EqptTestChainEntry
      ACCESS         not-accessible
      STATUS         mandatory
      DESCRIPTION
         "An entry in the eqptTestChainTable."

      INDEX { eqptHolderId }
      ::=  { eqptTestChainTable 1 }
   
   EqptTestChainEntry ::= SEQUENCE {
      eqptTestChainShelfToTapUp           INTEGER,
      eqptTestChainExtTestHeadToTapUp     INTEGER
   }
    
   eqptTestChainShelfToTapUp     OBJECT-TYPE
      SYNTAX                     INTEGER (0..255)
      ACCESS                     read-write
      STATUS                     mandatory
      DESCRIPTION
        "A unique value to identify a shelf position which is connected
         to the TAP_UP. The value '0' (default value) indicates that it
         is not connected. This parameter is used if
         eqptTestChainExtTestHeadToTapUp is set to '1' (i.e., 'no') and
         is ignored if eqptTestChainExtTestHeadToTapUp is set to '2'
         (i.e., 'yes').

         ALCATEL NOTE:
            ACCESS: NA     USAGE: OPT      PERSIST: YES     INSRVMOD: YES
            RANGE: DEP / 0 plus the range of eqptHolderId of the shelves. 
            DEFVALUE: 0 / this means that no shelf is configured to be 
               connected to the TAP_UP.
            UNITS: NA      SPARSE: NO      DESCR: NA "
       ::= { eqptTestChainEntry 1 }
   
    eqptTestChainExtTestHeadToTapUp       OBJECT-TYPE
       SYNTAX                         INTEGER {
                                          no (1),
                                          yes (2)
                                      } 
       ACCESS                         read-write
       STATUS                         mandatory
       DESCRIPTION
           "This parameter is used to indicate whether an external test
            head is connected to the TAP_UP. 
            no (1): no external test head is connected to the TAP_UP. 
            yes (2): an external test head is connected to the TAP_UP.
      
            ALCATEL NOTE:
                 ACCESS: NA         USAGE: OPT         PERSIST: YES
                 INSRVMOD: YES      RANGE: 1..2        DEFVALUE: 1
                 UNITS: NA          SPARSE: NO         DESCR: NA "
       ::= { eqptTestChainEntry 2 }

   eqptCustAlarmProfile OBJECT IDENTIFIER ::= { asamEquipmentMIB 8 }

   eqptCustAlarmProfileIndexNext OBJECT-TYPE
      SYNTAX AsamNextProfileIndex
      ACCESS read-only
      STATUS mandatory
      DESCRIPTION
           "This object contains an appropriate value to be used for
            eqptCustAlarmProfileIndex
            when creating entries in the associated profile table.
            The value 0 indicates that no unassigned entries are
            available. To obtain the profile index value for a new
            entry, the manager issues a management protocol retrieval
            operation to obtain the current value of this object.
            After each retrieval, the agent should modify the value to
            the next unassigned index."
    ::= { eqptCustAlarmProfile 1 }

   eqptCustAlarmProfileTable OBJECT-TYPE
      SYNTAX SEQUENCE OF EqptCustAlarmProfileEntry
      ACCESS not-accessible
      STATUS mandatory
      DESCRIPTION
         "A table representing the configurable attributes of the customizable  
          alarms : a description, and the corresponding Alarm Outputs to be
          activated when this alarm occurs.

          This table has a row for each external alarms profile.  It offers data
          for a maximum of 5 external alarms.  Alarms that are not defined for 
          a particular profile, need to contain default values in the fields 
          corresponding to that alarm number.  Independent of the alarm number,
          the name of the profile is also present, as well as the row status.  

          ALCATEL NOTE:
             SUPPORT: YES   TABLESIZE: DEP as described above"
      ::=  { eqptCustAlarmProfile 2}
   
   eqptCustAlarmProfileEntry OBJECT-TYPE
      SYNTAX EqptCustAlarmProfileEntry 
      ACCESS not-accessible 
      STATUS mandatory
      DESCRIPTION
         "An entry in the eqptCustAlarmProfileTable.

          ALCATEL NOTE:
             SUPPORT: YES"
      INDEX { eqptCustAlarmProfileIndex }
      ::=  { eqptCustAlarmProfileTable 1 }
   
   EqptCustAlarmProfileEntry ::= SEQUENCE {
      eqptCustAlarmProfileIndex                  AsamProfileIndex,
      eqptCustAlarmProfileName                   AsamProfileName,
      eqptCustAlarmProfileUsedStatus             AsamProfileRefCount,
      eqptCustAlarmProfileRowStatus              RowStatus,
      eqptCustAlarmProfileMnemonic1              DisplayString,
      eqptCustAlarmProfileDescription1           DisplayString,
      eqptCustAlarmProfileVisibleOutput1         EqptCustAlarmProfileOutputType,
      eqptCustAlarmProfileAudibleOutput1         EqptCustAlarmProfileOutputType,
      eqptCustAlarmProfilePolarity1              EqptCustAlarmProfilePolarityType,
      eqptCustAlarmProfileSeverity1              AsamAlarmSeverityType,
      eqptCustAlarmProfileMnemonic2              DisplayString,
      eqptCustAlarmProfileDescription2           DisplayString,
      eqptCustAlarmProfileVisibleOutput2         EqptCustAlarmProfileOutputType,
      eqptCustAlarmProfileAudibleOutput2         EqptCustAlarmProfileOutputType,
      eqptCustAlarmProfilePolarity2              EqptCustAlarmProfilePolarityType,
      eqptCustAlarmProfileSeverity2              AsamAlarmSeverityType,
      eqptCustAlarmProfileMnemonic3              DisplayString,
      eqptCustAlarmProfileDescription3           DisplayString,
      eqptCustAlarmProfileVisibleOutput3         EqptCustAlarmProfileOutputType,
      eqptCustAlarmProfileAudibleOutput3         EqptCustAlarmProfileOutputType,
      eqptCustAlarmProfilePolarity3              EqptCustAlarmProfilePolarityType,
      eqptCustAlarmProfileSeverity3              AsamAlarmSeverityType,
      eqptCustAlarmProfileMnemonic4              DisplayString,
      eqptCustAlarmProfileDescription4           DisplayString,
      eqptCustAlarmProfileVisibleOutput4         EqptCustAlarmProfileOutputType,
      eqptCustAlarmProfileAudibleOutput4         EqptCustAlarmProfileOutputType,
      eqptCustAlarmProfilePolarity4              EqptCustAlarmProfilePolarityType,
      eqptCustAlarmProfileSeverity4              AsamAlarmSeverityType,
      eqptCustAlarmProfileMnemonic5              DisplayString,
      eqptCustAlarmProfileDescription5           DisplayString,
      eqptCustAlarmProfileVisibleOutput5         EqptCustAlarmProfileOutputType,
      eqptCustAlarmProfileAudibleOutput5         EqptCustAlarmProfileOutputType,
      eqptCustAlarmProfilePolarity5              EqptCustAlarmProfilePolarityType,
      eqptCustAlarmProfileSeverity5              AsamAlarmSeverityType
   }
    
   eqptCustAlarmProfileIndex OBJECT-TYPE
      SYNTAX AsamProfileIndex
      ACCESS read-only
      STATUS mandatory
      DESCRIPTION
         "The Customizale Alarms Profile Index.

          ALCATEL NOTE:
             SUPPORT: YES   INSRVMOD: NA   RANGE: 1..20
             PERSIST: YES   DEFVALUE: NA   UNITS: -"
      ::= { eqptCustAlarmProfileEntry 1 }
 
  eqptCustAlarmProfileName OBJECT-TYPE
      SYNTAX AsamProfileName
      ACCESS read-write
      STATUS mandatory
      DESCRIPTION
         "A textual name uniquely identifying this profile.  
          
          Maximum length is 32, allowed characters A-Z, a-z, 0-9, '-'.  

          ALCATEL NOTE:
             SUPPORT: YES   INSRVMOD: NA   RANGE: See above
             PERSIST: YES   DEFVALUE: NA   UNITS: -"
      ::= { eqptCustAlarmProfileEntry 2 }
 
   eqptCustAlarmProfileUsedStatus OBJECT-TYPE
      SYNTAX AsamProfileRefCount
      ACCESS read-only
      STATUS mandatory
      DESCRIPTION
         "Indicates the number of entities using this profile.  If the 
          reference count is greater than 0, then this profile is 'in use',
          and may NOT be deleted.  If the value is 0, then this profile is
          'not in use', and can be deleted.  

          ALCATEL NOTE:
             SUPPORT: YES   INSRVMOD: NA   RANGE: See above
             PERSIST: YES   DEFVALUE: NA   UNITS: -"
      ::= { eqptCustAlarmProfileEntry 3 }

   eqptCustAlarmProfileRowStatus OBJECT-TYPE
      SYNTAX RowStatus
      ACCESS read-write
      STATUS mandatory
      DESCRIPTION
         "Entries in the eqptCustAlarmProfileTable can only be created at 
          once, by specifying eqptCustAlarmProfileRowStatus=createAndGo(4).  
          If all values are valid then the entry is made active(1). If the 
          object is set to destroy(6), the entry is deleted. 

          ALCATEL NOTE:
             SUPPORT: YES  INSRVMOD: NA          RANGE: See above
             PERSIST: NO   DEFVALUE: active(1)   UNITS: -"
      ::= { eqptCustAlarmProfileEntry 4 }
 
   eqptCustAlarmProfileMnemonic1 OBJECT-TYPE
      SYNTAX DisplayString (SIZE (0..16))
      ACCESS read-write
      STATUS mandatory
      DESCRIPTION
         "The mnemonic of the customizable alarm, for given Profile Index, 
          for external alarm number 1.

          Maximum length is 16, allowed characters A-Z.  

          ALCATEL NOTE:
             SUPPORT: NO    INSRVMOD: NA   RANGE: See above
             PERSIST: YES   DEFVALUE: 'UNDEF' UNITS: -"
      ::= { eqptCustAlarmProfileEntry 5 }

   eqptCustAlarmProfileDescription1 OBJECT-TYPE
      SYNTAX DisplayString (SIZE (0..40))
      ACCESS read-write
      STATUS mandatory
      DESCRIPTION
         "The description of the customizable alarm, for given 
          Profile Index, for external alarm number 1.

          Maximum length is 40.  

          ALCATEL NOTE:
             SUPPORT: YES   INSRVMOD: NA   RANGE: See above
             PERSIST: YES   DEFVALUE: 'Undefined' UNITS: -"
      ::= { eqptCustAlarmProfileEntry 6 }
 
   eqptCustAlarmProfileVisibleOutput1 OBJECT-TYPE
      SYNTAX EqptCustAlarmProfileOutputType
      ACCESS read-write
      STATUS mandatory
      DESCRIPTION
         "Shows whether or not to trigger the visible alarm output, 
          for given Profile Index, for external alarm number 1.

          ALCATEL NOTE:
             SUPPORT: YES   INSRVMOD: NA   RANGE: See above
             PERSIST: YES   DEFVALUE: notTriggered(2) UNITS: -"
      ::= { eqptCustAlarmProfileEntry 7 }

   eqptCustAlarmProfileAudibleOutput1 OBJECT-TYPE
      SYNTAX EqptCustAlarmProfileOutputType
      ACCESS read-write
      STATUS mandatory
      DESCRIPTION
         "Shows whether or not to trigger the audible alarm output,
          for given Profile Index, for external alarm number 1.

          ALCATEL NOTE:
             SUPPORT: YES   INSRVMOD: NA   RANGE: See above
             PERSIST: YES   DEFVALUE: notTriggered(2) UNITS: -"
      ::= { eqptCustAlarmProfileEntry 8 }
    
   eqptCustAlarmProfilePolarity1 OBJECT-TYPE
      SYNTAX EqptCustAlarmProfilePolarityType
      ACCESS read-write
      STATUS mandatory
      DESCRIPTION
         "Shows whether the alarm polarity is normal or inversed,
          for given Profile Index, for external alarm number 1.

          ALCATEL NOTE:
             SUPPORT: NO    INSRVMOD: NA   RANGE: See above
             PERSIST: YES   DEFVALUE: normal(2)   UNITS: -"
      ::= { eqptCustAlarmProfileEntry 9 }
    
   eqptCustAlarmProfileSeverity1 OBJECT-TYPE
      SYNTAX AsamAlarmSeverityType
      ACCESS read-write
      STATUS mandatory
      DESCRIPTION
         "Shows the severity of the alarm,
          for given Profile Index, for external alarm number 1.

          ALCATEL NOTE:
             SUPPORT: NO    INSRVMOD: NA   RANGE: See above
             PERSIST: YES   DEFVALUE: major(4) UNITS: -"
      ::= { eqptCustAlarmProfileEntry 10 }
    
   eqptCustAlarmProfileMnemonic2 OBJECT-TYPE
      SYNTAX DisplayString (SIZE (0..16))
      ACCESS read-write
      STATUS mandatory
      DESCRIPTION
         "The mnemonic of the customizable alarm, for given Profile Index, 
          for external alarm number 2.

          Maximum length is 16, allowed characters A-Z.  

          ALCATEL NOTE:
             SUPPORT: NO    INSRVMOD: NA   RANGE: See above
             PERSIST: YES   DEFVALUE: 'UNDEF' UNITS: -"
      ::= { eqptCustAlarmProfileEntry 11 }

   eqptCustAlarmProfileDescription2 OBJECT-TYPE
      SYNTAX DisplayString (SIZE (0..40))
      ACCESS read-write
      STATUS mandatory
      DESCRIPTION
         "The description of the customizable alarm, for given 
          Profile Index, for external alarm number 2.

          Maximum length is 40.  

          ALCATEL NOTE:
             SUPPORT: YES   INSRVMOD: NA   RANGE: See above
             PERSIST: YES   DEFVALUE: 'Undefined'   UNITS: -"
      ::= { eqptCustAlarmProfileEntry 12 }
 
   eqptCustAlarmProfileVisibleOutput2 OBJECT-TYPE
      SYNTAX EqptCustAlarmProfileOutputType
      ACCESS read-write
      STATUS mandatory
      DESCRIPTION
         "Shows whether or not to trigger the visible alarm output, 
          for given Profile Index, for external alarm number 2.

          ALCATEL NOTE:
             SUPPORT: YES   INSRVMOD: NA   RANGE: See above
             PERSIST: YES   DEFVALUE: notTriggered(2) UNITS: -"
      ::= { eqptCustAlarmProfileEntry 13 }

   eqptCustAlarmProfileAudibleOutput2 OBJECT-TYPE
      SYNTAX EqptCustAlarmProfileOutputType
      ACCESS read-write
      STATUS mandatory
      DESCRIPTION
         "Shows whether or not to trigger the audible alarm output,
          for given Profile Index, for external alarm number 2.

          ALCATEL NOTE:
             SUPPORT: YES   INSRVMOD: NA   RANGE: See above
             PERSIST: YES   DEFVALUE: notTriggered(2) UNITS: -"
      ::= { eqptCustAlarmProfileEntry 14 }
    
   eqptCustAlarmProfilePolarity2 OBJECT-TYPE
      SYNTAX EqptCustAlarmProfilePolarityType
      ACCESS read-write
      STATUS mandatory
      DESCRIPTION
         "Shows whether the alarm polarity is normal or inversed,
          for given Profile Index, for external alarm number 2.

          ALCATEL NOTE:
             SUPPORT: NO    INSRVMOD: NA   RANGE: See above
             PERSIST: YES   DEFVALUE: normal(2), UNITS: -"
      ::= { eqptCustAlarmProfileEntry 15 }
    
   eqptCustAlarmProfileSeverity2 OBJECT-TYPE
      SYNTAX AsamAlarmSeverityType
      ACCESS read-write
      STATUS mandatory
      DESCRIPTION
         "Shows the severity of the alarm,
          for given Profile Index, for external alarm number 2.

          ALCATEL NOTE:
             SUPPORT: NO    INSRVMOD: NA   RANGE: See above
             PERSIST: YES   DEFVALUE: major(4) UNITS: -"
      ::= { eqptCustAlarmProfileEntry 16 }
    
   eqptCustAlarmProfileMnemonic3 OBJECT-TYPE
      SYNTAX DisplayString (SIZE (0..16))
      ACCESS read-write
      STATUS mandatory
      DESCRIPTION
         "The mnemonic of the customizable alarm, for given Profile Index, 
          for external alarm number 3.

          Maximum length is 16, allowed characters A-Z.  

          ALCATEL NOTE:
             SUPPORT: NO    INSRVMOD: NA   RANGE: See above
             PERSIST: YES   DEFVALUE: 'UNDEF' UNITS: -"
      ::= { eqptCustAlarmProfileEntry 17 }

   eqptCustAlarmProfileDescription3 OBJECT-TYPE
      SYNTAX DisplayString (SIZE (0..40))
      ACCESS read-write
      STATUS mandatory
      DESCRIPTION
         "The description of the customizable alarm, for given 
          Profile Index, for external alarm number 3.

          Maximum length is 40.  

          ALCATEL NOTE:
             SUPPORT: YES   INSRVMOD: NA   RANGE: See above
             PERSIST: YES   DEFVALUE: 'Undefined' UNITS: -"
      ::= { eqptCustAlarmProfileEntry 18 }
 
   eqptCustAlarmProfileVisibleOutput3 OBJECT-TYPE
      SYNTAX EqptCustAlarmProfileOutputType
      ACCESS read-write
      STATUS mandatory
      DESCRIPTION
         "Shows whether or not to trigger the visible alarm output, 
          for given Profile Index, for external alarm number 3.

          ALCATEL NOTE:
             SUPPORT: YES   INSRVMOD: NA   RANGE: See above
             PERSIST: YES   DEFVALUE: notTriggered(2) UNITS: -"
      ::= { eqptCustAlarmProfileEntry 19 }

   eqptCustAlarmProfileAudibleOutput3 OBJECT-TYPE
      SYNTAX EqptCustAlarmProfileOutputType
      ACCESS read-write
      STATUS mandatory
      DESCRIPTION
         "Shows whether or not to trigger the audible alarm output,
          for given Profile Index, for external alarm number 3.

          ALCATEL NOTE:
             SUPPORT: YES   INSRVMOD: NA   RANGE: See above
             PERSIST: YES   DEFVALUE: notTriggered(2) UNITS: -"
      ::= { eqptCustAlarmProfileEntry 20 }
    
   eqptCustAlarmProfilePolarity3 OBJECT-TYPE
      SYNTAX EqptCustAlarmProfilePolarityType
      ACCESS read-write
      STATUS mandatory
      DESCRIPTION
         "Shows whether the alarm polarity is normal or inversed,
          for given Profile Index, for external alarm number 3.

          ALCATEL NOTE:
             SUPPORT: NO    INSRVMOD: NA   RANGE: See above
             PERSIST: YES   DEFVALUE: normal(2) UNITS: -"
      ::= { eqptCustAlarmProfileEntry 21 }
    
   eqptCustAlarmProfileSeverity3 OBJECT-TYPE
      SYNTAX AsamAlarmSeverityType
      ACCESS read-write
      STATUS mandatory
      DESCRIPTION
         "Shows the severity of the alarm,
          for given Profile Index, for external alarm number 3.

          ALCATEL NOTE:
             SUPPORT: NO    INSRVMOD: NA   RANGE: See above
             PERSIST: YES   DEFVALUE: major(4) UNITS: -"
      ::= { eqptCustAlarmProfileEntry 22 }
    
   eqptCustAlarmProfileMnemonic4 OBJECT-TYPE
      SYNTAX DisplayString (SIZE (0..16))
      ACCESS read-write
      STATUS mandatory
      DESCRIPTION
         "The mnemonic of the customizable alarm, for given Profile Index, 
          for external alarm number 4.

          Maximum length is 16, allowed characters A-Z.  

          ALCATEL NOTE:
             SUPPORT: NO    INSRVMOD: NA   RANGE: See above
             PERSIST: YES   DEFVALUE: 'UNDEF' UNITS: -"
      ::= { eqptCustAlarmProfileEntry 23 }

   eqptCustAlarmProfileDescription4 OBJECT-TYPE
      SYNTAX DisplayString (SIZE (0..40))
      ACCESS read-write
      STATUS mandatory
      DESCRIPTION
         "The description of the customizable alarm, for given 
          Profile Index, for external alarm number 4.

          Maximum length is 40.  

          ALCATEL NOTE:
             SUPPORT: YES   INSRVMOD: NA   RANGE: See above
             PERSIST: YES   DEFVALUE: 'Undefined' UNITS: -"
      ::= { eqptCustAlarmProfileEntry 24 }
 
   eqptCustAlarmProfileVisibleOutput4 OBJECT-TYPE
      SYNTAX EqptCustAlarmProfileOutputType
      ACCESS read-write
      STATUS mandatory
      DESCRIPTION
         "Shows whether or not to trigger the visible alarm output, 
          for given Profile Index, for external alarm number 4.

          ALCATEL NOTE:
             SUPPORT: YES   INSRVMOD: NA   RANGE: See above
             PERSIST: YES   DEFVALUE: notTriggered(2) UNITS: -"
      ::= { eqptCustAlarmProfileEntry 25 }

   eqptCustAlarmProfileAudibleOutput4 OBJECT-TYPE
      SYNTAX EqptCustAlarmProfileOutputType
      ACCESS read-write
      STATUS mandatory
      DESCRIPTION
         "Shows whether or not to trigger the audible alarm output,
          for given Profile Index, for external alarm number 4.

          ALCATEL NOTE:
             SUPPORT: YES   INSRVMOD: NA   RANGE: See above
             PERSIST: YES   DEFVALUE: notTriggered(2) UNITS: -"
      ::= { eqptCustAlarmProfileEntry 26 }
    
   eqptCustAlarmProfilePolarity4 OBJECT-TYPE
      SYNTAX EqptCustAlarmProfilePolarityType
      ACCESS read-write
      STATUS mandatory
      DESCRIPTION
         "Shows whether the alarm polarity is normal or inversed,
          for given Profile Index, for external alarm number 4.

          ALCATEL NOTE:
             SUPPORT: NO    INSRVMOD: NA   RANGE: See above
             PERSIST: YES   DEFVALUE: normal(2) UNITS: -"
      ::= { eqptCustAlarmProfileEntry 27 }
    
   eqptCustAlarmProfileSeverity4 OBJECT-TYPE
      SYNTAX AsamAlarmSeverityType
      ACCESS read-write
      STATUS mandatory
      DESCRIPTION
         "Shows the severity of the alarm,
          for given Profile Index, for external alarm number 4.

          ALCATEL NOTE:
             SUPPORT: NO    INSRVMOD: NA   RANGE: See above
             PERSIST: YES   DEFVALUE: major(4) UNITS: -"
      ::= { eqptCustAlarmProfileEntry 28 }
    
   eqptCustAlarmProfileMnemonic5 OBJECT-TYPE
      SYNTAX DisplayString (SIZE (0..16))
      ACCESS read-write
      STATUS mandatory
      DESCRIPTION
         "The mnemonic of the customizable alarm, for given Profile Index, 
          for external alarm number 5.

          Maximum length is 16, allowed characters A-Z.  

          ALCATEL NOTE:
             SUPPORT: NO    INSRVMOD: NA   RANGE: See above
             PERSIST: YES   DEFVALUE: 'UNDEF' UNITS: -"
      ::= { eqptCustAlarmProfileEntry 29 }

   eqptCustAlarmProfileDescription5 OBJECT-TYPE
      SYNTAX DisplayString (SIZE (0..40))
      ACCESS read-write
      STATUS mandatory
      DESCRIPTION
         "The description of the customizable alarm, for given 
          Profile Index, for external alarm number 5.

          Maximum length is 40.  

          ALCATEL NOTE:
             SUPPORT: YES   INSRVMOD: NA   RANGE: See above
             PERSIST: YES   DEFVALUE: 'Undefined' UNITS: -"
      ::= { eqptCustAlarmProfileEntry 30 }
 
   eqptCustAlarmProfileVisibleOutput5 OBJECT-TYPE
      SYNTAX EqptCustAlarmProfileOutputType
      ACCESS read-write
      STATUS mandatory
      DESCRIPTION
         "Shows whether or not to trigger the visible alarm output, 
          for given Profile Index, for external alarm number 5.

          ALCATEL NOTE:
             SUPPORT: YES   INSRVMOD: NA   RANGE: See above
             PERSIST: YES   DEFVALUE: notTriggered(2) UNITS: -"
      ::= { eqptCustAlarmProfileEntry 31 }

   eqptCustAlarmProfileAudibleOutput5 OBJECT-TYPE
      SYNTAX EqptCustAlarmProfileOutputType
      ACCESS read-write
      STATUS mandatory
      DESCRIPTION
         "Shows whether or not to trigger the audible alarm output,
          for given Profile Index, for external alarm number 5.

          ALCATEL NOTE:
             SUPPORT: YES   INSRVMOD: NA   RANGE: See above
             PERSIST: YES   DEFVALUE: notTriggered(2) UNITS: -"
      ::= { eqptCustAlarmProfileEntry 32 }
    
   eqptCustAlarmProfilePolarity5 OBJECT-TYPE
      SYNTAX EqptCustAlarmProfilePolarityType
      ACCESS read-write
      STATUS mandatory
      DESCRIPTION
         "Shows whether the alarm polarity is normal or inversed,
          for given Profile Index, for external alarm number 5.

          ALCATEL NOTE:
             SUPPORT: NO    INSRVMOD: NA   RANGE: See above
             PERSIST: YES   DEFVALUE: normal(2) UNITS: -"
      ::= { eqptCustAlarmProfileEntry 33 }
    
   eqptCustAlarmProfileSeverity5 OBJECT-TYPE
      SYNTAX AsamAlarmSeverityType
      ACCESS read-write
      STATUS mandatory
      DESCRIPTION
         "Shows the severity of the alarm,
          for given Profile Index, for external alarm number 5.

          ALCATEL NOTE:
             SUPPORT: NO    INSRVMOD: NA   RANGE: See above
             PERSIST: YES   DEFVALUE: major(4) UNITS: -"
      ::= { eqptCustAlarmProfileEntry 34 }
    
   eqptCustAlarmProfileMappingTable OBJECT-TYPE
      SYNTAX     SEQUENCE OF EqptCustAlarmProfileMappingEntry
      ACCESS     not-accessible
      STATUS     mandatory
      DESCRIPTION
            "The table listing the profile name to profile Index
            Mapping." 
      ::= { eqptCustAlarmProfile 3}

   eqptCustAlarmProfileMappingEntry OBJECT-TYPE
      SYNTAX     EqptCustAlarmProfileMappingEntry
      ACCESS     not-accessible
      STATUS     mandatory
      DESCRIPTION
            "An entry (conceptual row) representing the Customizable Alarm Profile
             Name to Index mapping.  The system automatically creates an entry in
             this table for each corresponding entry (custAlarm-profile) created
             in the eqptCustAlarmProfileTable.  Similarly, when a profile is 
             deleted, the corresponding entry in this table is also automatically
             deleted by the system."
          INDEX {eqptCustAlarmProfileMappingName }
        ::= {eqptCustAlarmProfileMappingTable 1}

   EqptCustAlarmProfileMappingEntry ::= SEQUENCE {
      eqptCustAlarmProfileMappingName                  AsamProfileName,
      eqptCustAlarmProfileMappingIndex                 AsamProfileIndex
   }
   
   eqptCustAlarmProfileMappingName OBJECT-TYPE
      SYNTAX AsamProfileName
      ACCESS not-accessible
      STATUS mandatory
      DESCRIPTION
         "A textual name uniquely identifying this profile.  
          This name has to be unique within the assigned scope.  

          Maximum length is 32, allowed characters A-Z, a-z, 0-9, '-'.  

          ALCATEL NOTE:
             SUPPORT: YES   INSRVMOD: NA   RANGE: See above
             PERSIST: YES   DEFVALUE: NA   UNITS: -"
      ::= { eqptCustAlarmProfileMappingEntry 1 }
 
   eqptCustAlarmProfileMappingIndex OBJECT-TYPE
      SYNTAX AsamProfileIndex
      ACCESS read-only
      STATUS mandatory
      DESCRIPTION
         "The Customizale Alarms Profile Index.

          ALCATEL NOTE:
             SUPPORT: YES   INSRVMOD: NA   RANGE: 1..20
             PERSIST: YES   DEFVALUE: NA   UNITS: -"
      ::= { eqptCustAlarmProfileMappingEntry 2 }

   eqptMtaTest OBJECT IDENTIFIER ::= { asamEquipmentMIB 9 }
   eqptMtaTestHeadType OBJECT-TYPE
	SYNTAX INTEGER {
                         four-wire(1),
                         two-wire(2)
		      }
	ACCESS read-write
	STATUS mandatory
	DESCRIPTION
           "setting the MTA test head type, four-wire mode or two-wire mode. 
           This object should be consistent with external test head equipment, 
           MTA subsystem will operate different relays based on this object. 
           MTA commands will have differentiation between these two mode.

           ALCATEL NOTE:
              ACCESS: NA         USAGE: OPT         PERSIST: YES
              INSRVMOD: YES      RANGE: 1..2        DEFVALUE: 1
              UNITS: NA          SPARSE: NO         DESCR: NA"
        ::= { eqptMtaTest 1 }
       
   eqptBoardThermalSensorTable OBJECT-TYPE
    SYNTAX SEQUENCE OF EqptBoardThermalSensorEntry
    ACCESS not-accessible
    STATUS mandatory
    DESCRIPTION
	           "A table representing the actual value and thresholds of Thermal Sensor(s) on boards. 
	           One entry corresponds to each sensor on board. 
	           The entries are presented only when the board is plugged in, operationally up, has thermal sensors on it, and when operator put a read request for it.

	           ALCATEL NOTE:
	           SUPPORT: YES	TABLESIZE: DEP as described above"
	        ::= { asamEquipmentMIB 10 }	

   eqptBoardThermalSensorEntry OBJECT-TYPE
	  SYNTAX EqptBoardThermalSensorEntry
	  ACCESS not-accessible
	  STATUS mandatory
	  DESCRIPTION
	           "An entry of the equipment thermal sensor table on boards

	           ALCATEL NOTE:
		         SUPPORT: YES"
             INDEX {eqptSlotId, eqptBoardThermalSensorId}
          ::= {eqptBoardThermalSensorTable 1}

   EqptBoardThermalSensorEntry ::= SEQUENCE{
		eqptBoardThermalSensorId			INTEGER,
		eqptBoardThermalSensorActualTemperature		INTEGER,
		eqptBoardThermalSensorTcaThresholdLow		INTEGER,
		eqptBoardThermalSensorTcaThresholdHigh		INTEGER,
		eqptBoardThermalSensorShutdownThresholdLow	INTEGER,
		eqptBoardThermalSensorShutdownThresholdHigh	INTEGER
		}

  eqptBoardThermalSensorId OBJECT-TYPE
	 SYNTAX INTEGER
	 ACCESS read-only
	 STATUS mandatory
	 DESCRIPTION
	          "Index of thermal sensors on board.

	          ALCATEL NOTE:
	          SUPPORT: YES   INSRVMOD: NA	   RANGE: 1..8
	          PERSIST: NO    DEFVALUE: NA         UNITS: - "
	       ::= { eqptBoardThermalSensorEntry 1}

   eqptBoardThermalSensorActualTemperature OBJECT-TYPE
	  SYNTAX INTEGER
	  ACCESS read-only
	  STATUS mandatory
	  DESCRIPTION
	          "Actual Temperature value read from thermal sensor on board.

	          ALCATEL NOTE:
	          SUPPORT: YES   INSRVMOD: NA	   RANGE: -40..150
	          PERSIST: NO    DEFVALUE: NA         UNITS: degree Celsius"
	       ::={ eqptBoardThermalSensorEntry 2}

   eqptBoardThermalSensorTcaThresholdLow	OBJECT-TYPE
	  SYNTAX INTEGER
	  ACCESS read-only
	  STATUS mandatory
	  DESCRIPTION
	           "Low Tca threshold of thermal sensor on Board
            
	           ALCATEL NOTE:
	           SUPPORT: YES   INSRVMOD: NA	   RANGE: NA
	           PERSIST: NO    DEFVALUE: NA         UNITS: degree Celsius"
	        ::= { eqptBoardThermalSensorEntry 3}   

   eqptBoardThermalSensorTcaThresholdHigh	OBJECT-TYPE
	  SYNTAX INTEGER
	  ACCESS read-only
	  STATUS mandatory
	  DESCRIPTION
	           "High Tca threshold of thermal sensor on Board
            
	           ALCATEL NOTE:
	           SUPPORT: YES   INSRVMOD: NA	   RANGE: NA
	           PERSIST: NO    DEFVALUE: NA         UNITS: degree Celsius"
	       ::={ eqptBoardThermalSensorEntry 4}  

   eqptBoardThermalSensorShutdownThresholdLow	OBJECT-TYPE
	  SYNTAX INTEGER
	  ACCESS read-only
	  STATUS mandatory
	  DESCRIPTION
	           "Low Shutdown threshold of thermal sensor on Board
            
	           ALCATEL NOTE:
	           SUPPORT: YES   INSRVMOD: NA	   RANGE: NA
	           PERSIST: NO    DEFVALUE: NA         UNITS: degree Celsius"
	       ::={ eqptBoardThermalSensorEntry 5} 

   eqptBoardThermalSensorShutdownThresholdHigh	OBJECT-TYPE
	  SYNTAX INTEGER
	  ACCESS read-only
	  STATUS mandatory
	  DESCRIPTION
	           "High Shutdown threshold of thermal sensor on Board
            
	           ALCATEL NOTE:
	           SUPPORT: YES   INSRVMOD: NA	   RANGE: NA
	           PERSIST: NO    DEFVALUE: NA         UNITS: degree Celsius"
	       ::={ eqptBoardThermalSensorEntry 6}
   
   eqptPortMappingTable OBJECT-TYPE
      SYNTAX SEQUENCE OF EqptPortMappingEntry
      ACCESS not-accessible
      STATUS mandatory
      DESCRIPTION
         "Equipment PortMapping table, showing the mapping between logical ports
          and physical ports (faceplate numbering).

          This table contains one row per logical port on the xHUB.

          ALCATEL NOTE:
             SUPPORT: YES  TABLESIZE: DEP as described above"
      ::= { asamEquipmentMIB 13 }

   eqptPortMappingEntry OBJECT-TYPE
      SYNTAX EqptPortMappingEntry
      ACCESS not-accessible
      STATUS mandatory
      DESCRIPTION
         "An entry of the equipment PortMapping table.

          ALCATEL NOTE:
             SUPPORT: YES"
      INDEX { eqptPortMappingLogPortNbr }
      ::= { eqptPortMappingTable 1 }

   EqptPortMappingEntry ::= SEQUENCE {
      eqptPortMappingLogPortNbr            EqptPortMappingIndex,
      eqptPortMappingLogPortType           INTEGER,
      eqptPortMappingPhyPortSlot           EqptSlotIndex,
      eqptPortMappingPhyPortType           INTEGER,
      eqptPortMappingPhyPortNbr            INTEGER,
      eqptPortMappingLSMSlot               EqptSlotIndex,
      eqptPortMappingChanges             Counter
   }

   eqptPortMappingLogPortNbr OBJECT-TYPE
      SYNTAX EqptPortMappingIndex
      ACCESS not-accessible
      STATUS mandatory
      DESCRIPTION
         "Index in equipment PortMapping Table: corresponds to the logical
          port id on the xHUB.

          ALCATEL NOTE:
             SUPPORT: YES   INSRVMOD: NA   RANGE: See above
             PERSIST: NO    DEFVALUE: NA   UNITS: -"
      ::= { eqptPortMappingEntry 1 }

   eqptPortMappingLogPortType OBJECT-TYPE
      SYNTAX INTEGER {
          uplink (1),    
          downlink (2),  
          hostlink (3)   
      }
      ACCESS read-only
      STATUS mandatory
      DESCRIPTION
         "The logical port type corresponds to the link classification.
         
          ALCATEL NOTE:
             SUPPORT: YES   INSRVMOD: NA   RANGE: 1..3
             PERSIST: NO    DEFVALUE: NA   UNITS: -"
      ::= { eqptPortMappingEntry 2 }

   eqptPortMappingPhyPortSlot OBJECT-TYPE
      SYNTAX EqptSlotIndex
      ACCESS read-only
      STATUS mandatory
      DESCRIPTION
         "The equipment slot index of the physical port.
          This slot will point to either a NT or NTIO slot position.

          This field is not applicable for hostlinks, in which case it gets
          the value 0xFFFF

          ALCATEL NOTE:
             SUPPORT: YES   INSRVMOD: NA   RANGE: See above
             PERSIST: NO    DEFVALUE: 0    UNITS: -"
      ::= { eqptPortMappingEntry 3 }

   eqptPortMappingPhyPortType OBJECT-TYPE
      SYNTAX INTEGER {
         not-applicable(1),
         sfp(2),
         xfp(3),
         vp(5),
         eth(10),
         mcast(11)
      }
      ACCESS read-only
      STATUS mandatory
      DESCRIPTION
         "The physcial port type.

          This field is not applicable for hostlinks.
   
          ALCATEL NOTE:
             SUPPORT: YES   INSRVMOD: NA   RANGE: 1..3,5, 10,11
             PERSIST: NO    DEFVALUE: 0    UNITS: -"
      ::= { eqptPortMappingEntry 4 }

   eqptPortMappingPhyPortNbr OBJECT-TYPE
      SYNTAX INTEGER
      ACCESS read-only
      STATUS mandatory
      DESCRIPTION
         "The pysical port number, which corresponds to the faceplate number
          of the sfp/xfp port.

          This field is not applicable for hostlinks, in which case it gets
          the value 0xFF.

          ALCATEL NOTE:
             SUPPORT: YES   INSRVMOD: NA   RANGE: See above
             PERSIST: NO    DEFVALUE: 0    UNITS: -"
      ::= { eqptPortMappingEntry 5 }

   eqptPortMappingLSMSlot OBJECT-TYPE
      SYNTAX EqptSlotIndex
      ACCESS read-only
      STATUS mandatory
      DESCRIPTION
         "The equipment slot index of the corresponding LSM slot.
         
          This field is only applicable for hostlinks, and downlinks to which
          a remote LSM slot is assigned. In other cases it gets the value
          0xFFFF.
         
          ALCATEL NOTE:
             SUPPORT: YES   INSRVMOD: NA   RANGE: See above
             PERSIST: NO    DEFVALUE: 0    UNITS: -"
      ::= { eqptPortMappingEntry 6 }

	eqptPortMappingChanges OBJECT-TYPE
      SYNTAX Counter
      ACCESS read-only
      STATUS mandatory
      DESCRIPTION
         "This counter represents the number of PortMapping configuration changes per row. It is a wraparound counter between 0 and MAX.
         ALCATEL NOTE:
             SUPPORT: YES   INSRVMOD: NA   RANGE: 0-MAX
             PERSIST: NO    DEFVALUE: 0    UNITS: -"      
        ::= { eqptPortMappingEntry 7}
      
       eqptPortMappingGlobalChangeCounter OBJECT-TYPE
    	SYNTAX Counter
      ACCESS read-only
      STATUS mandatory
      DESCRIPTION
         "This counter represents the number of global PortMapping configuration changes. It is a wraparound counter between 0 and MAX.
            SUPPORT: YES   INSRVMOD: NA   RANGE: 0-MAX
             PERSIST: NO    DEFVALUE: 0    UNITS: -"      
      ::= { asamEquipmentMIB 14 }

END
