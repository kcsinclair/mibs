OMNI-gx2EA1000-MIB DEFINITIONS ::= BEGIN

    IMPORTS
	IpAddress, TimeTicks            
					      FROM RFC1155-SMI
	OBJECT-TYPE                     
					      FROM RFC-1212
	sysUpTime, DisplayString        
					      FROM RFC1213-MIB
	TRAP-TYPE                       
					      FROM RFC-1215
	gi, motproxies                   
					      FROM NLS-BBNIDENT-MIB
	gx2Ea1000
					      FROM GX2HFC-MIB

	trapIdentifier,trapNetworkElemModelNumber,
	trapNetworkElemSerialNum, trapPerceivedSeverity,
	trapNetworkElemOperState, trapNetworkElemAlarmStatus,
	trapNetworkElemAdminState, trapNetworkElemAvailStatus,
	trapText, trapNETrapLastTrapTimeStamp, trapChangedObjectId,
	trapChangedValueInteger, trapChangedValueDisplayString
					      FROM NLSBBN-TRAPS-MIB;



	       -- This MIB module uses the extended OBJECT-TYPE macro as
	       -- defined in RFC1212 and the TRAP-TYPE macro as defined
	       -- in RFC 1215.
		
		   --REVISION	"0" April 26, 2011

		   --DESCRIPTION
		   --			Added revision and description comment section


		--    OMNISTAR EM1000 Laser Module (1550nM Forward Path Transmetter)  MIB MODULE

	-- This MIB module defines information for management of HFC networks
		-- 
		-- The MIB module assumes that all generic (static) network element
		-- information is defined in a different module such as the HFC module
		-- The MIB consists of two groups:
		-- the device type descriptor subgroup and 
		-- gx2Ea1000E Network Elements subgroup.
		-- The device type descriptor subgroup is used to define 
		-- parameters specific to gx2Ea1000E device type.
		-- These parameters are common across all network elements
		-- from gx2Ea1000 device type.
		--
		-- The gx2Ea1000 Network Elements subgroup is
		-- a list of gx2Ea1000 type elements in the
		-- current network topology with nominal
		-- and current parameter values for the
		-- individual network elements; the individual
		-- network elements are identified by  
		-- index from hfcCommonTable.
		-- That implies what hfcCommonTableIndex and
		-- gx2Ea1000TableIndex are equal for each individual
		-- network element.
		-- This table is an extension of the hfcCommonTable
		-- for all elements of gx2Ea1000 type.
		--
		-- Both groups are mandatory for management of gx2Ea1000 devices.

-- ****************************************************************************
		--
		-- All floating point numbers will be represented by an IEEE 32 Bit number.
		-- Conversion of this number must be done on the user interface to view the 
		-- actual floating point number. The Floating point number 10,000,000 will 
		-- be used as an out of range or un-used limit indicator. It will be in the 
		-- 32 bit hex representation of the IEE number as follows:  0x501502F9

		Float ::= Counter  -- UNSIGNED (32 BITS) 

-- ****************************************************************************

		-- gx2Ea1000 Device Descriptor subgroup.

		-- The device type descriptor subgroup is used to define 
		-- parameters specific to gx2Ea1000 device type.
		-- These parameters are common across all network elements
		-- from gx2Ea1000 device type.


		gx2ea1000Descriptor OBJECT IDENTIFIER ::= {gx2Ea1000 1}



--*****************************************************************************
		--              gx2Ea1000 Table
		
		-- Contains a list of all gx2Ea1000 type devices in
		-- the network. Each device is characterized with
		-- current network topology information, with nominal
		-- and current parameter values for the
		-- individual network elements;
		--
		-- The individual network elements indentified by  
		-- index from hfcCommonTable.
		-- That implies what hfcCommonTableIndex and
		-- gx2ea1000TableIndex are equal for each individual
		-- nettwork element.
		-- This table should be used as an extension of the hfcCommonTable
		-- for all elements of gx2Ea1000 type.


	       gx2ea1000AnalogTable                    OBJECT-TYPE
			 SYNTAX             SEQUENCE OF Gx2ea1000AnalogEntry
			 ACCESS             not-accessible
			 STATUS             mandatory
			 DESCRIPTION
			 "This table contains gx2Ea1000 specific parameters with
			  nominal and current values."
			 ::= { gx2Ea1000 2 }


	       gx2ea1000AnalogEntry               OBJECT-TYPE
			 SYNTAX             Gx2ea1000AnalogEntry
			 ACCESS             not-accessible
			 STATUS             mandatory
			 DESCRIPTION
			 "This list contains the analog parameters and descriptions."
			 INDEX { gx2ea1000AnalogTableIndex }
			 ::= { gx2ea1000AnalogTable  1}

--***********************************************************************
	       gx2ea1000DigitalTable                    OBJECT-TYPE
			 SYNTAX             SEQUENCE OF Gx2ea1000DigitalEntry
			 ACCESS             not-accessible
			 STATUS             mandatory
			 DESCRIPTION
			 "This table contains gx2Ea1000 specific parameters with
			  nominal and current values."
			 ::= { gx2Ea1000 3 }

	       gx2ea1000DigitalEntry               OBJECT-TYPE
			 SYNTAX             Gx2ea1000DigitalEntry
			 ACCESS             not-accessible
			 STATUS             mandatory
			 DESCRIPTION
			 "This list contains digital parameters and descriptions."
			 INDEX { gx2ea1000DigitalTableIndex }
			 ::= { gx2ea1000DigitalTable  2}

--***********************************************************************
	       gx2ea1000StatusTable                    OBJECT-TYPE
			 SYNTAX             SEQUENCE OF Gx2ea1000StatusEntry
			 ACCESS             not-accessible
			 STATUS             mandatory
			 DESCRIPTION
			 "This table contains gx2Ea1000 specific parameters with
			  nominal and current values."
			 ::= { gx2Ea1000 4 }

	       gx2ea1000StatusEntry               OBJECT-TYPE
			 SYNTAX             Gx2ea1000StatusEntry
			 ACCESS             not-accessible
			 STATUS             mandatory
			 DESCRIPTION
			 "This list contains Status parameters and descriptions."
			 INDEX { gx2ea1000StatusTableIndex }
			 ::= { gx2ea1000StatusTable  3}

--***********************************************************************
	       gx2ea1000FactoryTable                    OBJECT-TYPE
			 SYNTAX             SEQUENCE OF Gx2ea1000FactoryEntry
			 ACCESS             not-accessible
			 STATUS             mandatory
			 DESCRIPTION
			 "This table contains gx2Ea1000 specific parameters with
			  nominal and current values."
			 ::= { gx2Ea1000 5 }

	       gx2ea1000FactoryEntry               OBJECT-TYPE
			 SYNTAX             Gx2ea1000FactoryEntry
			 ACCESS             not-accessible
			 STATUS             mandatory
			 DESCRIPTION
			 "This list contains Factory parameters and descriptions."
			 INDEX { gx2ea1000FactoryTableIndex }
			 ::= { gx2ea1000FactoryTable  4}


		-- ****************  Analog Parameters ***********************

	      Gx2ea1000AnalogEntry    ::= SEQUENCE  
	       {
		gx2ea1000AnalogTableIndex      		INTEGER,
		
		ea1000labelOffsetNomMonitor 		DisplayString (SIZE (0..80)),
		ea1000uomOffsetNomMonitor			DisplayString (SIZE (0..80)),
		ea1000majorHighOffsetNomMonitor		Float, 
		ea1000majorLowOffsetNomMonitor		Float, 
		ea1000minorHighOffsetNomMonitor		Float,
		ea1000minorLowOffsetNomMonitor		Float, 
		ea1000currentValueOffsetNomMonitor	Float, 
		ea1000stateFlagOffsetNomMonitor		INTEGER,
		ea1000minValueOffsetNomMonitor		Float,
		ea1000maxValueOffsetNomMonitor 		Float,
		ea1000alarmStateOffsetNomMonitor	INTEGER,

		ea1000labelOffsetNomCnt 			DisplayString (SIZE (0..80)),
		ea1000uomOffsetNomCnt				DisplayString (SIZE (0..80)),
		ea1000majorHighOffsetNomCnt			Float, 
		ea1000majorLowOffsetNomCnt			Float, 
		ea1000minorHighOffsetNomCnt			Float,
		ea1000minorLowOffsetNomCnt			Float, 
		ea1000currentValueOffsetNomCnt		Float, 
		ea1000stateFlagOffsetNomCnt			INTEGER,
		ea1000minValueOffsetNomCnt			Float,
		ea1000maxValueOffsetNomCnt 			Float,
		ea1000alarmStateOffsetNomCnt		INTEGER,

		ea1000labelOptPower					DisplayString (SIZE (0..80)),
		ea1000uomOptPower					DisplayString (SIZE (0..80)),
		ea1000majorHighOptPower				Float, 
		ea1000majorLowOptPower				Float, 
		ea1000minorHighOptPower				Float,
		ea1000minorLowOptPower				Float, 
		ea1000currentValueOptPower			Float, 
		ea1000stateFlagOptPower				INTEGER,
		ea1000minValueOptPower				Float,
		ea1000maxValueOptPower 				Float,
		ea1000alarmStateOptPower			INTEGER,

		ea1000labelLaserTemp				DisplayString (SIZE (0..80)),
		ea1000uomLaserTemp					DisplayString (SIZE (0..80)),
		ea1000majorHighLaserTemp			Float, 
		ea1000majorLowLaserTemp				Float, 
		ea1000minorHighLaserTemp			Float,
		ea1000minorLowLaserTemp				Float, 
		ea1000currentValueLaserTemp			Float, 
		ea1000stateFlagLaserTemp			INTEGER,
		ea1000minValueLaserTemp				Float,
		ea1000maxValueLaserTemp				Float,
		ea1000alarmStateLaserTemp			INTEGER,

		ea1000labelLaserBias				DisplayString (SIZE (0..80)),
		ea1000uomLaserBias					DisplayString (SIZE (0..80)),
		ea1000majorHighLaserBias			Float, 
		ea1000majorLowLaserBias				Float, 
		ea1000minorHighLaserBias			Float,
		ea1000minorLowLaserBias				Float, 
		ea1000currentValueLaserBias			Float, 
		ea1000stateFlagLaserBias			INTEGER,
		ea1000minValueLaserBias				Float,
		ea1000maxValueLaserBias 			Float,
		ea1000alarmStateLaserBias			INTEGER,

		ea1000labelTecCurrent				DisplayString (SIZE (0..80)),
		ea1000uomTecCurrent					DisplayString (SIZE (0..80)),
		ea1000majorHighTecCurrent			Float, 
		ea1000majorLowTecCurrent			Float, 
		ea1000minorHighTecCurrent			Float,
		ea1000minorLowTecCurrent			Float, 
		ea1000currentValueTecCurrent		Float, 
		ea1000stateFlagTecCurrent			INTEGER,
		ea1000minValueTecCurrent			Float,
		ea1000maxValueTecCurrent 			Float,
		ea1000alarmStateTecCurrent			INTEGER,

		ea1000labelModuleTemp				DisplayString (SIZE (0..80)),
		ea1000uomModuleTemp					DisplayString (SIZE (0..80)),
		ea1000majorHighModuleTemp			Float, 
		ea1000majorLowModuleTemp			Float, 
		ea1000minorHighModuleTemp			Float,
		ea1000minorLowModuleTemp			Float, 
		ea1000currentValueModuleTemp		Float, 
		ea1000stateFlagModuleTemp			INTEGER,
		ea1000minValueModuleTemp			Float,
		ea1000maxValueModuleTemp			Float,
		ea1000alarmStateModuleTemp			INTEGER,

		ea1000labelFan1Speed				DisplayString (SIZE (0..80)),
		ea1000uomFan1Speed					DisplayString (SIZE (0..80)),
		ea1000majorHighFan1Speed			Float, 
		ea1000majorLowFan1Speed				Float, 
		ea1000minorHighFan1Speed			Float,
		ea1000minorLowFan1Speed				Float, 
		ea1000currentValueFan1Speed			Float, 
		ea1000stateFlagFan1Speed			INTEGER,
		ea1000minValueFan1Speed				Float,
		ea1000maxValueFan1Speed 			Float,
		ea1000alarmStateFan1Speed			INTEGER,

		ea1000labelFan2Speed				DisplayString (SIZE (0..80)),
		ea1000uomFan2Speed					DisplayString (SIZE (0..80)),
		ea1000majorHighFan2Speed			Float, 
		ea1000majorLowFan2Speed				Float, 
		ea1000minorHighFan2Speed			Float,
		ea1000minorLowFan2Speed				Float, 
		ea1000currentValueFan2Speed			Float, 
		ea1000stateFlagFan2Speed			INTEGER,
		ea1000minValueFan2Speed				Float,
		ea1000maxValueFan2Speed 			Float,
		ea1000alarmStateFan2Speed			INTEGER,

		ea1000label12Volt					DisplayString (SIZE (0..80)),
		ea1000uom12Volt						DisplayString (SIZE (0..80)),
		ea1000majorHigh12Volt				Float, 
		ea1000majorLow12Volt				Float, 
		ea1000minorHigh12Volt				Float,
		ea1000minorLow12Volt				Float, 
		ea1000currentValue12Volt			Float, 
		ea1000stateFlag12Volt				INTEGER,
		ea1000minValue12Volt				Float,
		ea1000maxValue12Volt				Float,
		ea1000alarmState12Volt				INTEGER
		}

		-- ****************  Digital Parameters ***********************
      Gx2ea1000DigitalEntry    ::= SEQUENCE  
      {
		gx2ea1000DigitalTableIndex         INTEGER,

		ea1000labelRfInput					DisplayString (SIZE (0..80)),
		ea1000enumRfInput					DisplayString (SIZE (0..80)),
		ea1000valueRfInput					INTEGER,
		ea1000stateflagRfInput  			INTEGER,

		ea1000labelOptOutput				DisplayString (SIZE (0..80)),
		ea1000enumOptOutput					DisplayString (SIZE (0..80)),
		ea1000valueOptOutput				INTEGER,
		ea1000stateflagOptOutput         	INTEGER,

		ea1000labelLaserMode				DisplayString (SIZE (0..80)),
		ea1000enumLaserMode					DisplayString (SIZE (0..80)),
		ea1000valueLaserMode				INTEGER,
		ea1000stateflagLaserMode         	INTEGER,

		ea1000labelAttenSetting 			DisplayString (SIZE (0..80)),
		ea1000enumAttenSetting				DisplayString (SIZE (0..80)),
		ea1000valueAttenSetting				INTEGER, 
		ea1000stateflagAttenSetting			INTEGER,

		ea1000labelLaserSecMode				DisplayString (SIZE (0..80)),
		ea1000enumLaserSecMode				DisplayString (SIZE (0..80)),
		ea1000valueLaserSecMode				INTEGER,
		ea1000stateflagLaserSecMode     	INTEGER,

		ea1000labelVideoOffset				DisplayString (SIZE (0..80)),
		ea1000enumVideoOffset				DisplayString (SIZE (0..80)),
		ea1000valueVideoOffset				INTEGER,
		ea1000stateflagVideoOffset         	INTEGER,

		ea1000labelFactoryDefault			DisplayString (SIZE (0..80)),
		ea1000enumFactoryDefault			DisplayString (SIZE (0..80)),
		ea1000valueFactoryDefault			INTEGER,
		ea1000stateflagFactoryDefault   	INTEGER

		}

		-- ****************  Status Parameters ************************************
      Gx2ea1000StatusEntry    ::= SEQUENCE  
      {
		gx2ea1000StatusTableIndex        	INTEGER,

		ea1000labelBoot						DisplayString (SIZE (0..80)),
		ea1000valueBoot						INTEGER,
		ea1000stateflagBoot					INTEGER,
		
		ea1000labelFlash					DisplayString (SIZE (0..80)),
		ea1000valueFlash					INTEGER,
		ea1000stateflagFlash				INTEGER,

		ea1000labelFactoryDataCRC 			DisplayString (SIZE (0..80)),
		ea1000valueFactoryDataCRC			INTEGER,
		ea1000stateflagFactoryDataCRC		INTEGER,

		ea1000labelLaserDataCRC 			DisplayString (SIZE (0..80)),
		ea1000valueLaserDataCRC 			INTEGER,
		ea1000stateflagLaserDataCRC 		INTEGER,

		ea1000labelAlarmDataCrc				DisplayString (SIZE (0..80)),
		ea1000valueAlarmDataCrc				INTEGER,
		ea1000stateflagAlarmDataCrc			INTEGER,

		ea1000labelRFInputStatus			DisplayString (SIZE (0..80)),
		ea1000valueRFInputStatus			INTEGER,
		ea1000stateflagRFInputStatus		INTEGER
		}


		-- ****************  Factory Parameters *************************************
      Gx2ea1000FactoryEntry   ::= SEQUENCE  
      {
		gx2ea1000FactoryTableIndex         	INTEGER,
		ea1000bootControlByteValue  		INTEGER,
		ea1000bootStatusByteValue   		INTEGER,
		ea1000bank1CRCValue    				INTEGER,
		ea1000bank2CRCValue    				INTEGER,
		ea1000prgEEPROMByteValue    		INTEGER,
		ea1000factoryCRCValue    			INTEGER,
		ea1000calculateCRCValue    			INTEGER,
		ea1000hourMeterValue    			INTEGER,
		ea1000flashPrgCntAValue    			INTEGER,
		ea1000flashPrgCntBValue    			INTEGER,
		ea1000flashBankARevValue    		DisplayString (SIZE (0..80)),
		ea1000flashBankBRevValue    		DisplayString (SIZE (0..80))
		}

            -- ************** Analog Parameters ****************************
		gx2ea1000AnalogTableIndex        	OBJECT-TYPE
			   SYNTAX           			INTEGER (1..4294967295)
			   ACCESS           			read-only
			   STATUS           			mandatory
			   DESCRIPTION
			   "The value of this object identifies the network
			    element. This index is equal to the
			    hfcCommonTableIndex for the same element."
			   ::= { gx2ea1000AnalogEntry 1}
-- New Parameter

		ea1000labelOffsetNomMonitor     	OBJECT-TYPE
			   SYNTAX           			DisplayString (SIZE (0..80))
			   ACCESS           			read-only
			   STATUS           			optional
			   DESCRIPTION
			   "The value of this object provides the label of the
			    Offset Monitor Analog parameter."
			   ::= { gx2ea1000AnalogEntry 2}

		ea1000uomOffsetNomMonitor       	OBJECT-TYPE
			   SYNTAX           			DisplayString (SIZE (0..80))
			   ACCESS           			read-only
			   STATUS           			optional
			   DESCRIPTION
			   "The value of this object provides the Unit of Measure of the
			    Offset Monitor Analog parameter."
			   ::= { gx2ea1000AnalogEntry 3}

		ea1000majorHighOffsetNomMonitor 	OBJECT-TYPE
			   SYNTAX           			Float 
			   ACCESS           			read-only
			   STATUS           			mandatory
			   DESCRIPTION
			   "The value of this object provides the Major High alarm value
			    of the Offset Monitor Analog parameter.
			   This value is a floating point number that is represented as an IEEE 32 bit number."
			   ::= { gx2ea1000AnalogEntry 4}


		ea1000majorLowOffsetNomMonitor  OBJECT-TYPE
			   SYNTAX           Float 
			   ACCESS           read-only
			   STATUS           mandatory
			   DESCRIPTION
			   "The value of this object provides the Major Low alarm value
			    of the Offset Monitor Analog parameter.
			    This value is a floating point number that is represented as an IEEE 32 bit number."
			   ::= { gx2ea1000AnalogEntry 5}

		ea1000minorHighOffsetNomMonitor OBJECT-TYPE
			   SYNTAX           Float
			   ACCESS           read-only
			   STATUS           mandatory
			   DESCRIPTION
			   "The value of this object provides the Minor High alarm value
			    of the Offset Monitor Analog parameter.
			   This value is a float and is represented as an IEEE 32 bit number."
			   ::= { gx2ea1000AnalogEntry 6}

		ea1000minorLowOffsetNomMonitor  OBJECT-TYPE
			   SYNTAX           Float 
			   ACCESS           read-only
			   STATUS           mandatory
			   DESCRIPTION
			   "The value of this object provides the Minor Low alarm value
			    of the Offset Monitor Analog parameter.
			   This value is a float and is represented as an IEEE 32 bit number."
			   ::= { gx2ea1000AnalogEntry 7}

		ea1000currentValueOffsetNomMonitor  OBJECT-TYPE
			   SYNTAX           Float 
			   ACCESS           read-only
			   STATUS           mandatory
			   DESCRIPTION
			   "The value of this object provides the Current value
			    of the Offset Monitor Analog parameter.
			   This value is a float and is represented as an IEEE 32 bit number."
			   ::= { gx2ea1000AnalogEntry 8}

		ea1000stateFlagOffsetNomMonitor  OBJECT-TYPE
			   SYNTAX           INTEGER
								{
								hidden(1),
								read-only(2),
								updateable(3)
								}
			   ACCESS           read-only
			   STATUS           mandatory
			   DESCRIPTION
			   "The value of this object provides the state
			    of the Offset Monitor Analog parameter. (0-Hidden	
			          1-Read-Only, 2-Updateable)"
			   ::= { gx2ea1000AnalogEntry 9}

		ea1000minValueOffsetNomMonitor  OBJECT-TYPE
			   SYNTAX           Float
			   ACCESS           read-only
			   STATUS           mandatory
			   DESCRIPTION
			   "The value of this object provides the minimum value
			    the Offset Monitor Analog parameter can achive.
			   This value is a float and is represented as an IEEE 32 bit number."
			   ::= { gx2ea1000AnalogEntry 10}

		ea1000maxValueOffsetNomMonitor  OBJECT-TYPE
			   SYNTAX           Float
			   ACCESS           read-only
			   STATUS           mandatory
			   DESCRIPTION
			   "The value of this object provides the maximum value
			    the Offset Monitor Analog parameter can achive.
			   This value is a float and is represented as an IEEE 32 bit number."
			   ::= { gx2ea1000AnalogEntry 11}

		ea1000alarmStateOffsetNomMonitor  OBJECT-TYPE
			   SYNTAX           INTEGER
									{
									noAlarm(1),
									majorLowAlarm(2),
									minorLowAlarm(3),
									minorHighAlarm(4),
									majorHighAlarm(5),
									informational(6)
									}
			   ACCESS           read-only
			   STATUS           mandatory
			   DESCRIPTION
			   "The value of this object provides the curent alarm state of
			    the Offset Monitor Analog parameter."
			   ::= { gx2ea1000AnalogEntry 12}

-- New Parameter

		ea1000labelOffsetNomCnt         OBJECT-TYPE
			   SYNTAX           DisplayString (SIZE (0..80))
			   ACCESS           read-only
			   STATUS           optional
			   DESCRIPTION
			   "The value of this object provides the label of the
			    Offset Control Analog parameter."
			   ::= { gx2ea1000AnalogEntry 13}

		ea1000uomOffsetNomCnt           OBJECT-TYPE
			   SYNTAX           DisplayString (SIZE (0..80))
			   ACCESS           read-only
			   STATUS           optional
			   DESCRIPTION
			   "The value of this object provides the label of the
			    Offset Control Analog parameter."
			   ::= { gx2ea1000AnalogEntry 14}

		ea1000majorHighOffsetNomCnt     OBJECT-TYPE
			   SYNTAX           Float 
			   ACCESS           read-only
			   STATUS           optional
			   DESCRIPTION
			   "The value of this object provides the Major High alarm value
			    of the Offset Control Analog parameter.
			   This value is a float and is represented as an IEEE 32 bit number. 
			   In this version of the Firmware and MIB this Parameter is not used and is 
			   optional. All reads will return the Unused Parameter (10,000,000)"
			   ::= { gx2ea1000AnalogEntry 15}


		ea1000majorLowOffsetNomCnt      OBJECT-TYPE
			   SYNTAX           Float 
			   ACCESS           read-only
			   STATUS           optional
			   DESCRIPTION
			   "The value of this object provides the Major Low alarm value
			    of the Offset Control Analog parameter.
			   This value is a float and is represented as an IEEE 32 bit number.
			   In this version of the Firmware and MIB this Parameter is not used and is 
			   optional. All reads will return the Unused Parameter (10,000,000)"
			   ::= { gx2ea1000AnalogEntry 16}

		ea1000minorHighOffsetNomCnt     OBJECT-TYPE
			   SYNTAX           Float
			   ACCESS           read-only
			   STATUS           optional
			   DESCRIPTION
			   "The value of this object provides the Minor High alarm value
			    of the Offset Control Analog parameter.
			   This value is a floating point number that is represented as an IEEE 32 bit number.
   			   In this version of the Firmware and MIB this Parameter is not used and is 
			   optional. All reads will return the Unused Parameter (10,000,000)"

			   ::= { gx2ea1000AnalogEntry 17}

		ea1000minorLowOffsetNomCnt      OBJECT-TYPE
			   SYNTAX           Float 
			   ACCESS           read-only
			   STATUS           optional
			   DESCRIPTION
			   "The value of this object provides the Minor Low alarm value
			    of the Offset Control Analog parameter.
			   This value is a floating point number that is represented as an IEEE 32 bit number.
			   In this version of the Firmware and MIB this Parameter is not used and is 
			   optional. All reads will return the Unused Parameter (10,000,000)"
			   ::= { gx2ea1000AnalogEntry 18}

		ea1000currentValueOffsetNomCnt  OBJECT-TYPE
			   SYNTAX			Float
			   ACCESS           read-write
			   STATUS           mandatory
			   DESCRIPTION
			   "The value of this object provides the Current value
			    of the Offset Control Analog parameter.
			   This value is a floating point number that is represented as an IEEE 32 bit number."
			   ::= { gx2ea1000AnalogEntry 19}

		ea1000stateFlagOffsetNomCnt     OBJECT-TYPE
			   SYNTAX           INTEGER
								{
								hidden(1),
								read-only(2),
								updateable(3)
								}
			   ACCESS           read-only
			   STATUS           mandatory
			   DESCRIPTION
			   "The value of this object provides the state
			    of the Offset Control Analog parameter. (0-Hidden	
			          1-Read-Only, 2-Updateable)"
			   ::= { gx2ea1000AnalogEntry 20}

		ea1000minValueOffsetNomCnt      OBJECT-TYPE
			   SYNTAX           Float
			   ACCESS           read-only
			   STATUS           mandatory
			   DESCRIPTION
			   "The value of this object provides the minimum value
			    the Offset Control Analog parameter can achive.
			   This value is a floating point number that is represented as an IEEE 32 bit number."
			   ::= { gx2ea1000AnalogEntry 21}

		ea1000maxValueOffsetNomCnt      OBJECT-TYPE
			   SYNTAX           Float
			   ACCESS           read-only
			   STATUS           mandatory
			   DESCRIPTION
			   "The value of this object provides the maximum value
			    the Offset Control Analog parameter can achive.
			   This value is a floating point number that is represented as an IEEE 32 bit number."
			   ::= { gx2ea1000AnalogEntry 22}

		ea1000alarmStateOffsetNomCnt    OBJECT-TYPE
			   SYNTAX           INTEGER
									{
									noAlarm(1),
									majorLowAlarm(2),
									minorLowAlarm(3),
									minorHighAlarm(4),
									majorHighAlarm(5),
									informational(6)
									}
			   ACCESS           read-only
			   STATUS           mandatory
			   DESCRIPTION
			   "The value of this object provides the curent alarm state of
			    the Offset Control Analog parameter."
			   ::= { gx2ea1000AnalogEntry 23}

-- New Parameter

		ea1000labelOptPower             OBJECT-TYPE
			   SYNTAX           DisplayString (SIZE (0..80))
			   ACCESS           read-only
			   STATUS           optional
			   DESCRIPTION
			   "The value of this object provides the label of the
			    Optical Power Analog parameter."
			   ::= { gx2ea1000AnalogEntry 24}

		ea1000uomOptPower               OBJECT-TYPE
			   SYNTAX           DisplayString (SIZE (0..80))
			   ACCESS           read-only
			   STATUS           optional
			   DESCRIPTION
			   "The value of this object provides the Unit of Measure of the
			    Optical Power Analog parameter."
			   ::= { gx2ea1000AnalogEntry 25}

		ea1000majorHighOptPower         OBJECT-TYPE
			   SYNTAX           Float 
			   ACCESS           read-only
			   STATUS           mandatory
			   DESCRIPTION
			   "The value of this object provides the Major High alarm value
			    of the Optical Power Analog parameter.
			   This value is a floating point number that is represented as an IEEE 32 bit number."
			   ::= { gx2ea1000AnalogEntry 26}


		ea1000majorLowOptPower          OBJECT-TYPE
			   SYNTAX           Float 
			   ACCESS           read-only
			   STATUS           mandatory
			   DESCRIPTION
			   "The value of this object provides the Major Low alarm value
			    of the Optical Power Analog parameter.
			   This value is a floating point number that is represented as an IEEE 32 bit number."
			   ::= { gx2ea1000AnalogEntry 27}

		ea1000minorHighOptPower         OBJECT-TYPE
			   SYNTAX           Float
			   ACCESS           read-only
			   STATUS           optional
			   DESCRIPTION
			   "The value of this object provides the Minor High alarm value
			    of the Optical Power Analog parameter.
			   This value is a floating point number that is represented as an IEEE 32 bit number.
			   In this version of the Firmware and MIB this Parameter is not used and is 
			   optional. All reads will return the Unused Parameter (10,000,000)"
			   ::= { gx2ea1000AnalogEntry 28}

		ea1000minorLowOptPower          OBJECT-TYPE
			   SYNTAX           Float 
			   ACCESS           read-only
			   STATUS           optional
			   DESCRIPTION
			   "The value of this object provides the Minor Low alarm value
			    of the Optical Power Analog parameter.
			   This value is a floating point number that is represented as an IEEE 32 bit number.
			   In this version of the Firmware and MIB this Parameter is not used and is 
			   optional. All reads will return the Unused Parameter (10,000,000)"
			   ::= { gx2ea1000AnalogEntry 29}

		ea1000currentValueOptPower      OBJECT-TYPE
			   SYNTAX           Float 
			   ACCESS           read-only
			   STATUS           mandatory
			   DESCRIPTION
			   "The value of this object provides the Current value
			    of the Optical Power Analog parameter.
			   This value is a floating point number that is represented as an IEEE 32 bit number."
			   ::= { gx2ea1000AnalogEntry 30}

		ea1000stateFlagOptPower         OBJECT-TYPE
			   SYNTAX           INTEGER
								{
								hidden(1),
								read-only(2),
								updateable(3)
								}
			   ACCESS           read-only
			   STATUS           mandatory
			   DESCRIPTION
			   "The value of this object provides the state
			    of the Optical Power Analog parameter. (0-Hidden	
			          1-Read-Only, 2-Updateable)."
			   ::= { gx2ea1000AnalogEntry 31}

		ea1000minValueOptPower          OBJECT-TYPE
			   SYNTAX           Float
			   ACCESS           read-only
			   STATUS           mandatory
			   DESCRIPTION
			   "The value of this object provides the minimum value
			    the Optical Power Analog parameter can achive.
			   This value is a floating point number that is represented as an IEEE 32 bit number."
			   ::= { gx2ea1000AnalogEntry 32}

		ea1000maxValueOptPower          OBJECT-TYPE
			   SYNTAX           Float
			   ACCESS           read-only
			   STATUS           mandatory
			   DESCRIPTION
			   "The value of this object provides the maximum value
			    the Optical Power Analog parameter can achive.
			   This value is a floating point number that is represented as an IEEE 32 bit number."
			   ::= { gx2ea1000AnalogEntry 33}

		ea1000alarmStateOptPower        OBJECT-TYPE
			   SYNTAX           INTEGER
									{
									noAlarm(1),
									majorLowAlarm(2),
									minorLowAlarm(3),
									minorHighAlarm(4),
									majorHighAlarm(5),
									informational(6)
									}
			   ACCESS           read-only
			   STATUS           mandatory
			   DESCRIPTION
			   "The value of this object provides the curent alarm state of
			    the Optical Power Analog parameter."
			   ::= { gx2ea1000AnalogEntry 34}

-- New Parameter

		ea1000labelLaserTemp            OBJECT-TYPE
			   SYNTAX           DisplayString (SIZE (0..80))
			   ACCESS           read-only
			   STATUS           optional
			   DESCRIPTION
			   "The value of this object provides the label of the
			    Laser Temperature Analog parameter."
			   ::= { gx2ea1000AnalogEntry 35}

		ea1000uomLaserTemp              OBJECT-TYPE
			   SYNTAX           DisplayString (SIZE (0..80))
			   ACCESS           read-only
			   STATUS           optional
			   DESCRIPTION
			   "The value of this object provides the Unit of Measure of the
			    Laser Temperature Analog parameter."
			   ::= { gx2ea1000AnalogEntry 36}

		ea1000majorHighLaserTemp        OBJECT-TYPE
			   SYNTAX           Float 
			   ACCESS           read-only
			   STATUS           mandatory
			   DESCRIPTION
			   "The value of this object provides the Major High alarm value
			    of the Laser Temperature Analog parameter.
			   This value is a floating point number that is represented as an IEEE 32 bit number."
			   ::= { gx2ea1000AnalogEntry 37}


		ea1000majorLowLaserTemp         OBJECT-TYPE
			   SYNTAX           Float 
			   ACCESS           read-only
			   STATUS           mandatory
			   DESCRIPTION
			   "The value of this object provides the Major Low alarm value
			    of the Laser Temperature Analog parameter.
			   This value is a floating point number that is represented as an IEEE 32 bit number."
			   ::= { gx2ea1000AnalogEntry 38}

		ea1000minorHighLaserTemp        OBJECT-TYPE
			   SYNTAX           Float
			   ACCESS           read-only
			   STATUS           mandatory
			   DESCRIPTION
			   "The value of this object provides the Minor High alarm value
			    of the Laser Temperature Analog parameter.
			   This value is a floating point number that is represented as an IEEE 32 bit number."
			   ::= { gx2ea1000AnalogEntry 39}

		ea1000minorLowLaserTemp         OBJECT-TYPE
			   SYNTAX           Float 
			   ACCESS           read-only
			   STATUS           mandatory
			   DESCRIPTION
			   "The value of this object provides the Minor Low alarm value
			    of the Laser Temperature Analog parameter.
			   This value is a floating point number that is represented as an IEEE 32 bit number."
			   ::= { gx2ea1000AnalogEntry 40}

		ea1000currentValueLaserTemp     OBJECT-TYPE
			   SYNTAX           Float 
			   ACCESS           read-only
			   STATUS           mandatory
			   DESCRIPTION
			   "The value of this object provides the Current value
			    of the Laser Temperature Analog parameter.
			   This value is a floating point number that is represented as an IEEE 32 bit number."
			   ::= { gx2ea1000AnalogEntry 41}

		ea1000stateFlagLaserTemp        OBJECT-TYPE
			   SYNTAX           INTEGER
								{
								hidden(1),
								read-only(2),
								updateable(3)
								}
			   ACCESS           read-only
			   STATUS           mandatory
			   DESCRIPTION
			   "The value of this object provides the state
			    of the Laser Temperature Analog parameter. (0-Hidden	
			          1-Read-Only, 2-Updateable)."
			   ::= { gx2ea1000AnalogEntry 42}

		ea1000minValueLaserTemp         OBJECT-TYPE
			   SYNTAX           Float
			   ACCESS           read-only
			   STATUS           mandatory
			   DESCRIPTION
			   "The value of this object provides the minimum value
			    the Laser Temperature Analog parameter can achive.
			   This value is a floating point number that is represented as an IEEE 32 bit number."
			   ::= { gx2ea1000AnalogEntry 43}

		ea1000maxValueLaserTemp         OBJECT-TYPE
			   SYNTAX           Float
			   ACCESS           read-only
			   STATUS           mandatory
			   DESCRIPTION
			   "The value of this object provides the maximum value
			    the Laser Temperature Analog parameter can achive.
			   This value is a floating point number that is represented as an IEEE 32 bit number."
			   ::= { gx2ea1000AnalogEntry 44}

		ea1000alarmStateLaserTemp       OBJECT-TYPE
			   SYNTAX           INTEGER
									{
									noAlarm(1),
									majorLowAlarm(2),
									minorLowAlarm(3),
									minorHighAlarm(4),
									majorHighAlarm(5),
									informational(6)
									}
			   ACCESS           read-only
			   STATUS           mandatory
			   DESCRIPTION
			   "The value of this object provides the curent alarm state of
			    the Laser Temperature Analog parameter."
			   ::= { gx2ea1000AnalogEntry 45}

-- New Parameter

		ea1000labelLaserBias            OBJECT-TYPE
			   SYNTAX           DisplayString (SIZE (0..80))
			   ACCESS           read-only
			   STATUS           optional
			   DESCRIPTION
			   "The value of this object provides the label of the
			    Laser Bias Current Analog parameter."
			   ::= { gx2ea1000AnalogEntry 46}

		ea1000uomLaserBias              OBJECT-TYPE
			   SYNTAX           DisplayString (SIZE (0..80))
			   ACCESS           read-only
			   STATUS           optional
			   DESCRIPTION
			   "The value of this object provides the Unit of Measure of the
			    Laser Bias Analog parameter."
			   ::= { gx2ea1000AnalogEntry 47}

		ea1000majorHighLaserBias        OBJECT-TYPE
			   SYNTAX           Float 
			   ACCESS           read-only
			   STATUS           mandatory
			   DESCRIPTION
			   "The value of this object provides the Major High alarm value
			    of the Laser Bias Analog parameter.
			   This value is a floating point number that is represented as an IEEE 32 bit number."
			   ::= { gx2ea1000AnalogEntry 48}


		ea1000majorLowLaserBias         OBJECT-TYPE
			   SYNTAX           Float 
			   ACCESS           read-only
			   STATUS           mandatory
			   DESCRIPTION
			   "The value of this object provides the Major Low alarm value
			    of the Laser Bias Analog parameter.
			   This value is a floating point number that is represented as an IEEE 32 bit number."
			   ::= { gx2ea1000AnalogEntry 49}

		ea1000minorHighLaserBias        OBJECT-TYPE
			   SYNTAX           Float
			   ACCESS           read-only
			   STATUS           optional
			   DESCRIPTION
			   "The value of this object provides the Minor High alarm value
			    of the Laser Bias Analog parameter.
			   This value is a floating point number that is represented as an IEEE 32 bit number.
			   In this version of the Firmware and MIB this Parameter is not used and is 
			   optional. All reads will return the Unused Parameter (10,000,000)"
			   ::= { gx2ea1000AnalogEntry 50}

		ea1000minorLowLaserBias         OBJECT-TYPE
			   SYNTAX           Float 
			   ACCESS           read-only
			   STATUS           optional
			   DESCRIPTION
			   "The value of this object provides the Minor Low alarm value
			    of the Laser Bias Analog parameter.
			   This value is a floating point number that is represented as an IEEE 32 bit number.
			   In this version of the Firmware and MIB this Parameter is not used and is 
			   optional. All reads will return the Unused Parameter (10,000,000)"
			   ::= { gx2ea1000AnalogEntry 51}

		ea1000currentValueLaserBias     OBJECT-TYPE
			   SYNTAX           Float 
			   ACCESS           read-only
			   STATUS           mandatory
			   DESCRIPTION
			   "The value of this object provides the Current value
			    of the Laser Bias Analog parameter.
			   This value is a floating point number that is represented as an IEEE 32 bit number."
			   ::= { gx2ea1000AnalogEntry 52}

		ea1000stateFlagLaserBias        OBJECT-TYPE
			   SYNTAX           INTEGER
								{
								hidden(1),
								read-only(2),
								updateable(3)
								}
			   ACCESS           read-only
			   STATUS           mandatory
			   DESCRIPTION
			   "The value of this object provides the state
			    of the Laser Bias Analog parameter. (0-Hidden	
			          1-Read-Only, 2-Updateable)."
			   ::= { gx2ea1000AnalogEntry 53}

		ea1000minValueLaserBias         OBJECT-TYPE
			   SYNTAX           Float
			   ACCESS           read-only
			   STATUS           mandatory
			   DESCRIPTION
			   "The value of this object provides the minimum value
			    the Laser Bias Analog parameter can achive.
			   This value is a floating point number that is represented as an IEEE 32 bit number."
			   ::= { gx2ea1000AnalogEntry 54}

		ea1000maxValueLaserBias         OBJECT-TYPE
			   SYNTAX           Float
			   ACCESS           read-only
			   STATUS           mandatory
			   DESCRIPTION
			   "The value of this object provides the maximum value
			    the Laser Bias Analog parameter can achive.
   			   This value is a floating point number that is represented as an IEEE 32 bit number."
			   ::= { gx2ea1000AnalogEntry 55}

		ea1000alarmStateLaserBias       OBJECT-TYPE
			   SYNTAX           INTEGER
									{
									noAlarm(1),
									majorLowAlarm(2),
									minorLowAlarm(3),
									minorHighAlarm(4),
									majorHighAlarm(5),
									informational(6)
									}
			   ACCESS           read-only
			   STATUS           mandatory
			   DESCRIPTION
			   "The value of this object provides the curent alarm state of
			    the Laser Bias Analog parameter."
			   ::= { gx2ea1000AnalogEntry 56}
-- New Parameter

		ea1000labelTecCurrent           OBJECT-TYPE
			   SYNTAX           DisplayString (SIZE (0..80))
			   ACCESS           read-only
			   STATUS           optional
			   DESCRIPTION
			   "The value of this object provides the label of the
			    TEC Current Analog parameter."
			   ::= { gx2ea1000AnalogEntry 57}

		ea1000uomTecCurrent             OBJECT-TYPE
			   SYNTAX           DisplayString (SIZE (0..80))
			   ACCESS           read-only
			   STATUS           optional
			   DESCRIPTION
			   "The value of this object provides the Unit of Measure of the
			    TEC Current Analog parameter.."
			   ::= { gx2ea1000AnalogEntry 58}

		ea1000majorHighTecCurrent       OBJECT-TYPE
			   SYNTAX           Float 
			   ACCESS           read-only
			   STATUS           mandatory
			   DESCRIPTION
			   "The value of this object provides the Major High alarm value
			    of the TEC Current Analog parameter.
			   This value is a floating point number that is represented as an IEEE 32 bit number."
			   ::= { gx2ea1000AnalogEntry 59}


		ea1000majorLowTecCurrent        OBJECT-TYPE
			   SYNTAX           Float 
			   ACCESS           read-only
			   STATUS           mandatory
			   DESCRIPTION
			   "The value of this object provides the Major Low alarm value
			    of the TEC Current Analog parameter.
			   This value is a floating point number that is represented as an IEEE 32 bit number."
			   ::= { gx2ea1000AnalogEntry 60}

		ea1000minorHighTecCurrent       OBJECT-TYPE
			   SYNTAX           Float
			   ACCESS           read-only
			   STATUS           optional
			   DESCRIPTION
			   "The value of this object provides the Minor High alarm value
			    of the TEC Current Analog parameter.
			   This value is a floating point number that is represented as an IEEE 32 bit number.
			   In this version of the Firmware and MIB this Parameter is not used and is 
			   optional. All reads will return the Unused Parameter (10,000,000)"
			   ::= { gx2ea1000AnalogEntry 61}

		ea1000minorLowTecCurrent        OBJECT-TYPE
			   SYNTAX           Float 
			   ACCESS           read-only
			   STATUS           optional
			   DESCRIPTION
			   "The value of this object provides the Minor Low alarm value
			    of the TEC Current Analog parameter.
			   This value is a floating point number that is represented as an IEEE 32 bit number.
			   In this version of the Firmware and MIB this Parameter is not used and is 
			   optional. All reads will return the Unused Parameter (10,000,000)"
			   ::= { gx2ea1000AnalogEntry 62}

		ea1000currentValueTecCurrent    OBJECT-TYPE
			   SYNTAX           Float 
			   ACCESS           read-only
			   STATUS           mandatory
			   DESCRIPTION
			   "The value of this object provides the Current value
			    of the TEC Current Analog parameter.
			   This value is a floating point number that is represented as an IEEE 32 bit number."
			   ::= { gx2ea1000AnalogEntry 63}

		ea1000stateFlagTecCurrent       OBJECT-TYPE
			   SYNTAX           INTEGER
								{
								hidden(1),
								read-only(2),
								updateable(3)
								}
			   ACCESS           read-only
			   STATUS           mandatory
			   DESCRIPTION
			   "The value of this object provides the state
			    of the TEC Current Analog parameter. (0-Hidden	
			          1-Read-Only, 2-Updateable)."
			   ::= { gx2ea1000AnalogEntry 64}

		ea1000minValueTecCurrent        OBJECT-TYPE
			   SYNTAX           Float
			   ACCESS           read-only
			   STATUS           mandatory
			   DESCRIPTION
			   "The value of this object provides the minimum value
			    the TEC Current Analog parameter can achive.
	   		   This value is a floating point number that is represented as an IEEE 32 bit number."
			   ::= { gx2ea1000AnalogEntry 65}

		ea1000maxValueTecCurrent        OBJECT-TYPE
			   SYNTAX           Float
			   ACCESS           read-only
			   STATUS           mandatory
			   DESCRIPTION
			   "The value of this object provides the maximum value
			    the TEC Current Analog parameter can achive.
			   This value is a floating point number that is represented as an IEEE 32 bit number."
			   ::= { gx2ea1000AnalogEntry 66}

		ea1000alarmStateTecCurrent      OBJECT-TYPE
			   SYNTAX           INTEGER
									{
									noAlarm(1),
									majorLowAlarm(2),
									minorLowAlarm(3),
									minorHighAlarm(4),
									majorHighAlarm(5),
									informational(6)
									}
			   ACCESS           read-only
			   STATUS           mandatory
			   DESCRIPTION
			   "The value of this object provides the curent alarm state of
			    the TEC Current Analog parameter."
			   ::= { gx2ea1000AnalogEntry 67}

-- New Parameter

		ea1000labelModuleTemp              OBJECT-TYPE
			   SYNTAX           DisplayString (SIZE (0..80))
			   ACCESS           read-only
			   STATUS           optional
			   DESCRIPTION
			   "The value of this object provides the label of the
			    Module Temperature Analog parameter."
			   ::= { gx2ea1000AnalogEntry 68}

		ea1000uomModuleTemp                OBJECT-TYPE
			   SYNTAX           DisplayString (SIZE (0..80))
			   ACCESS           read-only
			   STATUS           optional
			   DESCRIPTION
			   "The value of this object provides the Unit of Measure of the
			    Module Temperature Analog parameter."
			   ::= { gx2ea1000AnalogEntry 69}

		ea1000majorHighModuleTemp          OBJECT-TYPE
			   SYNTAX           Float 
			   ACCESS           read-only
			   STATUS           mandatory
			   DESCRIPTION
			   "The value of this object provides the Major High alarm value
			    of the Module Temperature Analog parameter.
			   This value is a floating point number that is represented as an IEEE 32 bit number."
			   ::= { gx2ea1000AnalogEntry 70}


		ea1000majorLowModuleTemp           OBJECT-TYPE
			   SYNTAX           Float 
			   ACCESS           read-only
			   STATUS           mandatory
			   DESCRIPTION
			   "The value of this object provides the Major Low alarm value
			    of the Module Temperature Analog parameter.
			   This value is a floating point number that is represented as an IEEE 32 bit number."
			   ::= { gx2ea1000AnalogEntry 71}

		ea1000minorHighModuleTemp          OBJECT-TYPE
			   SYNTAX           Float
			   ACCESS           read-only
			   STATUS           mandatory
			   DESCRIPTION
			   "The value of this object provides the Minor High alarm value
			    of the Module Temperature Analog parameter.
			   This value is a floating point number that is represented as an IEEE 32 bit number."
			   ::= { gx2ea1000AnalogEntry 72}

		ea1000minorLowModuleTemp           OBJECT-TYPE
			   SYNTAX           Float 
			   ACCESS           read-only
			   STATUS           mandatory
			   DESCRIPTION
			   "The value of this object provides the Minor Low alarm value
			    of the Module Temperature Analog parameter.
			   This value is a floating point number that is represented as an IEEE 32 bit number."
			   ::= { gx2ea1000AnalogEntry 73}

		ea1000currentValueModuleTemp       OBJECT-TYPE
			   SYNTAX           Float 
			   ACCESS           read-only
			   STATUS           mandatory
			   DESCRIPTION
			   "The value of this object provides the Current value
			    of the Module Temperature Analog parameter.
			   This value is a floating point number that is represented as an IEEE 32 bit number."
			   ::= { gx2ea1000AnalogEntry 74}

		ea1000stateFlagModuleTemp          OBJECT-TYPE
			   SYNTAX           INTEGER
								{
								hidden(1),
								read-only(2),
								updateable(3)
								}
			   ACCESS           read-only
			   STATUS           mandatory
			   DESCRIPTION
			   "The value of this object provides the state
			    of the Module Temperature Analog parameter. (0-Hidden	
			          1-Read-Only, 2-Updateable)."
			   ::= { gx2ea1000AnalogEntry 75}

		ea1000minValueModuleTemp           OBJECT-TYPE
			   SYNTAX           Float
			   ACCESS           read-only
			   STATUS           mandatory
			   DESCRIPTION
			   "The value of this object provides the minimum value
			    the Module Temperature Analog parameter can achive.
			   This value is a floating point number that is represented as an IEEE 32 bit number."
			   ::= { gx2ea1000AnalogEntry 76}

		ea1000maxValueModuleTemp           OBJECT-TYPE
			   SYNTAX           Float
			   ACCESS           read-only
			   STATUS           mandatory
			   DESCRIPTION
			   "The value of this object provides the maximum value
			    the Module Temperature Analog parameter can achive.
			   This value is a floating point number that is represented as an IEEE 32 bit number."
			   ::= { gx2ea1000AnalogEntry 77}

		ea1000alarmStateModuleTemp         OBJECT-TYPE
			   SYNTAX           INTEGER
									{
									noAlarm(1),
									majorLowAlarm(2),
									minorLowAlarm(3),
									minorHighAlarm(4),
									majorHighAlarm(5),
									informational(6)
									}
			   ACCESS           read-only
			   STATUS           mandatory
			   DESCRIPTION
			   "The value of this object provides the curent alarm state of
			    the Module Temperature Analog parameter."
			   ::= { gx2ea1000AnalogEntry 78}
			   
-- New Parameter

		ea1000labelFan1Speed           OBJECT-TYPE
			   SYNTAX           DisplayString (SIZE (0..80))
			   ACCESS           read-only
			   STATUS           optional
			   DESCRIPTION
			   "The value of this object provides the label of the
			    Fan 1 Speed Analog parameter."
			   ::= { gx2ea1000AnalogEntry 79}

		ea1000uomFan1Speed             OBJECT-TYPE
			   SYNTAX           DisplayString (SIZE (0..80))
			   ACCESS           read-only
			   STATUS           optional
			   DESCRIPTION
			   "The value of this object provides the Unit of Measure of the
			    Fan 1 Speed Analog parameter."
			   ::= { gx2ea1000AnalogEntry 80}

		ea1000majorHighFan1Speed       OBJECT-TYPE
			   SYNTAX           Float 
			   ACCESS           read-only
			   STATUS           optional
			   DESCRIPTION
			   "The value of this object provides the Major High alarm value
			    of the Fan 1 Speed Analog parameter.
			   This value is a floating point number that is represented as an IEEE 32 bit number.
			   In this version of the Firmware and MIB this Parameter is not used and is 
			   optional. All reads will return the Unused Parameter (10,000,000)"
			   ::= { gx2ea1000AnalogEntry 81}


		ea1000majorLowFan1Speed        OBJECT-TYPE
			   SYNTAX           Float 
			   ACCESS           read-only
			   STATUS           mandatory
			   DESCRIPTION
			   "The value of this object provides the Major Low alarm value
			    of the Fan 1 Speed Analog parameter.
			   This value is a floating point number that is represented as an IEEE 32 bit number."
			   ::= { gx2ea1000AnalogEntry 82}

		ea1000minorHighFan1Speed       OBJECT-TYPE
			   SYNTAX           Float
			   ACCESS           read-only
			   STATUS           optional
			   DESCRIPTION
			   "The value of this object provides the Minor High alarm value
			    of the Fan 1 Speed Analog parameter.
			   This value is a floating point number that is represented as an IEEE 32 bit number.
			   In this version of the Firmware and MIB this Parameter is not used and is 
			   optional. All reads will return the Unused Parameter (10,000,000)"
			   ::= { gx2ea1000AnalogEntry 83}

		ea1000minorLowFan1Speed        OBJECT-TYPE
			   SYNTAX           Float 
			   ACCESS           read-only
			   STATUS           mandatory
			   DESCRIPTION
			   "The value of this object provides the Minor Low alarm value
			    of the Fan 1 Speed Analog parameter.
			   This value is a floating point number that is represented as an IEEE 32 bit number."
			   ::= { gx2ea1000AnalogEntry 84}

		ea1000currentValueFan1Speed    OBJECT-TYPE
			   SYNTAX           Float 
			   ACCESS           read-only
			   STATUS           mandatory
			   DESCRIPTION
			   "The value of this object provides the Current value
			    of the Fan 1 Speed Analog parameter.
			   This value is a floating point number that is represented as an IEEE 32 bit number."
			   ::= { gx2ea1000AnalogEntry 85}

		ea1000stateFlagFan1Speed       OBJECT-TYPE
			   SYNTAX           INTEGER
								{
								hidden(1),
								read-only(2),
								updateable(3)
								}
			   ACCESS           read-only
			   STATUS           mandatory
			   DESCRIPTION
			   "The value of this object provides the state
			    of the Fan 1 Speed Analog parameter. (0-Hidden	
			          1-Read-Only, 2-Updateable)."
			   ::= { gx2ea1000AnalogEntry 86}

		ea1000minValueFan1Speed        OBJECT-TYPE
			   SYNTAX           Float
			   ACCESS           read-only
			   STATUS           mandatory
			   DESCRIPTION
			   "The value of this object provides the minimum value
			    the Fan 1 Speed Analog parameter can achive.
			   This value is a floating point number that is represented as an IEEE 32 bit number."
			   ::= { gx2ea1000AnalogEntry 87}

		ea1000maxValueFan1Speed        OBJECT-TYPE
			   SYNTAX           Float
			   ACCESS           read-only
			   STATUS           mandatory
			   DESCRIPTION
			   "The value of this object provides the maximum value
			    the Fan 1 Speed Analog parameter can achive.
			   This value is a floating point number that is represented as an IEEE 32 bit number."
			   ::= { gx2ea1000AnalogEntry 88}

		ea1000alarmStateFan1Speed      OBJECT-TYPE
			   SYNTAX           INTEGER
									{
									noAlarm(1),
									majorLowAlarm(2),
									minorLowAlarm(3),
									minorHighAlarm(4),
									majorHighAlarm(5),
									informational(6)
									}
			   ACCESS           read-only
			   STATUS           mandatory
			   DESCRIPTION
			   "The value of this object provides the curent alarm state of
			    the Fan 1 Speed Analog parameter."
			   ::= { gx2ea1000AnalogEntry 89 }
			   
-- New Parameter

		ea1000labelFan2Speed           OBJECT-TYPE
			   SYNTAX           DisplayString (SIZE (0..80))
			   ACCESS           read-only
			   STATUS           optional
			   DESCRIPTION
			   "The value of this object provides the label of the
			    Fan 2 Speed Analog parameter."
			   ::= { gx2ea1000AnalogEntry 90 }

		ea1000uomFan2Speed             OBJECT-TYPE
			   SYNTAX           DisplayString (SIZE (0..80))
			   ACCESS           read-only
			   STATUS           optional
			   DESCRIPTION
			   "The value of this object provides the Unit of Measure of the
			    Fan 2 Speed Analog parameter."
			   ::= { gx2ea1000AnalogEntry 91 }

		ea1000majorHighFan2Speed       OBJECT-TYPE
			   SYNTAX           Float 
			   ACCESS           read-only
			   STATUS           optional
			   DESCRIPTION
			   "The value of this object provides the Major High alarm value
			    of the Fan 2 Speed Analog parameter.
			   This value is a floating point number that is represented as an IEEE 32 bit number.
			   In this version of the Firmware and MIB this Parameter is not used and is 
			   optional. All reads will return the Unused Parameter (10,000,000)"
			   ::= { gx2ea1000AnalogEntry 92 }


		ea1000majorLowFan2Speed        OBJECT-TYPE
			   SYNTAX           Float 
			   ACCESS           read-only
			   STATUS           mandatory
			   DESCRIPTION
			   "The value of this object provides the Major Low alarm value
			    of the Fan 2 Speed Analog parameter.
			   This value is a floating point number that is represented as an IEEE 32 bit number."
			   ::= { gx2ea1000AnalogEntry 93 }

		ea1000minorHighFan2Speed       OBJECT-TYPE
			   SYNTAX           Float
			   ACCESS           read-only
			   STATUS           optional
			   DESCRIPTION
			   "The value of this object provides the Minor High alarm value
			    of the Fan 2 Speed Analog parameter.
			   This value is a floating point number that is represented as an IEEE 32 bit number.
			   In this version of the Firmware and MIB this Parameter is not used and is 
			   optional. All reads will return the Unused Parameter (10,000,000)"
			   ::= { gx2ea1000AnalogEntry 94 }

		ea1000minorLowFan2Speed        OBJECT-TYPE
			   SYNTAX           Float 
			   ACCESS           read-only
			   STATUS           mandatory
			   DESCRIPTION
			   "The value of this object provides the Minor Low alarm value
			    of the Fan 2 Speed Analog parameter.
			   This value is a floating point number that is represented as an IEEE 32 bit number."
			   ::= { gx2ea1000AnalogEntry 95 }

		ea1000currentValueFan2Speed    OBJECT-TYPE
			   SYNTAX           Float 
			   ACCESS           read-only
			   STATUS           mandatory
			   DESCRIPTION
			   "The value of this object provides the Current value
			    of the Fan 2 Speed Analog parameter.
			   This value is a floating point number that is represented as an IEEE 32 bit number."
			   ::= { gx2ea1000AnalogEntry 96 }

		ea1000stateFlagFan2Speed       OBJECT-TYPE
			   SYNTAX           INTEGER
								{
								hidden(1),
								read-only(2),
								updateable(3)
								}
			   ACCESS           read-only
			   STATUS           mandatory
			   DESCRIPTION
			   "The value of this object provides the state
			    of the Fan 2 Speed Analog parameter. (0-Hidden	
			          1-Read-Only, 2-Updateable)."
			   ::= { gx2ea1000AnalogEntry 97 }

		ea1000minValueFan2Speed        OBJECT-TYPE
			   SYNTAX           Float
			   ACCESS           read-only
			   STATUS           mandatory
			   DESCRIPTION
			   "The value of this object provides the minimum value
			    the Fan 2 Speed Analog parameter can achive.
			   This value is a floating point number that is represented as an IEEE 32 bit number."
			   ::= { gx2ea1000AnalogEntry 98 }

		ea1000maxValueFan2Speed        OBJECT-TYPE
			   SYNTAX           Float
			   ACCESS           read-only
			   STATUS           mandatory
			   DESCRIPTION
			   "The value of this object provides the maximum value
			    the Fan 2 Speed Analog parameter can achive.
			   This value is a floating point number that is represented as an IEEE 32 bit number."
			   ::= { gx2ea1000AnalogEntry 99 }

		ea1000alarmStateFan2Speed      OBJECT-TYPE
			   SYNTAX           INTEGER
									{
									noAlarm(1),
									majorLowAlarm(2),
									minorLowAlarm(3),
									minorHighAlarm(4),
									majorHighAlarm(5),
									informational(6)
									}
			   ACCESS           read-only
			   STATUS           mandatory
			   DESCRIPTION
			   "The value of this object provides the curent alarm state of
			    the Fan 2 Speed Analog parameter."
			   ::= { gx2ea1000AnalogEntry 100}
			   
-- New Parameter

		ea1000label12Volt               OBJECT-TYPE
			   SYNTAX           DisplayString (SIZE (0..80))
			   ACCESS           read-only
			   STATUS           optional
			   DESCRIPTION
			   "The value of this object provides the label of the
			    12v Current Analog parameter."
			   ::= { gx2ea1000AnalogEntry 101}

		ea1000uom12Volt                 OBJECT-TYPE
			   SYNTAX           DisplayString (SIZE (0..80))
			   ACCESS           read-only
			   STATUS           optional
			   DESCRIPTION
			   "The value of this object provides the Unit of Measure of the
			    12v Current Analog parameter."
			   ::= { gx2ea1000AnalogEntry 102}

		ea1000majorHigh12Volt           OBJECT-TYPE
			   SYNTAX           Float 
			   ACCESS           read-only
			   STATUS           mandatory
			   DESCRIPTION
			   "The value of this object provides the Major High alarm value
			    of the 12v Current Analog parameter.
			   This value is a floating point number that is represented as an IEEE 32 bit number."
			   ::= { gx2ea1000AnalogEntry 103}


		ea1000majorLow12Volt            OBJECT-TYPE
			   SYNTAX           Float 
			   ACCESS           read-only
			   STATUS           mandatory
			   DESCRIPTION
			   "The value of this object provides the Major Low alarm value
			    of the 12v Current Analog parameter.
			   This value is a floating point number that is represented as an IEEE 32 bit number."
			   ::= { gx2ea1000AnalogEntry 104}

		ea1000minorHigh12Volt           OBJECT-TYPE
			   SYNTAX           Float
			   ACCESS           read-only
			   STATUS           mandatory
			   DESCRIPTION
			   "The value of this object provides the Minor High alarm value
			    of the 12v Current Analog parameter.
			   This value is a floating point number that is represented as an IEEE 32 bit number."
			   ::= { gx2ea1000AnalogEntry 105}

		ea1000minorLow12Volt            OBJECT-TYPE
			   SYNTAX           Float 
			   ACCESS           read-only
			   STATUS           mandatory
			   DESCRIPTION
			   "The value of this object provides the Minor Low alarm value
			    of the 12v Current Analog parameter.
			   This value is a floating point number that is represented as an IEEE 32 bit number."
			   ::= { gx2ea1000AnalogEntry 106}

		ea1000currentValue12Volt        OBJECT-TYPE
			   SYNTAX           Float 
			   ACCESS           read-only
			   STATUS           mandatory
			   DESCRIPTION
			   "The value of this object provides the Current value
			    of the 12v Current Analog parameter.
			   This value is a floating point number that is represented as an IEEE 32 bit number."
			   ::= { gx2ea1000AnalogEntry 107}

		ea1000stateFlag12Volt           OBJECT-TYPE
			   SYNTAX           INTEGER
								{
								hidden(1),
								read-only(2),
								updateable(3)
								}
			   ACCESS           read-only
			   STATUS           mandatory
			   DESCRIPTION
			   "The value of this object provides the state
			    of the 12v Current Analog parameter. (0-Hidden	
			          1-Read-Only, 2-Updateable)."
			   ::= { gx2ea1000AnalogEntry 108}

		ea1000minValue12Volt            OBJECT-TYPE
			   SYNTAX           Float
			   ACCESS           read-only
			   STATUS           mandatory
			   DESCRIPTION
			   "The value of this object provides the minimum value
			    the 12v Current Analog parameter can achive.
			   This value is a floating point number that is represented as an IEEE 32 bit number."
			   ::= { gx2ea1000AnalogEntry 109}

		ea1000maxValue12Volt            OBJECT-TYPE
			   SYNTAX           Float
			   ACCESS           read-only
			   STATUS           mandatory
			   DESCRIPTION
			   "The value of this object provides the maximum value
			    the 12v Current Analog parameter can achive.
			   This value is a floating point number that is represented as an IEEE 32 bit number."
			   ::= { gx2ea1000AnalogEntry 110}

		ea1000alarmState12Volt          OBJECT-TYPE
			   SYNTAX           INTEGER
									{
									noAlarm(1),
									majorLowAlarm(2),
									minorLowAlarm(3),
									minorHighAlarm(4),
									majorHighAlarm(5),
									informational(6)
									}
			   ACCESS           read-only
			   STATUS           mandatory
			   DESCRIPTION
			   "The value of this object provides the curent alarm state of
			    the 12v Current Analog parameter."
			   ::= { gx2ea1000AnalogEntry 111}

-- ************************ Digital parameters **********************************
		gx2ea1000DigitalTableIndex              OBJECT-TYPE
			   SYNTAX           INTEGER (1..4294967295)
			   ACCESS           read-only
			   STATUS           mandatory
			   DESCRIPTION
			   "The value of this object identifies the network
			    element. This index is equal to the
			    hfcCommonTableIndex for the same element."
			   ::= { gx2ea1000DigitalEntry 1}

-- New parameter
		ea1000labelRfInput                	OBJECT-TYPE
			   SYNTAX       		DisplayString (SIZE (0..80))         
			   ACCESS           	read-only
			   STATUS           	optional
			   DESCRIPTION
			   "The value of this object provides the label of the
			    RF Input Control  Digital parameter."
			   ::= { gx2ea1000DigitalEntry 2}

		ea1000enumRfInput               		OBJECT-TYPE
			   SYNTAX       		DisplayString (SIZE (0..80))         
			   ACCESS           	read-only
			   STATUS           	optional
			   DESCRIPTION
			   "The value of this object represents the Enumeration values
			    possible for the Digital parameter. Each Enumerated values is
			    separated by a common. The first value has a enumerated value of 1."
			   ::= { gx2ea1000DigitalEntry 3}

		ea1000valueRfInput                	OBJECT-TYPE
			   SYNTAX       		INTEGER
					    		{
							off(1),
							on(2)
					    		}
			   ACCESS           	read-write
			   STATUS           	mandatory
			   DESCRIPTION
			   "The value of this object is the current value of the parameter."
			   ::= { gx2ea1000DigitalEntry 4}

		ea1000stateflagRfInput              OBJECT-TYPE
			   SYNTAX       		INTEGER
								{
								hidden(1),
								read-only(2),
								updateable(3)
								}
			   ACCESS           	read-only
			   STATUS           	mandatory
			   DESCRIPTION
			   "The value of this object provides the state
			    of the RF Input Control  Digital parameter. (0-Hidden	
			          1-Read-Only, 2-Updateable)."
			   ::= { gx2ea1000DigitalEntry 5}

-- New parameter
		ea1000labelOptOutput                OBJECT-TYPE
			   SYNTAX       		DisplayString (SIZE (0..80))         
			   ACCESS           	read-only
			   STATUS           	optional
			   DESCRIPTION
			   "The value of this object provides the label of the
			    Optical Output Control  Digital parameter."
			   ::= { gx2ea1000DigitalEntry 6}

		ea1000enumOptOutput               	      OBJECT-TYPE
			   SYNTAX          	DisplayString (SIZE (0..80))         
			   ACCESS           	read-only
			   STATUS           	optional
			   DESCRIPTION
			   "The value of this object represents the Enumeration values
			    possible for the Digital parameter. Each Enumerated values is
			    separated by a common. The first value has a enumerated value of 1."
			   ::= { gx2ea1000DigitalEntry 7}

		ea1000valueOptOutput                OBJECT-TYPE
			   SYNTAX       		INTEGER
					    		{
							off(1),
							on(2)
					    		}
			   ACCESS           	read-write
			   STATUS           	mandatory
			   DESCRIPTION
			   "The value of this object is the current value of the parameter."
			   ::= { gx2ea1000DigitalEntry 8}

		ea1000stateflagOptOutput            OBJECT-TYPE
			   SYNTAX      		INTEGER
								{
								hidden(1),
								read-only(2),
								updateable(3)
								}
			   ACCESS           	read-only
			   STATUS           	mandatory
			   DESCRIPTION
			   "The value of this object provides the ea1000state
			    of the the parameter. (0-Hidden 1-Read-Only, 2-Updateable)."
			   ::= { gx2ea1000DigitalEntry 9}
-- New parameter
		ea1000labelLaserMode                OBJECT-TYPE
			   SYNTAX         	DisplayString (SIZE (0..80))         
			   ACCESS           	read-only
			   STATUS           	optional
			   DESCRIPTION
			   "The value of this object provides the label of the
			    Laser Mode  Digital parameter."
			   ::= { gx2ea1000DigitalEntry 10}

		ea1000enumLaserMode               	OBJECT-TYPE
			   SYNTAX         	DisplayString (SIZE (0..80))         
			   ACCESS           	read-only
			   STATUS           	optional
			   DESCRIPTION
			   "The value of this object represents the Enumeration values
			    possible for the Digital parameter. Each Enumerated values is
			    separated by a common. The first value has a enumerated value of 1."
			   ::= { gx2ea1000DigitalEntry 11}

		ea1000valueLaserMode                OBJECT-TYPE
			   SYNTAX       		INTEGER
					    		{
							preset(1),
							set(2),
							setEquate(3),
							manual(4),
							manualEquate(5)
					    		}
			   ACCESS           	read-write
			   STATUS           	mandatory
			   DESCRIPTION
			   "The value of this object is the current value of the parameter."
			   ::= { gx2ea1000DigitalEntry 12}

		ea1000stateflagLaserMode            OBJECT-TYPE
			   SYNTAX         	INTEGER
								{
								hidden(1),
								read-only(2),
								updateable(3)
								}
			   ACCESS           	read-only
			   STATUS           	mandatory
			   DESCRIPTION
			   "The value of this object provides the state
			    of the the parameter. (0-Hidden 1-Read-Only, 2-Updateable)."
			   ::= { gx2ea1000DigitalEntry 13}
-- New parameter
		ea1000labelAttenSetting             OBJECT-TYPE
			   SYNTAX         	DisplayString (SIZE (0..80))         
			   ACCESS           	read-only
			   STATUS           	optional
			   DESCRIPTION
			   "The value of this object provides the label of the
			    Attenuation Setting Ditital Parameter."
			   ::= { gx2ea1000DigitalEntry 14}

		ea1000enumAttenSetting               	OBJECT-TYPE
			   SYNTAX         	DisplayString (SIZE (0..80))         
			   ACCESS           	read-only
			   STATUS           	optional
			   DESCRIPTION
			   "The value of this object represents the Enumeration values
			    possible for the Digital parameter. Each Enumerated values is
			    separated by a common. The first value has a enumerated value of 1."
			   ::= { gx2ea1000DigitalEntry 15}

		ea1000valueAttenSetting                OBJECT-TYPE
			   SYNTAX       		INTEGER
					    		{
							attn0pt0(1),
							attn0pt5(2),
							attn1pt0(3),
							attn1pt5(4),
							attn2pt0(5),
							attn2pt5(6),
							attn3pt0(7),
							attn3pt5(8),
							attn4pt0(9),
							attn4pt5(10),
							attn5pt0(11),
							attn5pt5(12),
							attn6pt0(13),
							attn6pt5(14),
							attn7pt0(15),
							attn7pt5(16),
							attn8pt0(17),
							attn8pt5(18),
							attn9pt0(19),
							attn9pt5(20),
							attn10pt0(21),
							attn10pt5(22),
							attn11pt0(23),
							attn11pt5(24),
							attn12pt0(25)
					    		}
			   ACCESS           	read-write
			   STATUS           	mandatory
			   DESCRIPTION
			   "The value of this object is the current value of the parameter."
			   ::= { gx2ea1000DigitalEntry 16}

		ea1000stateflagAttenSetting            OBJECT-TYPE
			   SYNTAX         	INTEGER
								{
								hidden(1),
								read-only(2),
								updateable(3)
								}
			   ACCESS           	read-only
			   STATUS           	mandatory
			   DESCRIPTION
			   "The value of this object provides the state
			    of the the parameter. (0-Hidden 1-Read-Only, 2-Updateable)."
			   ::= { gx2ea1000DigitalEntry 17}
-- New parameter
		ea1000labelLaserSecMode             OBJECT-TYPE
			   SYNTAX         	DisplayString (SIZE (0..80))         
			   ACCESS           	read-only
			   STATUS           	optional
			   DESCRIPTION
			   "The value of this object provides the label of the
			    Laser Secondary Mode Digital parameter."
			   ::= { gx2ea1000DigitalEntry 18}

		ea1000enumLaserSecMode               	OBJECT-TYPE
			   SYNTAX          	DisplayString (SIZE (0..80))         
			   ACCESS           	read-only
			   STATUS           	optional
			   DESCRIPTION
			   "The value of this object represents the Enumeration values
			    possible for the Digital parameter. Each Enumerated values is
			    separated by a common. The first value has a enumerated value of 1."
			   ::= { gx2ea1000DigitalEntry 19}

		ea1000valueLaserSecMode           	OBJECT-TYPE
			   SYNTAX       		INTEGER
					    		{
							cw(1),
							video(2)
					    		}
			   ACCESS           	read-write
			   STATUS           	mandatory
			   DESCRIPTION
			   "The value of this object is the current value of the parameter."
			   ::= { gx2ea1000DigitalEntry 20}

		ea1000stateflagLaserSecMode         OBJECT-TYPE
			   SYNTAX         	INTEGER
								{
								hidden(1),
								read-only(2),
								updateable(3)
								}
			   ACCESS           	read-only
			   STATUS           	mandatory
			   DESCRIPTION
			   "The value of this object provides the state
			    of the the parameter. (0-Hidden 1-Read-Only, 2-Updateable)."
			   ::= { gx2ea1000DigitalEntry 21}

-- New parameter
		ea1000labelVideoOffset            	OBJECT-TYPE
			   SYNTAX       	      DisplayString (SIZE (0..80))         
			   ACCESS           	read-only
			   STATUS           	optional
			   DESCRIPTION
			   "The value of this object provides the label of the
			    Video Offset  Digital parameter."
			   ::= { gx2ea1000DigitalEntry 22}

		ea1000enumVideoOffset               	OBJECT-TYPE
			   SYNTAX       	      DisplayString (SIZE (0..80))         
			   ACCESS           	read-only
			   STATUS           	optional
			   DESCRIPTION
			   "The value of this object represents the Enumeration values
			    possible for the Digital parameter. Each Enumerated values is
			    separated by a common. The first value has a enumerated value of 1.."
			   ::= { gx2ea1000DigitalEntry 23}

		ea1000valueVideoOffset              OBJECT-TYPE
			   SYNTAX       		INTEGER
					    		{
							minus1dB(1),
							minus2dB(2),
							minus3dB(3),
 							minus4dB(4),
							minus5dB(5)
					    		}
			   ACCESS           	read-write
			   STATUS           	mandatory
			   DESCRIPTION
			   "The value of this object is the current value of the parameter."
			   ::= { gx2ea1000DigitalEntry 24}

		ea1000stateflagVideoOffset        	OBJECT-TYPE
			   SYNTAX       		INTEGER
								{
								hidden(1),
								read-only(2),
								updateable(3)
								}
			   ACCESS           	read-only
			   STATUS           	mandatory
			   DESCRIPTION
			   "The value of this object provides the state
			    of the the parameter. (0-Hidden 1-Read-Only, 2-Updateable)."
			   ::= { gx2ea1000DigitalEntry 25}
-- New parameter
		ea1000labelFactoryDefault           OBJECT-TYPE
			   SYNTAX       		DisplayString (SIZE (0..80))         
			   ACCESS           	read-only
			   STATUS           	optional
			   DESCRIPTION
			   "The value of this object provides the label of the
			    Factory Default Reset  Digital parameter."
			   ::= { gx2ea1000DigitalEntry 26}

		ea1000enumFactoryDefault               	OBJECT-TYPE
			   SYNTAX       		DisplayString (SIZE (0..80))         
			   ACCESS           	read-only
			   STATUS           	optional
			   DESCRIPTION
			   "The value of this object represents the Enumeration values
			    possible for the Digital parameter. Each Enumerated values is
			    separated by a common. The first value has a enumerated value of 1."
			   ::= { gx2ea1000DigitalEntry 27}


		ea1000valueFactoryDefault         	OBJECT-TYPE
			   SYNTAX       		INTEGER
					    		{
							off(1),
							on(2)
					    		}
			   ACCESS           	read-write
			   STATUS           	mandatory
			   DESCRIPTION
			   "The value of this object is the current value of the parameter."
			   ::= { gx2ea1000DigitalEntry 28}

		ea1000stateflagFactoryDefault     	OBJECT-TYPE
			   SYNTAX       		INTEGER
								{
								hidden(1),
								read-only(2),
								updateable(3)
								}
			   ACCESS           	read-only
			   STATUS           	mandatory
			   DESCRIPTION
			   "The value of this object provides the state
			    of the the parameter. (0-Hidden 1-Read-Only, 2-Updateable)."
			   ::= { gx2ea1000DigitalEntry 29}



		--*********** STATUS *****************
		gx2ea1000StatusTableIndex              OBJECT-TYPE
			   SYNTAX           INTEGER (1..4294967295)
			   ACCESS           read-only
			   STATUS           mandatory
			   DESCRIPTION
			   "The value of this object identifies the network
			    element. This index is equal to the
			    hfcCommonTableIndex for the same element."
			   ::= { gx2ea1000StatusEntry 1}

--New Parameter
		ea1000labelBoot               	OBJECT-TYPE
			   SYNTAX       		DisplayString (SIZE (0..80))         
			   ACCESS           	read-only
			   STATUS           	optional
			   DESCRIPTION
			   "The value of this object provides the label of the
			    Boot Status  Status parameter."
			   ::= { gx2ea1000StatusEntry 2}

		ea1000valueBoot              		OBJECT-TYPE
			   SYNTAX       		INTEGER
									{
									ok(1),
									undetermined(2),
									warning(3),
									minor(4),
									major(5),
									critical(6)
									}
			   ACCESS           	read-only
			   STATUS           	mandatory
			   DESCRIPTION
			   "The value of this object provides the current state of
			    the parameter (0-Ok, 1-Undetermined
			    2-Warning, 3-Minor, 4-Major, 5-Critical)."
			   ::= { gx2ea1000StatusEntry 3}

		ea1000stateflagBoot     	OBJECT-TYPE
			   SYNTAX       		INTEGER
								{
								hidden(1),
								read-only(2),
								updateable(3)
								}
			   ACCESS           	read-only
			   STATUS           	mandatory
			   DESCRIPTION
			   "The value of this object provides the state
			    of the the parameter. (0-Hidden 1-Read-Only, 2-Updateable)."
			   ::= { gx2ea1000StatusEntry  4}



--New Parameter
		ea1000labelFlash               	OBJECT-TYPE
			   SYNTAX       		DisplayString (SIZE (0..80))         
			   ACCESS           	read-only
			   STATUS           	optional
			   DESCRIPTION
			   "The value of this object provides the label of the
			    Flash Status  Status parameter."
			   ::= { gx2ea1000StatusEntry 5}

		ea1000valueFlash              	OBJECT-TYPE
			   SYNTAX       		INTEGER
									{
									ok(1),
									undetermined(2),
									warning(3),
									minor(4),
									major(5),
									critical(6)
									}
			   ACCESS           	read-only
			   STATUS           	mandatory
			   DESCRIPTION
			   "The value of this object provides the current state of
			    the parameter (0-Ok, 1-Undetermined
			    2-Warning, 3-Minor, 4-Major, 5-Critical)."
			   ::= { gx2ea1000StatusEntry 6}

		ea1000stateflagFlash     	OBJECT-TYPE
			   SYNTAX       		INTEGER
								{
								hidden(1),
								read-only(2),
								updateable(3)
								}
			   ACCESS           	read-only
			   STATUS           	mandatory
			   DESCRIPTION
			   "The value of this object provides the state
			    of the the parameter. (0-Hidden 1-Read-Only, 2-Updateable)."
			   ::= { gx2ea1000StatusEntry  7}

--New Parameter
		ea1000labelFactoryDataCRC           OBJECT-TYPE
			   SYNTAX       		DisplayString (SIZE (0..80))         
			   ACCESS           	read-only
			   STATUS           	optional
			   DESCRIPTION
			   "The value of this object provides the label of the
			    Factory Data CRC Status parameter."
			   ::= { gx2ea1000StatusEntry 8}

		ea1000valueFactoryDataCRC          	OBJECT-TYPE
			   SYNTAX       		INTEGER
									{
									ok(1),
									undetermined(2),
									warning(3),
									minor(4),
									major(5),
									critical(6)
									}
			   ACCESS           	read-only
			   STATUS           	mandatory
			   DESCRIPTION
			   "The value of this object provides the current state of
			    the parameter (0-Ok, 1-Undetermined
			    2-Warning, 3-Minor, 4-Major, 5-Critical)."
			   ::= { gx2ea1000StatusEntry 9}

		ea1000stateflagFactoryDataCRC     	OBJECT-TYPE
			   SYNTAX       		INTEGER
								{
								hidden(1),
								read-only(2),
								updateable(3)
								}
			   ACCESS           	read-only
			   STATUS           	mandatory
			   DESCRIPTION
			   "The value of this object provides the state
			    of the the parameter. (0-Hidden 1-Read-Only, 2-Updateable)."
			   ::= { gx2ea1000StatusEntry  10}


--New Parameter
		ea1000labelLaserDataCRC             OBJECT-TYPE
			   SYNTAX       		DisplayString (SIZE (0..80))         
			   ACCESS           	read-only
			   STATUS           	optional
			   DESCRIPTION
			   "The value of this object provides the label of the
			    Laser Data CRC Status parameter."
			   ::= { gx2ea1000StatusEntry 11}

		ea1000valueLaserDataCRC           	OBJECT-TYPE
			   SYNTAX       		INTEGER
									{
									ok(1),
									undetermined(2),
									warning(3),
									minor(4),
									major(5),
									critical(6)
									}
			   ACCESS           	read-only
			   STATUS           	mandatory
			   DESCRIPTION
			   "The value of this object provides the current state of
			    the parameter (0-Ok, 1-Undetermined
			    2-Warning, 3-Minor, 4-Major, 5-Critical)."
			   ::= { gx2ea1000StatusEntry 12}

		ea1000stateflagLaserDataCRC     	OBJECT-TYPE
			   SYNTAX       		INTEGER
								{
								hidden(1),
								read-only(2),
								updateable(3)
								}
			   ACCESS           	read-only
			   STATUS           	mandatory
			   DESCRIPTION
			   "The value of this object provides the state
			    of the the parameter. (0-Hidden 1-Read-Only, 2-Updateable)."
			   ::= { gx2ea1000StatusEntry  13}

--New Parameter
		ea1000labelAlarmDataCrc               	      OBJECT-TYPE
			   SYNTAX       		DisplayString (SIZE (0..80))         
			   ACCESS           	read-only
			   STATUS           	optional
			   DESCRIPTION
			   "The value of this object provides the label of the
			    Alarm Data Crc parameter."
			   ::= { gx2ea1000StatusEntry 14}

		ea1000valueAlarmDataCrc              		OBJECT-TYPE
			   SYNTAX       		INTEGER
									{
									ok(1),
									undetermined(2),
									warning(3),
									minor(4),
									major(5),
									critical(6)
									}
			   ACCESS           	read-only
			   STATUS           	mandatory
			   DESCRIPTION
			   "The value of this object provides the current state of
			    the parameter (0-Ok, 1-Undetermined
			    2-Warning, 3-Minor, 4-Major, 5-Critical)."
			   ::= { gx2ea1000StatusEntry 15}

		ea1000stateflagAlarmDataCrc     	OBJECT-TYPE
			   SYNTAX       		INTEGER
								{
								hidden(1),
								read-only(2),
								updateable(3)
								}
			   ACCESS           	read-only
			   STATUS           	mandatory
			   DESCRIPTION
			   "The value of this object provides the state
			    of the the parameter. (0-Hidden 1-Read-Only, 2-Updateable)."
			   ::= { gx2ea1000StatusEntry  16}

--New Parameter
		ea1000labelRFInputStatus              OBJECT-TYPE
			   SYNTAX       		DisplayString (SIZE (0..80))         
			   ACCESS           	read-only
			   STATUS           	optional
			   DESCRIPTION
			   "The value of this object provides the label of the
			    RF Input Status parameter."
			   ::= { gx2ea1000StatusEntry 17}

		ea1000valueRFInputStatus              OBJECT-TYPE
			   SYNTAX       		INTEGER
									{
									ok(1),
									undetermined(2),
									warning(3),
									minor(4),
									major(5),
									critical(6)
									}
			   ACCESS           	read-only
			   STATUS           	mandatory
			   DESCRIPTION
			   "The value of this object provides the current state of
			    the parameter (0-Ok, 1-Undetermined
			    2-Warning, 3-Minor, 4-Major, 5-Critical)."
			   ::= { gx2ea1000StatusEntry 18}

		ea1000stateflagRFInputStatus     	OBJECT-TYPE
			   SYNTAX       		INTEGER
								{
								hidden(1),
								read-only(2),
								updateable(3)
								}
			   ACCESS           	read-only
			   STATUS           	mandatory
			   DESCRIPTION
			   "The value of this object provides the state
			    of the the parameter. (0-Hidden 1-Read-Only, 2-Updateable)."
			   ::= { gx2ea1000StatusEntry  19}



            -- ************ FACTORY DATA ****************
		gx2ea1000FactoryTableIndex              OBJECT-TYPE
			   SYNTAX           INTEGER (1..4294967295)
			   ACCESS           read-only
			   STATUS           mandatory
			   DESCRIPTION
			   "The value of this object identifies the network
			    element. This index is equal to the
			    hfcCommonTableIndex for the same element."
			   ::= { gx2ea1000FactoryEntry 1}

		ea1000bootControlByteValue          	OBJECT-TYPE
			   SYNTAX       		INTEGER
			   ACCESS           	read-only
			   STATUS           	mandatory
			   DESCRIPTION
			   "The value of this object indicates which bank the firmware
			    is currently being boot from."
			   ::= { gx2ea1000FactoryEntry 2}

		ea1000bootStatusByteValue          	OBJECT-TYPE
			   SYNTAX       		INTEGER
			   ACCESS           	read-only
			   STATUS           	mandatory
			   DESCRIPTION
			   "This object indicates the status of the last boot"
			   ::= { gx2ea1000FactoryEntry 3}

		ea1000bank1CRCValue          		OBJECT-TYPE
			   SYNTAX       		INTEGER
			   ACCESS           	read-only
			   STATUS           	mandatory
			   DESCRIPTION
			   "This object provides the CRC code of bank 0."
			   ::= { gx2ea1000FactoryEntry 4}

		ea1000bank2CRCValue          		OBJECT-TYPE
			   SYNTAX       		INTEGER
			   ACCESS           	read-only
			   STATUS           	mandatory
			   DESCRIPTION
			   "This object provides the CRC code of bank 1."
			   ::= { gx2ea1000FactoryEntry 5}

		ea1000prgEEPROMByteValue          		OBJECT-TYPE
			   SYNTAX       		INTEGER
			   ACCESS           	read-only
			   STATUS           	mandatory
			   DESCRIPTION
			   "This object indicates if the EEPROM has been programmed"
			   ::= { gx2ea1000FactoryEntry 6}

		ea1000factoryCRCValue          		OBJECT-TYPE
			   SYNTAX       		INTEGER
			   ACCESS           	read-only
			   STATUS           	mandatory
			   DESCRIPTION
			   "This object provides the CRC code for the Factory data."
			   ::= { gx2ea1000FactoryEntry 7}

		ea1000calculateCRCValue          		OBJECT-TYPE
			   SYNTAX       		INTEGER
					    		{
							factory(1),
							laserData(2),
							alarm(3)
					    		}
			   ACCESS           	read-only
			   STATUS           	mandatory
			   DESCRIPTION
			   "This object indicates which of the Emnums will have the CRC calculated."
			   ::= { gx2ea1000FactoryEntry 8}

		ea1000hourMeterValue          		OBJECT-TYPE
			   SYNTAX       		INTEGER
			   ACCESS           	read-only
			   STATUS           	mandatory
			   DESCRIPTION
			   "This object provides the hour meter reading of the module."
			   ::= { gx2ea1000FactoryEntry 9}

		ea1000flashPrgCntAValue          		OBJECT-TYPE
			   SYNTAX       		INTEGER
			   ACCESS           	read-only
			   STATUS           	mandatory
			   DESCRIPTION
			   "This object provides the number of times Bank 1 flash has been 
                      programmed."
			   ::= { gx2ea1000FactoryEntry 10}

		ea1000flashPrgCntBValue          		OBJECT-TYPE
			   SYNTAX       		INTEGER
			   ACCESS           	read-only
			   STATUS           	mandatory
			   DESCRIPTION
			   "This object provides the number of times Bank 1 flash has been 
                      programmed."
			   ::= { gx2ea1000FactoryEntry 11}

		ea1000flashBankARevValue          		OBJECT-TYPE
			   SYNTAX       		DisplayString (SIZE (0..80))
			   ACCESS           	read-only
			   STATUS           	mandatory
			   DESCRIPTION
			   "This object provides the revision of flash bank 0."
			   ::= { gx2ea1000FactoryEntry 12}

		ea1000flashBankBRevValue          		OBJECT-TYPE
			   SYNTAX       		DisplayString (SIZE (0..80))
			   ACCESS           	read-only
			   STATUS           	mandatory
			   DESCRIPTION
			   "This object provides the revision of flash bank 1."
			   ::= { gx2ea1000FactoryEntry 13}



-- ****************************************************************
--
-- TRAP DEFINITIONS
--
--
-- Every trap generated by an HFC agents will include first 9 identical
-- fields. If particular variable is not supported in
-- particular TRAP-TYPE then default value will be returned.
--
-- DESCRIPTION will include explanation of use of generic
-- variables (trapAdditionalInfo******.)  If no
-- DESCRIPTION is given then generic variables will contain
-- default values.
--
-- *****************************************************************

-- **************************************************************************
--                          EA 1000 Laser Module traps
-- **************************************************************************
   trapEA1000ConfigChangeInteger TRAP-TYPE
       ENTERPRISE gx2Ea1000
       VARIABLES
	       {       
		trapIdentifier,
		trapNetworkElemModelNumber,
		trapNetworkElemSerialNum,
		trapPerceivedSeverity,
		trapNetworkElemOperState,
		trapNetworkElemAlarmStatus,  
		trapNetworkElemAdminState,
		trapNetworkElemAvailStatus,
		trapText,
		trapChangedObjectId,
		trapChangedValueInteger,
		trapNETrapLastTrapTimeStamp
	       }
       DESCRIPTION
	"This trap is issued if configuration of a single variable
	 with integer type was changed (via ANY interface).  
	 TrapChangedValueInteger variable may contain current reading
	 of that variable.
	 trapPerceivedSeverity - 'indeterminate'"
  ::= 1

   trapEA1000ConfigChangeDisplayString TRAP-TYPE
       ENTERPRISE gx2Ea1000
       VARIABLES
	       {       
		trapIdentifier,
		trapNetworkElemModelNumber,
		trapNetworkElemSerialNum,
		trapPerceivedSeverity,
		trapNetworkElemOperState,
		trapNetworkElemAlarmStatus,  
		trapNetworkElemAdminState,
		trapNetworkElemAvailStatus,
		trapText,
		trapChangedObjectId,
		trapChangedValueDisplayString,
		trapNETrapLastTrapTimeStamp
	       }
       DESCRIPTION
	"This trap is issued if configuration of a single variable
	 with DispalayString type was changed (via ANY interface).  
	 TrapChangedValueDisplayString variable may contain current reading
	 of that variable.
	 trapPerceivedSeverity - 'indeterminate'"
  ::= 2

  trapEA1000RFInputAlarm TRAP-TYPE
	ENTERPRISE gx2Ea1000
	VARIABLES
		{       
		 trapIdentifier,
		 trapNetworkElemModelNumber,
		 trapNetworkElemSerialNum,
		 trapPerceivedSeverity,
		 trapNetworkElemOperState,
		 trapNetworkElemAlarmStatus,  
		 trapNetworkElemAdminState,
		 trapNetworkElemAvailStatus,
		 trapText,
		 trapChangedObjectId,
		 trapChangedValueInteger,
		 trapNETrapLastTrapTimeStamp
		}
	DESCRIPTION
	"This trap is issued when the Laser Modules RF input parameter 
	 goes out of range.
	 trapAdditionalInfoInteger variable contains current reading of 
	 the this parameter."
  ::= 3
  
  trapEA1000RFOverloadAlarm TRAP-TYPE
	ENTERPRISE gx2Ea1000
	VARIABLES
		{       
		 trapIdentifier,
		 trapNetworkElemModelNumber,
		 trapNetworkElemSerialNum,
		 trapPerceivedSeverity,
		 trapNetworkElemOperState,
		 trapNetworkElemAlarmStatus,  
		 trapNetworkElemAdminState,
		 trapNetworkElemAvailStatus,
		 trapText,
		 trapChangedObjectId,
		 trapChangedValueInteger,
		 trapNETrapLastTrapTimeStamp
		}
	DESCRIPTION
	"This trap is issued when the Laser Modules RF overload parameter 
	 goes out of range.
	 trapAdditionalInfoInteger variable contains current reading of 
	 the this parameter."
  ::= 4

  trapEA1000RFOffsetAlarm TRAP-TYPE
	ENTERPRISE gx2Ea1000
	VARIABLES
		{       
		 trapIdentifier,
		 trapNetworkElemModelNumber,
		 trapNetworkElemSerialNum,
		 trapPerceivedSeverity,
		 trapNetworkElemOperState,
		 trapNetworkElemAlarmStatus,  
		 trapNetworkElemAdminState,
		 trapNetworkElemAvailStatus,
		 trapText,
		 trapChangedObjectId,
		 trapChangedValueInteger,
		 trapNETrapLastTrapTimeStamp
		}
	DESCRIPTION
	"This trap is issued when the Laser Modules RF Offset parameter 
	 goes out of range.
	 trapAdditionalInfoInteger variable contains current reading of 
	 the this parameter."
  ::= 5

  trapEA1000OpticalPowerAlarm TRAP-TYPE
	ENTERPRISE gx2Ea1000
	VARIABLES
		{       
		 trapIdentifier,
		 trapNetworkElemModelNumber,
		 trapNetworkElemSerialNum,
		 trapPerceivedSeverity,
		 trapNetworkElemOperState,
		 trapNetworkElemAlarmStatus,  
		 trapNetworkElemAdminState,
		 trapNetworkElemAvailStatus,
		 trapText,
		 trapChangedObjectId,
		 trapChangedValueInteger,
		 trapNETrapLastTrapTimeStamp
		}
	DESCRIPTION
	"This trap is issued when the Laser Modules Optical Power parameter 
	 goes out of range.
	 trapAdditionalInfoInteger variable contains current reading of 
	 the this parameter."
  ::= 6

  trapEA1000LaserBiasAlarm TRAP-TYPE
	ENTERPRISE gx2Ea1000
	VARIABLES
		{       
		 trapIdentifier,
		 trapNetworkElemModelNumber,
		 trapNetworkElemSerialNum,
		 trapPerceivedSeverity,
		 trapNetworkElemOperState,
		 trapNetworkElemAlarmStatus,  
		 trapNetworkElemAdminState,
		 trapNetworkElemAvailStatus,
		 trapText,
		 trapChangedObjectId,
		 trapChangedValueInteger,
		 trapNETrapLastTrapTimeStamp
		}
	DESCRIPTION
	"This trap is issued when the Laser Bias parameter goes out of range.
	 trapAdditionalInfoInteger variable contains current reading of 
	 the this parameter."
  ::= 7
     
  trapEA1000LaserTempAlarm TRAP-TYPE
	ENTERPRISE gx2Ea1000
	VARIABLES
		{       
		 trapIdentifier,
		 trapNetworkElemModelNumber,
		 trapNetworkElemSerialNum,
		 trapPerceivedSeverity,
		 trapNetworkElemOperState,
		 trapNetworkElemAlarmStatus,  
		 trapNetworkElemAdminState,
		 trapNetworkElemAvailStatus,
		 trapText,
		 trapChangedObjectId,
		 trapChangedValueInteger,
		 trapNETrapLastTrapTimeStamp
		}
	DESCRIPTION
	"This trap is issued when the Laser Temperature parameter 
	 goes out of range.
	 trapAdditionalInfoInteger variable contains current reading of 
	 the this parameter."
  ::= 8

  trapEA1000TECCurrentAlarm TRAP-TYPE
	ENTERPRISE gx2Ea1000
	VARIABLES
		{       
		 trapIdentifier,
		 trapNetworkElemModelNumber,
		 trapNetworkElemSerialNum,
		 trapPerceivedSeverity,
		 trapNetworkElemOperState,
		 trapNetworkElemAlarmStatus,  
		 trapNetworkElemAdminState,
		 trapNetworkElemAvailStatus,
		 trapText,
		 trapChangedObjectId,
		 trapChangedValueInteger,
		 trapNETrapLastTrapTimeStamp
		}
	DESCRIPTION
	"This trap is issued when the Laser Modules TEC Current parameter 
	 goes out of range.
	 trapAdditionalInfoInteger variable contains current reading of 
	 the this parameter."
  ::= 9

  trapEA1000Fan1SpeedAlarm TRAP-TYPE
	ENTERPRISE gx2Ea1000
	VARIABLES
		{       
		 trapIdentifier,
		 trapNetworkElemModelNumber,
		 trapNetworkElemSerialNum,
		 trapPerceivedSeverity,
		 trapNetworkElemOperState,
		 trapNetworkElemAlarmStatus,  
		 trapNetworkElemAdminState,
		 trapNetworkElemAvailStatus,
		 trapText,
		 trapChangedObjectId,
		 trapChangedValueInteger,
		 trapNETrapLastTrapTimeStamp
		}
	DESCRIPTION
	"This trap is issued when the Laser Modules Fan 1 Speed 
	 parameter goes out of range.
	 trapAdditionalInfoInteger variable contains current reading of 
	 the this parameter."
  ::= 10

  trapEA1000Fan2SpeedAlarm TRAP-TYPE
	ENTERPRISE gx2Ea1000
	VARIABLES
		{       
		 trapIdentifier,
		 trapNetworkElemModelNumber,
		 trapNetworkElemSerialNum,
		 trapPerceivedSeverity,
		 trapNetworkElemOperState,
		 trapNetworkElemAlarmStatus,  
		 trapNetworkElemAdminState,
		 trapNetworkElemAvailStatus,
		 trapText,
		 trapChangedObjectId,
		 trapChangedValueInteger,
		 trapNETrapLastTrapTimeStamp
		}
	DESCRIPTION
	"This trap is issued when the Laser Modules Fan 2 Speed 
	 parameter goes out of range.
	 trapAdditionalInfoInteger variable contains current reading of 
	 the this parameter."
  ::= 11

  trapEA100012vAlarm TRAP-TYPE
	ENTERPRISE gx2Ea1000
	VARIABLES
		{       
		 trapIdentifier,
		 trapNetworkElemModelNumber,
		 trapNetworkElemSerialNum,
		 trapPerceivedSeverity,
		 trapNetworkElemOperState,
		 trapNetworkElemAlarmStatus,  
		 trapNetworkElemAdminState,
		 trapNetworkElemAvailStatus,
		 trapText,
		 trapChangedObjectId,
		 trapChangedValueInteger,
		 trapNETrapLastTrapTimeStamp
		}
	DESCRIPTION
	"This trap is issued when the Laser Modules 12 Volt parameter goes out of range.
	 trapAdditionalInfoInteger variable contains current reading of 
	 the this parameter."
  ::= 12

  trapEA1000ModuleTempAlarm TRAP-TYPE
	ENTERPRISE gx2Ea1000
	VARIABLES
		{       
		 trapIdentifier,
		 trapNetworkElemModelNumber,
		 trapNetworkElemSerialNum,
		 trapPerceivedSeverity,
		 trapNetworkElemOperState,
		 trapNetworkElemAlarmStatus,  
		 trapNetworkElemAdminState,
		 trapNetworkElemAvailStatus,
		 trapText,
		 trapChangedObjectId,
		 trapChangedValueInteger,
		 trapNETrapLastTrapTimeStamp
		}
	DESCRIPTION
	"This trap is issued when the Laser Module Temperature goes out of range."
  ::= 13

  trapEA1000FlashAlarm TRAP-TYPE
	ENTERPRISE gx2Ea1000
	VARIABLES
		{       
		 trapIdentifier,
		 trapNetworkElemModelNumber,
		 trapNetworkElemSerialNum,
		 trapPerceivedSeverity,
		 trapNetworkElemOperState,
		 trapNetworkElemAlarmStatus,  
		 trapNetworkElemAdminState,
		 trapNetworkElemAvailStatus,
		 trapText,
		 trapChangedObjectId,
		 trapChangedValueInteger,
		 trapNETrapLastTrapTimeStamp
		}
	DESCRIPTION
	"This trap is issued when the Laser Modules detects an error during
	Flash memory operations."
  ::= 14

  trapEA1000LaserBiasCntLoopAlarm TRAP-TYPE
	ENTERPRISE gx2Ea1000
	VARIABLES
		{       
		 trapIdentifier,
		 trapNetworkElemModelNumber,
		 trapNetworkElemSerialNum,
		 trapPerceivedSeverity,
		 trapNetworkElemOperState,
		 trapNetworkElemAlarmStatus,  
		 trapNetworkElemAdminState,
		 trapNetworkElemAvailStatus,
		 trapText,
		 trapChangedObjectId,
		 trapChangedValueInteger,
		 trapNETrapLastTrapTimeStamp
		}
	DESCRIPTION
	"This trap is issued when the Laser Modules detects an error in its Laser Bias control loop
       operation."
  ::= 15

  trapEA1000BankBootAlarm TRAP-TYPE
	ENTERPRISE gx2Ea1000
	VARIABLES
		{       
		 trapIdentifier,
		 trapNetworkElemModelNumber,
		 trapNetworkElemSerialNum,
		 trapPerceivedSeverity,
		 trapNetworkElemOperState,
		 trapNetworkElemAlarmStatus,  
		 trapNetworkElemAdminState,
		 trapNetworkElemAvailStatus,
		 trapText,
		 trapChangedObjectId,
		 trapChangedValueInteger,
		 trapNETrapLastTrapTimeStamp
		}
	DESCRIPTION
	"This trap is issued when the Laser Modules detects an error while booting
	from bank 0 or bank 1."
  ::= 16

	trapEA1000LaserBiasCntLoopInitAlarm TRAP-TYPE
	ENTERPRISE gx2Ea1000
	VARIABLES
		{       
		 trapIdentifier,
		 trapNetworkElemModelNumber,
		 trapNetworkElemSerialNum,
		 trapPerceivedSeverity,
		 trapNetworkElemOperState,
		 trapNetworkElemAlarmStatus,  
		 trapNetworkElemAdminState,
		 trapNetworkElemAvailStatus,
		 trapText,
		 trapChangedObjectId,
		 trapChangedValueInteger,
		 trapNETrapLastTrapTimeStamp
		}
	DESCRIPTION
	"This trap is issued when the Laser Bias Control loop init fails."
  ::= 17

	trapEA1000RFParamInitAlarm TRAP-TYPE
	ENTERPRISE gx2Ea1000
	VARIABLES
		{       
		 trapIdentifier,
		 trapNetworkElemModelNumber,
		 trapNetworkElemSerialNum,
		 trapPerceivedSeverity,
		 trapNetworkElemOperState,
		 trapNetworkElemAlarmStatus,  
		 trapNetworkElemAdminState,
		 trapNetworkElemAvailStatus,
		 trapText,
		 trapChangedObjectId,
		 trapChangedValueInteger,
		 trapNETrapLastTrapTimeStamp
		}
	DESCRIPTION
	"This trap is issued when the RF parameter Init fails."
  ::= 18

	trapEA1000TECParamInitAlarm TRAP-TYPE
	ENTERPRISE gx2Ea1000
	VARIABLES
		{       
		 trapIdentifier,
		 trapNetworkElemModelNumber,
		 trapNetworkElemSerialNum,
		 trapPerceivedSeverity,
		 trapNetworkElemOperState,
		 trapNetworkElemAlarmStatus,  
		 trapNetworkElemAdminState,
		 trapNetworkElemAvailStatus,
		 trapText,
		 trapChangedObjectId,
		 trapChangedValueInteger,
		 trapNETrapLastTrapTimeStamp
		}
	DESCRIPTION
	"This trap is issued when the TEC Parameter Init fails."
  ::= 19

	trapEA1000AttnTableInitAlarm TRAP-TYPE
	ENTERPRISE gx2Ea1000
	VARIABLES
		{       
		 trapIdentifier,
		 trapNetworkElemModelNumber,
		 trapNetworkElemSerialNum,
		 trapPerceivedSeverity,
		 trapNetworkElemOperState,
		 trapNetworkElemAlarmStatus,  
		 trapNetworkElemAdminState,
		 trapNetworkElemAvailStatus,
		 trapText,
		 trapChangedObjectId,
		 trapChangedValueInteger,
		 trapNETrapLastTrapTimeStamp
		}
	DESCRIPTION
	"This trap is issued when the Attenuator Table Init fails."
  ::= 20

	trapEA1000PowerMeterTableInitAlarm TRAP-TYPE
	ENTERPRISE gx2Ea1000
	VARIABLES
		{       
		 trapIdentifier,
		 trapNetworkElemModelNumber,
		 trapNetworkElemSerialNum,
		 trapPerceivedSeverity,
		 trapNetworkElemOperState,
		 trapNetworkElemAlarmStatus,  
		 trapNetworkElemAdminState,
		 trapNetworkElemAvailStatus,
		 trapText,
		 trapChangedObjectId,
		 trapChangedValueInteger,
		 trapNETrapLastTrapTimeStamp
		}
	DESCRIPTION
	"This trap is issued when the Power Meter Table Init fails."
  ::= 21

	trapEA1000LaserDataCRCAlarm TRAP-TYPE
	ENTERPRISE gx2Ea1000
	VARIABLES
		{       
		 trapIdentifier,
		 trapNetworkElemModelNumber,
		 trapNetworkElemSerialNum,
		 trapPerceivedSeverity,
		 trapNetworkElemOperState,
		 trapNetworkElemAlarmStatus,  
		 trapNetworkElemAdminState,
		 trapNetworkElemAvailStatus,
		 trapText,
		 trapChangedObjectId,
		 trapChangedValueInteger,
		 trapNETrapLastTrapTimeStamp
		}
	DESCRIPTION
	"This trap is issued when the Laser Data CRC is incorrect."
  ::= 22

	trapEA1000AlarmDataCRCAlarm TRAP-TYPE
	ENTERPRISE gx2Ea1000
	VARIABLES
		{       
		 trapIdentifier,
		 trapNetworkElemModelNumber,
		 trapNetworkElemSerialNum,
		 trapPerceivedSeverity,
		 trapNetworkElemOperState,
		 trapNetworkElemAlarmStatus,  
		 trapNetworkElemAdminState,
		 trapNetworkElemAvailStatus,
		 trapText,
		 trapChangedObjectId,
		 trapChangedValueInteger,
		 trapNETrapLastTrapTimeStamp
		}
	DESCRIPTION
	"This trap is issued when the Alarm Data CRC is incorrect."
  ::= 23

	trapEA1000FactoryDataCRCAlarm TRAP-TYPE
	ENTERPRISE gx2Ea1000
	VARIABLES
		{       
		 trapIdentifier,
		 trapNetworkElemModelNumber,
		 trapNetworkElemSerialNum,
		 trapPerceivedSeverity,
		 trapNetworkElemOperState,
		 trapNetworkElemAlarmStatus,  
		 trapNetworkElemAdminState,
		 trapNetworkElemAvailStatus,
		 trapText,
		 trapChangedObjectId,
		 trapChangedValueInteger,
		 trapNETrapLastTrapTimeStamp
		}
	DESCRIPTION
	"This trap is issued when the Factory Data CRC is incorrect."
  ::= 24

	trapEA1000UserRFOffAlarm TRAP-TYPE
	ENTERPRISE gx2Ea1000
	VARIABLES
		{       
		 trapIdentifier,
		 trapNetworkElemModelNumber,
		 trapNetworkElemSerialNum,
		 trapPerceivedSeverity,
		 trapNetworkElemOperState,
		 trapNetworkElemAlarmStatus,  
		 trapNetworkElemAdminState,
		 trapNetworkElemAvailStatus,
		 trapText,
		 trapChangedObjectId,
		 trapChangedValueInteger,
		 trapNETrapLastTrapTimeStamp
		}
	DESCRIPTION
	"This trap is issued when the the User RF is turned off."
  ::= 25

	trapEA1000UserOpticalOffAlarm TRAP-TYPE
	ENTERPRISE gx2Ea1000
	VARIABLES
		{       
		 trapIdentifier,
		 trapNetworkElemModelNumber,
		 trapNetworkElemSerialNum,
		 trapPerceivedSeverity,
		 trapNetworkElemOperState,
		 trapNetworkElemAlarmStatus,  
		 trapNetworkElemAdminState,
		 trapNetworkElemAvailStatus,
		 trapText,
		 trapChangedObjectId,
		 trapChangedValueInteger,
		 trapNETrapLastTrapTimeStamp
		}
	DESCRIPTION
	"This trap is issued when the User Optical Power is turned off."
  ::= 26

	trapEA1000ResetFactoryDefaultAlarm TRAP-TYPE
	ENTERPRISE gx2Ea1000
	VARIABLES
		{       
		 trapIdentifier,
		 trapNetworkElemModelNumber,
		 trapNetworkElemSerialNum,
		 trapPerceivedSeverity,
		 trapNetworkElemOperState,
		 trapNetworkElemAlarmStatus,  
		 trapNetworkElemAdminState,
		 trapNetworkElemAvailStatus,
		 trapText,
		 trapChangedObjectId,
		 trapChangedValueInteger,
		 trapNETrapLastTrapTimeStamp
		}
	DESCRIPTION
	"This trap is issued when the Factory Default Reset occurs."
  ::= 27

  END
