-- **********************************************************
-- Copyright Opmantek, Ltd.  All rights reserved. 
-- **********************************************************

OPMANTEK-MIB DEFINITIONS ::= BEGIN

IMPORTS
	OBJECT-TYPE, OBJECT-IDENTITY, MODULE-IDENTITY, NOTIFICATION-TYPE,
	Counter32, Integer32, TimeTicks, enterprises
		FROM SNMPv2-SMI
	DisplayString, DateAndTime
		FROM SNMPv2-TC
	MODULE-COMPLIANCE, OBJECT-GROUP, NOTIFICATION-GROUP
		FROM SNMPv2-CONF;
     
opmantek MODULE-IDENTITY
	LAST-UPDATED "201702100000Z"
	ORGANIZATION "Opmantek Ltd"
	CONTACT-INFO
		"Opmantek Ltd
		Level 13
		50 Cavill Avenue
		Surfers Paradise, Queensland 4217
		Australia
		Tel: 
		Web: https://community.opmantek.com
		"
	DESCRIPTION
		"Opmantek root assignements
		This module defines the Opmantek SNMP MIB root
		and its primary subtrees.
		"

 -- Revision log, in reverse chronological order

	REVISION      "201705080000Z"
	DESCRIPTION
		"Added three new object to the trap omkNodeGroup, omkNodeRole, omkNodeCountry and omkNodeProperty."

	REVISION      "201702100000Z"
	DESCRIPTION
		"Added missing values to omkEvent, omkProbableCause and omkAlarmId."

	REVISION      "201702080000Z"
	DESCRIPTION
		"Added two new objects to the trap, omkProbableCause and omkAlarmId."

	REVISION      "201503160000Z"
	DESCRIPTION
		"The initial revision."
	::= { enterprises 4818 }     

omkNotifications OBJECT-IDENTITY
	STATUS  current
	DESCRIPTION
		"Parent of all Opmantek notifications (traps, informs)."
	::= { opmantek 1 }

omkObjects OBJECT-IDENTITY
	STATUS  current
	DESCRIPTION
		"Parent of all Opmantek notifications (traps, informs)."
	::= { opmantek 2 }

omkEvent NOTIFICATION-TYPE
	OBJECTS     { omkId, omkTime, omkDate, omkNode, omkHost, omkEventName, omkElement, omkState, omkStateful, omkDetails, omkType, omkPriority, omkLevel, omkProbableCause, omkAlarmId, omkNodeGroup, omkNodeRole, omkNodeCountry, omkNodeProperty }
	STATUS      current
	DESCRIPTION 
		"The Opmantek Event coming from opEvents with rich data about state and priority."
	::= { omkNotifications 1 }

nmisEvent NOTIFICATION-TYPE
	OBJECTS     { nmisTime, nmisNode, nmisEvent, nmisLevel, nmisElement, nmisDetails }
	STATUS      current
	DESCRIPTION 
		"The NMIS Event with standard event properties."
	::= { omkNotifications 2 }

omkEventGroup OBJECT-GROUP
	OBJECTS {
		omkId,
		omkTime,
		omkDate,
		omkNode,
		omkHost,
		omkEventName,
		omkElement,
		omkState,
		omkStateful,
		omkDetails,
		omkType,
		omkPriority,
		omkLevel,
		omkProbableCause,
		omkAlarmId,
		omkNodeGroup,
		omkNodeRole,
		omkNodeCountry,
		omkNodeProperty
	} 
	STATUS current
	DESCRIPTION
		"These objects make up the Event details in the OMK notification."
	::= { omkObjects 1 }

omkId OBJECT-TYPE
	SYNTAX      DisplayString
	MAX-ACCESS  read-only
	STATUS      current
	DESCRIPTION 
		"A globally unique Event ID"
	::= { omkEventGroup 1 }

omkTime OBJECT-TYPE
	SYNTAX      DisplayString
	MAX-ACCESS  read-only
	STATUS      current
	DESCRIPTION 
		"Unix time of the event (seconds since 1970)"
	::= { omkEventGroup 2 }

omkDate OBJECT-TYPE
	SYNTAX      DisplayString
	MAX-ACCESS  read-only
	STATUS      current
	DESCRIPTION 
		"The event time in human readable format"
	::= { omkEventGroup 3 }

omkNode OBJECT-TYPE
	SYNTAX      DisplayString
	MAX-ACCESS  read-only
	STATUS      current
	DESCRIPTION 
		"The NMIS node name"
	::= { omkEventGroup 4 }

omkHost OBJECT-TYPE
	SYNTAX      DisplayString
	MAX-ACCESS  read-only
	STATUS      current
	DESCRIPTION 
		"The IP address or hostname"
	::= { omkEventGroup 5 }

omkEventName OBJECT-TYPE
	SYNTAX      DisplayString
	MAX-ACCESS  read-only
	STATUS      current
	DESCRIPTION 
		"Name of the event"
	::= { omkEventGroup 6 }

omkElement OBJECT-TYPE
	SYNTAX      DisplayString
	MAX-ACCESS  read-only
	STATUS      current
	DESCRIPTION 
		"What is the element of the node"
	::= { omkEventGroup 7 }

omkState OBJECT-TYPE
	SYNTAX      DisplayString
	MAX-ACCESS  read-only
	STATUS      current
	DESCRIPTION 
		"Is the state true or false, up/down, open/closed, etc."
	::= { omkEventGroup 8 }

omkStateful OBJECT-TYPE
	SYNTAX      DisplayString
	MAX-ACCESS  read-only
	STATUS      current
	DESCRIPTION 
		"Stateful object name"
	::= { omkEventGroup 9 }

omkDetails OBJECT-TYPE
	SYNTAX      DisplayString
	MAX-ACCESS  read-only
	STATUS      current
	DESCRIPTION 
		"Other event details"
	::= { omkEventGroup 10 }

omkType OBJECT-TYPE
	SYNTAX      DisplayString
	MAX-ACCESS  read-only
	STATUS      current
	DESCRIPTION 
		"Where did the event originate?"
	::= { omkEventGroup 11 }

omkPriority OBJECT-TYPE
	SYNTAX      DisplayString
	MAX-ACCESS  read-only
	STATUS      current
	DESCRIPTION 
		"opEvents priority level, see opEvents priority levels vs. NMIS and Syslog levels"
	::= { omkEventGroup 12 }

omkLevel OBJECT-TYPE
	SYNTAX      DisplayString
	MAX-ACCESS  read-only
	STATUS      current
	DESCRIPTION 
		"NMIS Event Level"
	::= { omkEventGroup 13 }

omkProbableCause OBJECT-TYPE
	SYNTAX      DisplayString
	MAX-ACCESS  read-only
	STATUS      current
	DESCRIPTION 
		"The Probable Cause carried from other possible sources"
	::= { omkEventGroup 14 }

omkAlarmId OBJECT-TYPE
	SYNTAX      INTEGER
	MAX-ACCESS  read-only
	STATUS      current
	DESCRIPTION 
		"The AlarmID carried from other possible sources"
	::= { omkEventGroup 15 }    

omkNodeGroup OBJECT-TYPE
	SYNTAX      DisplayString
	MAX-ACCESS  read-only
	STATUS      current
	DESCRIPTION 
		"The name of the group for the node related to this event"
	::= { omkEventGroup 16 }

omkNodeRole OBJECT-TYPE
	SYNTAX      DisplayString
	MAX-ACCESS  read-only
	STATUS      current
	DESCRIPTION 
		"The name of the role for the node related to this event"
	::= { omkEventGroup 17 }

omkNodeCountry OBJECT-TYPE
	SYNTAX      DisplayString
	MAX-ACCESS  read-only
	STATUS      current
	DESCRIPTION 
		"The name of the country for the node related to this event"
	::= { omkEventGroup 18 }

omkNodeProperty OBJECT-TYPE
	SYNTAX      DisplayString
	MAX-ACCESS  read-only
	STATUS      current
	DESCRIPTION 
		"The name of the property for the node related to this event"
	::= { omkEventGroup 19 }

nmisEventGroup OBJECT-GROUP
	OBJECTS {
		nmisTime,
		nmisNode,
		nmisEvent,
		nmisLevel,
		nmisElement,
		nmisDetails
	} 
	STATUS current
	DESCRIPTION
		"These objects make up the Event details in the NMIS notification."
	::= { omkObjects 2 }

nmisTime OBJECT-TYPE
	SYNTAX      DisplayString
	MAX-ACCESS  read-only
	STATUS      current
	DESCRIPTION 
		"TODO"
	::= { nmisEventGroup 1 }

nmisNode OBJECT-TYPE
	SYNTAX      DisplayString
	MAX-ACCESS  read-only
	STATUS      current
	DESCRIPTION 
		"TODO"
	::= { nmisEventGroup 2 }

nmisEvent OBJECT-TYPE
	SYNTAX      DisplayString
	MAX-ACCESS  read-only
	STATUS      current
	DESCRIPTION 
		"TODO"
	::= { nmisEventGroup 3 }

nmisLevel OBJECT-TYPE
	SYNTAX      DisplayString
	MAX-ACCESS  read-only
	STATUS      current
	DESCRIPTION 
		"TODO"
	::= { nmisEventGroup 4 }

nmisElement OBJECT-TYPE
	SYNTAX      DisplayString
	MAX-ACCESS  read-only
	STATUS      current
	DESCRIPTION 
		"TODO"
	::= { nmisEventGroup 5 }

nmisDetails OBJECT-TYPE
	SYNTAX      DisplayString
	MAX-ACCESS  read-only
	STATUS      current
	DESCRIPTION 
		"TODO"
	::= { nmisEventGroup 6 }


END -- end of module OPMANTEK-MIB.
