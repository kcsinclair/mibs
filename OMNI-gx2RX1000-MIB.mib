OMNI-gx2RX1000-MIB DEFINITIONS ::= BEGIN

    IMPORTS
	IpAddress, TimeTicks
					      FROM RFC1155-SMI
	OBJECT-TYPE
					      FROM RFC-1212
	sysUpTime, DisplayString
					      FROM RFC1213-MIB
	TRAP-TYPE
					      FROM RFC-1215
	gi, motproxies
					      FROM NLS-BBNIDENT-MIB
	gx2Rx1000
					      FROM GX2HFC-MIB

	trapIdentifier,trapNetworkElemModelNumber,
	trapNetworkElemSerialNum, trapPerceivedSeverity,
	trapNetworkElemOperState, trapNetworkElemAlarmStatus,
	trapNetworkElemAdminState, trapNetworkElemAvailStatus,
	trapText, trapNETrapLastTrapTimeStamp, trapChangedObjectId,
	trapChangedValueInteger, trapChangedValueDisplayString
					      FROM NLSBBN-TRAPS-MIB;



	       -- This MIB module uses the extended OBJECT-TYPE macro as
	       -- defined in RFC1212 and the TRAP-TYPE macro as defined
	       -- in RFC 1215.

		   --REVISION	"3" Jan 20, 2003
		   --DESCRIPTION
		   --			Added revision and description comment section


		--    OMNISTAR Forward Path Receiver Module  MIB MODULE

	-- This MIB module defines information for management of HFC networks
		--
		-- The MIB module assumes that all generic (static) network element
		-- information is defined in a different module such as the HFC module
		-- The MIB consists of two groups:
		-- the device type descriptor subgroup and
		-- gx2Rx1000 Network Elements subgroup.
		-- The device type descriptor subgroup is used to define
		-- parameters specific to gx2Rx1000 device type.
		-- These parameters are common across all network elements
		-- from gx2Rx1000 device type.
		--
		-- The gx2Rx1000 Network Elements subgroup is
		-- a list of gx2Rx1000 type elements in the
		-- current network topology with nominal
		-- and current parameter values for the
		-- individual network elements; the individual
		-- network elements are identified by
		-- index from hfcCommonTable.
		-- That implies what hfcCommonTableIndex and
		-- gx2Rx1000TableIndex are equal for each individual
		-- network element.
		-- This table is an extension of the hfcCommonTable
		-- for all elements of gx2Rx1000 type.
		--
		-- Both groups are mandatory for management of gx2Rx1000 devices.

-- ****************************************************************************
		--
		-- All floating point numbers will be represented by an IEEE 32 Bit number.
		-- Conversion of this number must be done on the user interface to view the
		-- actual floating point number.
		--

		Float ::= Counter  -- UNSIGNED (32 BITS)

-- ****************************************************************************

		-- gx2Rx1000 Device Descriptor subgroup.

		-- The device type descriptor subgroup is used to define
		-- parameters specific to gx2Rx1000 device type.
		-- These parameters are common across all network elements
		-- from gx2Rx1000 device type.


		gx2Rx1000Descriptor OBJECT IDENTIFIER ::= {gx2Rx1000 1}



--*****************************************************************************
		--              gx2Rx1000 Table

		-- Contains a list of all gx2Rx1000 type devices in
		-- the network. Each device is characterized with
		-- current network topology information, with nominal
		-- and current parameter values for the
		-- individual network elements;
		--
		-- The individual network elements indentified by
		-- index from hfcCommonTable.
		-- That implies what hfcCommonTableIndex and
		-- gx2Rx1000TableIndex are equal for each individual
		-- nettwork element.
		-- This table should be used as an extension of the hfcCommonTable
		-- for all elements of gx2Rx1000 type.


	       gx2Rx1000AnalogTable                    OBJECT-TYPE
			 SYNTAX             SEQUENCE OF Gx2Rx1000AnalogEntry
			 ACCESS             not-accessible
			 STATUS             mandatory
			 DESCRIPTION
			 "This table contains gx2Rx1000 specific parameters with
			  nominal and current values."
			 ::= { gx2Rx1000 2 }


	       gx2Rx1000AnalogEntry               OBJECT-TYPE
			 SYNTAX             Gx2Rx1000AnalogEntry
			 ACCESS             not-accessible
			 STATUS             mandatory
			 DESCRIPTION
			 "This list contains digital product class and the
			  associated RF channel parameters and descriptions."
			 INDEX { fprgx2Rx1000AnalogTableIndex }
			 ::= { gx2Rx1000AnalogTable  1}

--*************************************************************************
	       gx2Rx1000DigitalTable                    OBJECT-TYPE
			 SYNTAX             SEQUENCE OF Gx2Rx1000DigitalEntry
			 ACCESS             not-accessible
			 STATUS             mandatory
			 DESCRIPTION
			 "This table contains gx2Rx1000 specific parameters with
			  nominal and current values."
			 ::= { gx2Rx1000 3 }

	       gx2Rx1000DigitalEntry               OBJECT-TYPE
			 SYNTAX             Gx2Rx1000DigitalEntry
			 ACCESS             not-accessible
			 STATUS             mandatory
			 DESCRIPTION
			 "This list contains digital product class and the
			  associated RF channel parameters and descriptions."
			 INDEX { fprgx2Rx1000DigitalTableIndex }
			 ::= { gx2Rx1000DigitalTable  2}

--*************************************************************************
	       gx2Rx1000StatusTable                    OBJECT-TYPE
			 SYNTAX             SEQUENCE OF Gx2Rx1000StatusEntry
			 ACCESS             not-accessible
			 STATUS             mandatory
			 DESCRIPTION
			 "This table contains gx2Rx1000 specific parameters with
			  nominal and current values."
			 ::= { gx2Rx1000 4 }

	       gx2Rx1000StatusEntry               OBJECT-TYPE
			 SYNTAX             Gx2Rx1000StatusEntry
			 ACCESS             not-accessible
			 STATUS             mandatory
			 DESCRIPTION
			 "This list contains digital product class and the
			  associated RF channel parameters and descriptions."
			 INDEX { fprgx2Rx1000StatusTableIndex }
			 ::= { gx2Rx1000StatusTable  3}

--*************************************************************************
	       gx2Rx1000FactoryTable                    OBJECT-TYPE
			 SYNTAX             SEQUENCE OF Gx2Rx1000FactoryEntry
			 ACCESS             not-accessible
			 STATUS             mandatory
			 DESCRIPTION
			 "This table contains gx2Rx1000 specific parameters with
			  nominal and current values."
			 ::= { gx2Rx1000 5 }

	       gx2Rx1000FactoryEntry               OBJECT-TYPE
			 SYNTAX             Gx2Rx1000FactoryEntry
			 ACCESS             not-accessible
			 STATUS             mandatory
			 DESCRIPTION
			 "This list contains digital product class and the
			  associated RF channel parameters and descriptions."
			 INDEX { fprgx2Rx1000FactoryTableIndex }
			 ::= { gx2Rx1000FactoryTable  4}
--***********************************************************************

	       gx2Rx1000HoldTimeTable                    OBJECT-TYPE
			 SYNTAX             SEQUENCE OF Gx2Rx1000HoldTimeEntry
			 ACCESS             not-accessible
			 STATUS             mandatory
			 DESCRIPTION
			 "This table contains gx2Rx1000 specific parameters with
			  nominal and current values."
			 ::= { gx2Rx1000 6 }

	       gx2Rx1000HoldTimeEntry               OBJECT-TYPE
			 SYNTAX             Gx2Rx1000HoldTimeEntry
			 ACCESS             not-accessible
			 STATUS             mandatory
			 DESCRIPTION
			 "This list contains digital product class and the
			  associated RF channel parameters and descriptions."
			 INDEX { gx2Rx1000HoldTimeTableIndex, gx2Rx1000HoldTimeSpecIndex }
			 ::= { gx2Rx1000HoldTimeTable  5}

--***********************************************************************

	     Gx2Rx1000AnalogEntry    ::= SEQUENCE
	    {
		fprgx2Rx1000AnalogTableIndex         INTEGER,

		--           Analog Parameters

		fprlabelOptPower			DisplayString (SIZE (0..80)),
		fpruomOptPower			DisplayString (SIZE (0..80)),
		fprmajorHighOptPower		Float,
		fprmajorLowOptPower		Float,
		fprminorHighOptPower		Float,
		fprminorLowOptPower		Float,
		fprcurrentValueOptPower		Float,
		fprstateFlagOptPower		INTEGER,
		fprminValueOptPower		Float,
		fprmaxValueOptPower 		Float,
		fpralarmStateOptPower		INTEGER,

		fprlabelModTemp			DisplayString (SIZE (0..80)),
		fpruomModTemp			DisplayString (SIZE (0..80)),
		fprmajorHighModTemp		Float,
		fprmajorLowModTemp		Float,
		fprminorHighModTemp		Float,
		fprminorLowModTemp		Float,
		fprcurrentValueModTemp		Float,
		fprstateFlagModTemp		INTEGER,
		fprminValueModTemp		Float,
		fprmaxValueModTemp		Float,
		fpralarmStateModTemp		INTEGER,

		fprlabelSinkTemp			DisplayString (SIZE (0..80)),
		fpruomSinkTemp			DisplayString (SIZE (0..80)),
		fprmajorHighSinkTemp		Float,
		fprmajorLowSinkTemp		Float,
		fprminorHighSinkTemp		Float,
		fprminorLowSinkTemp		Float,
		fprcurrentValueSinkTemp		Float,
		fprstateFlagSinkTemp		INTEGER,
		fprminValueSinkTemp		Float,
		fprmaxValueSinkTemp		Float,
		fpralarmStateSinkTemp		INTEGER,

		fprlabelFanCurrent		DisplayString (SIZE (0..80)),
		fpruomFanCurrent			DisplayString (SIZE (0..80)),
		fprmajorHighFanCurrent		Float,
		fprmajorLowFanCurrent		Float,
		fprminorHighFanCurrent		Float,
		fprminorLowFanCurrent		Float,
		fprcurrentValueFanCurrent	Float,
		fprstateFlagFanCurrent		INTEGER,
		fprminValueFanCurrent		Float,
		fprmaxValueFanCurrent 		Float,
		fpralarmStateFanCurrent		INTEGER,

		fprlabel12Volt			DisplayString (SIZE (0..80)),
		fpruom12Volt			DisplayString (SIZE (0..80)),
		fprmajorHigh12Volt		Float,
		fprmajorLow12Volt			Float,
		fprminorHigh12Volt		Float,
		fprminorLow12Volt			Float,
		fprcurrentValue12Volt		Float,
		fprstateFlag12Volt		INTEGER,
		fprminValue12Volt			Float,
		fprmaxValue12Volt			Float,
		fpralarmState12Volt		INTEGER
		}

		-- ****************  Digital Parameters ***********************
      Gx2Rx1000DigitalEntry   ::= SEQUENCE
      {

		fprgx2Rx1000DigitalTableIndex         INTEGER,
		fprlabelSlopeSetting 		DisplayString (SIZE (0..80)),
		fprvalueSlopeSetting		INTEGER,
		fprenumSlopeSetting		DisplayString (SIZE (0..80)),
		fprstateFlagSlopeSetting      	INTEGER,

		fprlabelAttnSetting		DisplayString (SIZE (0..80)),
		fprvalueAttnSetting		INTEGER,
		fprenumAttnSetting		DisplayString (SIZE (0..80)),
		fprstateFlagAttnSetting      	INTEGER,

		fprlabelWavelength	 	DisplayString (SIZE (0..80)),
		fprvalueWavelength		INTEGER,
		fprenumWavelength			DisplayString (SIZE (0..80)),
		fprstateFlagWavelength       	INTEGER,

		fprlabelFactoryDefault		DisplayString (SIZE (0..80)),
		fprvalueFactoryDefault		INTEGER,
		fprenumFactoryDefault		DisplayString (SIZE (0..80)),
		fprstateFlagFactoryDefault   	INTEGER,

		fprlabelSwModeThreshold	 	DisplayString (SIZE (0..80)),
		fprvalueSwModeThreshold		INTEGER,
		fprenumSwModeThreshold		DisplayString (SIZE (0..80)),
		fprstateFlagSwModeThreshold   INTEGER,

		fprlabelSwModeSetting		DisplayString (SIZE (0..80)),
		fprvalueSwModeSetting		INTEGER,
		fprenumSwModeSetting		DisplayString (SIZE (0..80)),
		fprstateFlagSwModeSetting     INTEGER

		}

		-- ****************  Status Parameters ************************************
      Gx2Rx1000StatusEntry    ::= SEQUENCE
      {

		fprgx2Rx1000StatusTableIndex         INTEGER,
		fprlabelBoot				DisplayString (SIZE (0..80)),
		fprvalueBoot				INTEGER,
		fprstateflagBoot				INTEGER,

		fprlabelFlash				DisplayString (SIZE (0..80)),
		fprvalueFlash				INTEGER,
		fprstateflagFlash				INTEGER,

		fprlabelFactoryDataCRC 			DisplayString (SIZE (0..80)),
		fprvalueFactoryDataCRC			INTEGER,
		fprstateflagFactoryDataCRC		INTEGER,

		fprlabelAlarmDataCRC 			DisplayString (SIZE (0..80)),
		fprvalueAlarmDataCRC			INTEGER,
		fprstateflagAlarmDataCRC		INTEGER,

		fprlabelCalibrationDataCRC		DisplayString (SIZE (0..80)),
		fprvalueCalibrationDataCRC		INTEGER,
		fprstateflagCalibrationDataCRC	INTEGER,

		fprlabelFacCalSettingCRC		DisplayString (SIZE (0..80)),
		fprvalueFacCalSettingCRC		INTEGER,
		fprstateflagFacCalSettingCRC		INTEGER,

		fprlabelInputSig				DisplayString (SIZE (0..80)),
		fprvalueInputSig				INTEGER,
		fprstateflagInputSig			INTEGER

		}


		-- ****************  Factory Parameters *************************************
      Gx2Rx1000FactoryEntry    ::= SEQUENCE
      {
		fprgx2Rx1000FactoryTableIndex         INTEGER,
		fprbootControlByte  	INTEGER,
		fprbootStatusByte   	INTEGER,
		fprbank0CRC    			INTEGER,
		fprbank1CRC    			INTEGER,
		fprprgEEPROMByte    	INTEGER,
		fprfactoryCRC    		INTEGER,
		fprcalculateCRC    		INTEGER,
		fprhourMeter    		INTEGER,
		fprflashPrgCntA    		INTEGER,
		fprflashPrgCntB    		INTEGER,
		fprfwRev0	    		DisplayString (SIZE (0..80)),
		fprfwRev1	    		DisplayString (SIZE (0..80))

		}

		-- ****************  Hold Time Parameters *************************************
	    Gx2Rx1000HoldTimeEntry    ::= SEQUENCE
	    {
		gx2Rx1000HoldTimeTableIndex        INTEGER,
		gx2Rx1000HoldTimeSpecIndex         INTEGER,
		gx2Rx1000HoldTimeData              INTEGER
		}

            -- ************** Analog Parameters ****************************
		fprgx2Rx1000AnalogTableIndex              OBJECT-TYPE
			   SYNTAX           INTEGER (1..4294967295)
			   ACCESS           read-only
			   STATUS           mandatory
			   DESCRIPTION
			   "The value of this object identifies the network
			    element. This index is equal to the
			    hfcCommonTableIndex for the same element."
			   ::= { gx2Rx1000AnalogEntry 1}

-- New Parameter

		fprlabelOptPower             OBJECT-TYPE
			   SYNTAX           DisplayString (SIZE (0..80))
			   ACCESS           read-only
			   STATUS           optional
			   DESCRIPTION
			   "The value of this object provides the label of the
			    Optical Power Analog parameter."
			   ::= { gx2Rx1000AnalogEntry 2}

		fpruomOptPower               OBJECT-TYPE
			   SYNTAX           DisplayString (SIZE (0..80))
			   ACCESS           read-only
			   STATUS           optional
			   DESCRIPTION
			   "The value of this object provides the Unit of Measure of the
			    Optical Power Analog parameter."
			   ::= { gx2Rx1000AnalogEntry 3}

		fprmajorHighOptPower         OBJECT-TYPE
			   SYNTAX           Float
			   ACCESS           read-only
			   STATUS           mandatory
			   DESCRIPTION
			   "The value of this object provides the Major High alarm value
			          of the Optical Power Analog parameter. This value is a floating
			    point number that is represented as an IEEE 32 bit number."
			   ::= { gx2Rx1000AnalogEntry 4}


		fprmajorLowOptPower          OBJECT-TYPE
			   SYNTAX           Float
			   ACCESS           read-only
			   STATUS           mandatory
			   DESCRIPTION
			   "The value of this object provides the Major Low alarm value
			          of the Optical Power Analog parameter. This value is a floating
			    point number that is represented as an IEEE 32 bit number."
			   ::= { gx2Rx1000AnalogEntry 5}

		fprminorHighOptPower         OBJECT-TYPE
			   SYNTAX           Float
			   ACCESS           read-only
			   STATUS           mandatory
			   DESCRIPTION
			   "The value of this object provides the Minor High alarm value
			          of the Optical Power Analog parameter. This value is a floating
			    point number that is represented as an IEEE 32 bit number."
			   ::= { gx2Rx1000AnalogEntry 6}

		fprminorLowOptPower          OBJECT-TYPE
			   SYNTAX           Float
			   ACCESS           read-only
			   STATUS           mandatory
			   DESCRIPTION
			   "The value of this object provides the Minor Low alarm value
			          of the Optical Power Analog parameter. This value is a floating
			    point number that is represented as an IEEE 32 bit number."
			   ::= { gx2Rx1000AnalogEntry 7}

		fprcurrentValueOptPower      OBJECT-TYPE
			   SYNTAX           Float
			   ACCESS           read-only
			   STATUS           mandatory
			   DESCRIPTION
			   "The value of this object provides the Current value
			          of the Optical Power Analog parameter. This value is a floating
			    point number that is represented as an IEEE 32 bit number."
			   ::= { gx2Rx1000AnalogEntry 8}

		fprstateFlagOptPower         OBJECT-TYPE
			   SYNTAX           INTEGER
								{
								hidden(1),
								read-only(2),
								updateable(3)
								}
			   ACCESS           read-only
			   STATUS           mandatory
			   DESCRIPTION
			   "The value of this object provides the state
			    of the Optical Power Analog parameter. (0-Hidden
			          1-Read-Only, 2-Updateable)."
			   ::= { gx2Rx1000AnalogEntry 9}

		fprminValueOptPower          OBJECT-TYPE
			   SYNTAX           Float
			   ACCESS           read-only
			   STATUS           mandatory
			   DESCRIPTION
			   "The value of this object provides the minimum value
			          of the Optical Power Analog parameter. This value is a floating
			    point number that is represented as an IEEE 32 bit number."
			   ::= { gx2Rx1000AnalogEntry 10}

		fprmaxValueOptPower          OBJECT-TYPE
			   SYNTAX           Float
			   ACCESS           read-only
			   STATUS           mandatory
			   DESCRIPTION
			   "The value of this object provides the maximum value
			          of the Optical Power Analog parameter. This value is a floating
			    point number that is represented as an IEEE 32 bit number."
			   ::= { gx2Rx1000AnalogEntry 11}

		fpralarmStateOptPower        OBJECT-TYPE
			   SYNTAX           INTEGER
									{
									noAlarm(1),
									majorLowAlarm(2),
									minorLowAlarm(3),
									minorHighAlarm(4),
									majorHighAlarm(5),
									informational(6)
									}
			   ACCESS           read-only
			   STATUS           mandatory
			   DESCRIPTION
			   "The value of this object provides the curent alarm state of
			    the Optical Power Analog parameter."
			   ::= { gx2Rx1000AnalogEntry 12}

-- New Parameter

		fprlabelModTemp              OBJECT-TYPE
			   SYNTAX           DisplayString (SIZE (0..80))
			   ACCESS           read-only
			   STATUS           optional
			   DESCRIPTION
			   "The value of this object provides the label of the
			    Module Temperature Analog parameter."
			   ::= { gx2Rx1000AnalogEntry 13}

		fpruomModTemp                OBJECT-TYPE
			   SYNTAX           DisplayString (SIZE (0..80))
			   ACCESS           read-only
			   STATUS           optional
			   DESCRIPTION
			   "The value of this object provides the Unit of Measure of the
			    Module Temperature Analog parameter."
			   ::= { gx2Rx1000AnalogEntry 14}

		fprmajorHighModTemp          OBJECT-TYPE
			   SYNTAX           Float
			   ACCESS           read-only
			   STATUS           mandatory
			   DESCRIPTION
			   "The value of this object provides the Major High alarm value
			          of the Module Temperature Analog parameter. This value is a floating
			    point number that is represented as an IEEE 32 bit number."
			   ::= { gx2Rx1000AnalogEntry 15}


		fprmajorLowModTemp           OBJECT-TYPE
			   SYNTAX           Float
			   ACCESS           read-only
			   STATUS           mandatory
			   DESCRIPTION
			   "The value of this object provides the Major Low alarm value
			          of the Module Temperature Analog parameter. This value is a floating
			    point number that is represented as an IEEE 32 bit number."
			   ::= { gx2Rx1000AnalogEntry 16}

		fprminorHighModTemp          OBJECT-TYPE
			   SYNTAX           Float
			   ACCESS           read-only
			   STATUS           mandatory
			   DESCRIPTION
			   "The value of this object provides the Minor High alarm value
			          of the Module Temperature Analog parameter. This value is a floating
			    point number that is represented as an IEEE 32 bit number."
			   ::= { gx2Rx1000AnalogEntry 17}

		fprminorLowModTemp           OBJECT-TYPE
			   SYNTAX           Float
			   ACCESS           read-only
			   STATUS           mandatory
			   DESCRIPTION
			   "The value of this object provides the Minor Low alarm value
			          of the Module Temperature Analog parameter. This value is a floating
			    point number that is represented as an IEEE 32 bit number."
			   ::= { gx2Rx1000AnalogEntry 18}

		fprcurrentValueModTemp       OBJECT-TYPE
			   SYNTAX           Float
			   ACCESS           read-only
			   STATUS           mandatory
			   DESCRIPTION
			   "The value of this object provides the Current value
			          of the Module Temperature Analog parameter. This value is a floating
			    point number that is represented as an IEEE 32 bit number."
			   ::= { gx2Rx1000AnalogEntry 19}

		fprstateFlagModTemp          OBJECT-TYPE
			   SYNTAX           INTEGER
								{
								hidden(1),
								read-only(2),
								updateable(3)
								}
			   ACCESS           read-only
			   STATUS           mandatory
			   DESCRIPTION
			   "The value of this object provides the state
			    of the Module Temperature Analog parameter. (0-Hidden
			          1-Read-Only, 2-Updateable)."
			   ::= { gx2Rx1000AnalogEntry 20}

		fprminValueModTemp           OBJECT-TYPE
			   SYNTAX           Float
			   ACCESS           read-only
			   STATUS           mandatory
			   DESCRIPTION
			   "The value of this object provides the minimum value
			          of the Module Temperature Analog parameter. This value is a floating
			    point number that is represented as an IEEE 32 bit number."
			   ::= { gx2Rx1000AnalogEntry 21}

		fprmaxValueModTemp           OBJECT-TYPE
			   SYNTAX           Float
			   ACCESS           read-only
			   STATUS           mandatory
			   DESCRIPTION
			   "The value of this object provides the maximum value
			          of the Module Temperature Analog parameter. This value is a floating
			    point number that is represented as an IEEE 32 bit number."
			   ::= { gx2Rx1000AnalogEntry 22}

		fpralarmStateModTemp         OBJECT-TYPE
			   SYNTAX           INTEGER
									{
									noAlarm(1),
									majorLowAlarm(2),
									minorLowAlarm(3),
									minorHighAlarm(4),
									majorHighAlarm(5),
									informational(6)
									}
			   ACCESS           read-only
			   STATUS           mandatory
			   DESCRIPTION
			   "The value of this object provides the curent alarm state of
			    the Module Temperature Analog parameter."
			   ::= { gx2Rx1000AnalogEntry 23}

-- New Parameter

		fprlabelSinkTemp              OBJECT-TYPE
			   SYNTAX           DisplayString (SIZE (0..80))
			   ACCESS           read-only
			   STATUS           optional
			   DESCRIPTION
			   "The value of this object provides the label of the
			    Module Temperature Analog parameter."
			   ::= { gx2Rx1000AnalogEntry 24}

		fpruomSinkTemp                OBJECT-TYPE
			   SYNTAX           DisplayString (SIZE (0..80))
			   ACCESS           read-only
			   STATUS           optional
			   DESCRIPTION
			   "The value of this object provides the Unit of Measure of the
			    Module Temperature Analog parameter."
			   ::= { gx2Rx1000AnalogEntry 25}

		fprmajorHighSinkTemp          OBJECT-TYPE
			   SYNTAX           Float
			   ACCESS           read-only
			   STATUS           mandatory
			   DESCRIPTION
			   "The value of this object provides the Major High alarm value
			          of the Module Temperature Analog parameter. This value is a floating
			    point number that is represented as an IEEE 32 bit number."
			   ::= { gx2Rx1000AnalogEntry 26}


		fprmajorLowSinkTemp           OBJECT-TYPE
			   SYNTAX           Float
			   ACCESS           read-only
			   STATUS           mandatory
			   DESCRIPTION
			   "The value of this object provides the Major Low alarm value
			          of the Module Temperature Analog parameter. This value is a floating
			    point number that is represented as an IEEE 32 bit number."
			   ::= { gx2Rx1000AnalogEntry 27}

		fprminorHighSinkTemp          OBJECT-TYPE
			   SYNTAX           Float
			   ACCESS           read-only
			   STATUS           mandatory
			   DESCRIPTION
			   "The value of this object provides the Minor High alarm value
			          of the Module Temperature Analog parameter. This value is a floating
			    point number that is represented as an IEEE 32 bit number."
			   ::= { gx2Rx1000AnalogEntry 28}

		fprminorLowSinkTemp           OBJECT-TYPE
			   SYNTAX           Float
			   ACCESS           read-only
			   STATUS           mandatory
			   DESCRIPTION
			   "The value of this object provides the Minor Low alarm value
			          of the Module Temperature Analog parameter. This value is a floating
			    point number that is represented as an IEEE 32 bit number."
			   ::= { gx2Rx1000AnalogEntry 29}

		fprcurrentValueSinkTemp       OBJECT-TYPE
			   SYNTAX           Float
			   ACCESS           read-only
			   STATUS           mandatory
			   DESCRIPTION
			   "The value of this object provides the Current value
			          of the Module Temperature Analog parameter. This value is a floating
			    point number that is represented as an IEEE 32 bit number."
			   ::= { gx2Rx1000AnalogEntry 30}

		fprstateFlagSinkTemp          OBJECT-TYPE
			   SYNTAX           INTEGER
								{
								hidden(1),
								read-only(2),
								updateable(3)
								}
			   ACCESS           read-only
			   STATUS           mandatory
			   DESCRIPTION
			   "The value of this object provides the state
			    of the Module Temperature Analog parameter. (0-Hidden
			          1-Read-Only, 2-Updateable)."
			   ::= { gx2Rx1000AnalogEntry 31}

		fprminValueSinkTemp           OBJECT-TYPE
			   SYNTAX           Float
			   ACCESS           read-only
			   STATUS           mandatory
			   DESCRIPTION
			   "The value of this object provides the minimum value
			          of the Module Temperature Analog parameter. This value is a floating
			    point number that is represented as an IEEE 32 bit number."
			   ::= { gx2Rx1000AnalogEntry 32}

		fprmaxValueSinkTemp           OBJECT-TYPE
			   SYNTAX           Float
			   ACCESS           read-only
			   STATUS           mandatory
			   DESCRIPTION
			   "The value of this object provides the maximum value
			          of the Module Temperature Analog parameter. This value is a floating
			    point number that is represented as an IEEE 32 bit number."
			   ::= { gx2Rx1000AnalogEntry 33}

		fpralarmStateSinkTemp         OBJECT-TYPE
			   SYNTAX           INTEGER
									{
									noAlarm(1),
									majorLowAlarm(2),
									minorLowAlarm(3),
									minorHighAlarm(4),
									majorHighAlarm(5),
									informational(6)
									}
			   ACCESS           read-only
			   STATUS           mandatory
			   DESCRIPTION
			   "The value of this object provides the curent alarm state of
			    the Module Temperature Analog parameter."
			   ::= { gx2Rx1000AnalogEntry 34}

-- New Parameter

		fprlabelFanCurrent           OBJECT-TYPE
			   SYNTAX           DisplayString (SIZE (0..80))
			   ACCESS           read-only
			   STATUS           optional
			   DESCRIPTION
			   "The value of this object provides the label of the
			    Fan Current Analog parameter."
			   ::= { gx2Rx1000AnalogEntry 35}

		fpruomFanCurrent             OBJECT-TYPE
			   SYNTAX           DisplayString (SIZE (0..80))
			   ACCESS           read-only
			   STATUS           optional
			   DESCRIPTION
			   "The value of this object provides the Unit of Measure of the
			    Fan Current Analog parameter."
			   ::= { gx2Rx1000AnalogEntry 36}

		fprmajorHighFanCurrent       OBJECT-TYPE
			   SYNTAX           Float
			   ACCESS           read-only
			   STATUS           mandatory
			   DESCRIPTION
			   "The value of this object provides the Major High alarm value
			          of the Fan Current Analog parameter. This value is a floating
			    point number that is represented as an IEEE 32 bit number."
			   ::= { gx2Rx1000AnalogEntry 37}


		fprmajorLowFanCurrent        OBJECT-TYPE
			   SYNTAX           Float
			   ACCESS           read-only
			   STATUS           mandatory
			   DESCRIPTION
			   "The value of this object provides the Major Low alarm value
			          of the Fan Current Analog parameter. This value is a floating
			    point number that is represented as an IEEE 32 bit number."
			   ::= { gx2Rx1000AnalogEntry 38}

		fprminorHighFanCurrent       OBJECT-TYPE
			   SYNTAX           Float
			   ACCESS           read-only
			   STATUS           mandatory
			   DESCRIPTION
			   "The value of this object provides the Minor High alarm value
			          of the Fan Current Analog parameter. This value is a floating
			    point number that is represented as an IEEE 32 bit number."
			   ::= { gx2Rx1000AnalogEntry 39}

		fprminorLowFanCurrent        OBJECT-TYPE
			   SYNTAX           Float
			   ACCESS           read-only
			   STATUS           mandatory
			   DESCRIPTION
			   "The value of this object provides the Minor Low alarm value
			          of the Fan Current Analog parameter. This value is a floating
			    point number that is represented as an IEEE 32 bit number."
			   ::= { gx2Rx1000AnalogEntry 40}

		fprcurrentValueFanCurrent    OBJECT-TYPE
			   SYNTAX           Float
			   ACCESS           read-only
			   STATUS           mandatory
			   DESCRIPTION
			   "The value of this object provides the Current value
			          of the Fan Current Analog parameter. This value is a floating
			    point number that is represented as an IEEE 32 bit number."
			   ::= { gx2Rx1000AnalogEntry 41}

		fprstateFlagFanCurrent       OBJECT-TYPE
			   SYNTAX           INTEGER
								{
								hidden(1),
								read-only(2),
								updateable(3)
								}

			   ACCESS           read-only
			   STATUS           mandatory
			   DESCRIPTION
			   "The value of this object provides the state
			    of the Fan Current Analog parameter. (0-Hidden
			          1-Read-Only, 2-Updateable)."
			   ::= { gx2Rx1000AnalogEntry 42}

		fprminValueFanCurrent        OBJECT-TYPE
			   SYNTAX           Float
			   ACCESS           read-only
			   STATUS           mandatory
			   DESCRIPTION
			   "The value of this object provides the minimum value
			          of the Fan Current Analog parameter. This value is a floating
			    point number that is represented as an IEEE 32 bit number."
			   ::= { gx2Rx1000AnalogEntry 43}

		fprmaxValueFanCurrent        OBJECT-TYPE
			   SYNTAX           Float
			   ACCESS           read-only
			   STATUS           mandatory
			   DESCRIPTION
			   "The value of this object provides the maximum value
			          of the Fan Current Analog parameter. This value is a floating
			    point number that is represented as an IEEE 32 bit number."
			   ::= { gx2Rx1000AnalogEntry 44}

		fpralarmStateFanCurrent      OBJECT-TYPE
			   SYNTAX           INTEGER
									{
									noAlarm(1),
									majorLowAlarm(2),
									minorLowAlarm(3),
									minorHighAlarm(4),
									majorHighAlarm(5),
									informational(6)
									}
			   ACCESS           read-only
			   STATUS           mandatory
			   DESCRIPTION
			   "The value of this object provides the curent alarm state of
			    the Fan Current Analog parameter."
			   ::= { gx2Rx1000AnalogEntry 45}
-- New Parameter

		fprlabel12Volt               OBJECT-TYPE
			   SYNTAX           DisplayString (SIZE (0..80))
			   ACCESS           read-only
			   STATUS           optional
			   DESCRIPTION
			   "The value of this object provides the label of the
			    12v Current Analog parameter."
			   ::= { gx2Rx1000AnalogEntry 46}

		fpruom12Volt                 OBJECT-TYPE
			   SYNTAX           DisplayString (SIZE (0..80))
			   ACCESS           read-only
			   STATUS           optional
			   DESCRIPTION
			   "The value of this object provides the Unit of Measure of the
			    12v Current Analog parameter."
			   ::= { gx2Rx1000AnalogEntry 47}

		fprmajorHigh12Volt           OBJECT-TYPE
			   SYNTAX           Float
			   ACCESS           read-only
			   STATUS           mandatory
			   DESCRIPTION
			   "The value of this object provides the Major High alarm value
			          of the 12 Volt Current Analog parameter. This value is a floating
			    point number that is represented as an IEEE 32 bit number."
			   ::= { gx2Rx1000AnalogEntry 48}


		fprmajorLow12Volt            OBJECT-TYPE
			   SYNTAX           Float
			   ACCESS           read-only
			   STATUS           mandatory
			   DESCRIPTION
			   "The value of this object provides the Major Low alarm value
			          of the 12 Volt Current Analog parameter. This value is a floating
			    point number that is represented as an IEEE 32 bit number."
			   ::= { gx2Rx1000AnalogEntry 49}

		fprminorHigh12Volt           OBJECT-TYPE
			   SYNTAX           Float
			   ACCESS           read-only
			   STATUS           mandatory
			   DESCRIPTION
			   "The value of this object provides the Minor High alarm value
			          of the 12 Volt Current Analog parameter. This value is a floating
			    point number that is represented as an IEEE 32 bit number."
			   ::= { gx2Rx1000AnalogEntry 50}

		fprminorLow12Volt            OBJECT-TYPE
			   SYNTAX           Float
			   ACCESS           read-only
			   STATUS           mandatory
			   DESCRIPTION
			   "The value of this object provides the Minor Low alarm value
			          of the 12 Volt Current Analog parameter. This value is a floating
			    point number that is represented as an IEEE 32 bit number."
			   ::= { gx2Rx1000AnalogEntry 51}

		fprcurrentValue12Volt        OBJECT-TYPE
			   SYNTAX           Float
			   ACCESS           read-only
			   STATUS           mandatory
			   DESCRIPTION
			   "The value of this object provides the Current value
			          of the 12 Volt Current Analog parameter. This value is a floating
			    point number that is represented as an IEEE 32 bit number."
			   ::= { gx2Rx1000AnalogEntry 52}

		fprstateFlag12Volt           OBJECT-TYPE
			   SYNTAX           INTEGER
								{
								hidden(1),
								read-only(2),
								updateable(3)
								}
			   ACCESS           read-only
			   STATUS           mandatory
			   DESCRIPTION
			   "The value of this object provides the state
			    of the 12v Current Analog parameter. (0-Hidden
			          1-Read-Only, 2-Updateable)."
			   ::= { gx2Rx1000AnalogEntry 53}

		fprminValue12Volt            OBJECT-TYPE
			   SYNTAX           Float
			   ACCESS           read-only
			   STATUS           mandatory
			   DESCRIPTION
			   "The value of this object provides the minimum value
			          of the 12 Volt Current Analog parameter. This value is a floating
			    point number that is represented as an IEEE 32 bit number."
			   ::= { gx2Rx1000AnalogEntry 54}

		fprmaxValue12Volt            OBJECT-TYPE
			   SYNTAX           Float
			   ACCESS           read-only
			   STATUS           mandatory
			   DESCRIPTION
			   "The value of this object provides the maximum value
			          of the 12 Volt Current Analog parameter. This value is a floating
			    point number that is represented as an IEEE 32 bit number."
			   ::= { gx2Rx1000AnalogEntry 55}

		fpralarmState12Volt          OBJECT-TYPE
			   SYNTAX           INTEGER
									{
									noAlarm(1),
									majorLowAlarm(2),
									minorLowAlarm(3),
									minorHighAlarm(4),
									majorHighAlarm(5),
									informational(6)
									}
			   ACCESS           read-only
			   STATUS           mandatory
			   DESCRIPTION
			   "The value of this object provides the curent alarm state of
			    the 12v Current Analog parameter."
			   ::= { gx2Rx1000AnalogEntry 56}

-- ************************ Digital parameters **********************************
		fprgx2Rx1000DigitalTableIndex              OBJECT-TYPE
			   SYNTAX           INTEGER (1..4294967295)
			   ACCESS           read-only
			   STATUS           mandatory
			   DESCRIPTION
			   "The value of this object identifies the network
			    element. This index is equal to the
			    hfcCommonTableIndex for the same element."
			   ::= { gx2Rx1000DigitalEntry 1}

-- New parameter
		fprlabelSlopeSetting	          	OBJECT-TYPE
			   SYNTAX         	DisplayString (SIZE (0..80))
			   ACCESS           	read-only
			   STATUS           	optional
			   DESCRIPTION
			   "The value of this object provides the label of the
			    RX1000's AttnSetting  Digital parameter."
			   ::= { gx2Rx1000DigitalEntry 2}

		fprenumSlopeSetting	          	OBJECT-TYPE
			   SYNTAX         	DisplayString (SIZE (0..80))
			   ACCESS           	read-only
			   STATUS           	optional
			   DESCRIPTION
			   "The value of this object represents the Enumeration values
			    possible for the Digital parameter. Each Enumerated values is
			    separated by a common. The first value has a enumerated value of 0."
			   ::= { gx2Rx1000DigitalEntry 3}

		fprvalueSlopeSetting	            OBJECT-TYPE
			   SYNTAX       		INTEGER

			   ACCESS           	read-write
			   STATUS           	mandatory
			   DESCRIPTION
			   "The value of this object is the current value of the parameter. It is an integer
                      value from 0 to 6. Each increment represents 1/2 dB of slope from 0 to 3 dB.
			    Where 0 = 0db and 6 = 3db"
			   ::= { gx2Rx1000DigitalEntry 4}

		fprstateFlagSlopeSetting	    	OBJECT-TYPE
			   SYNTAX         	INTEGER
								{
								hidden(1),
								read-only(2),
								updateable(3)
								}
			   ACCESS           	read-only
			   STATUS           	mandatory
			   DESCRIPTION
			   "The value of this object provides the state
			    of the the parameter. (0-Hidden 1-Read-Only, 2-Updateable)."
			   ::= { gx2Rx1000DigitalEntry 5}
-- New parameter
		fprlabelAttnSetting	          	OBJECT-TYPE
			   SYNTAX         	DisplayString (SIZE (0..80))
			   ACCESS           	read-only
			   STATUS           	optional
			   DESCRIPTION
			   "The value of this object provides the label of the
			    RX1000's AttnSetting  Digital parameter."
			   ::= { gx2Rx1000DigitalEntry 6}

		fprenumAttnSetting	          	OBJECT-TYPE
			   SYNTAX         	DisplayString (SIZE (0..80))
			   ACCESS           	read-only
			   STATUS           	optional
			   DESCRIPTION
			   "The value of this object represents the Enumeration values
			    possible for the Digital parameter. Each Enumerated values is
			    separated by a common. The first value has a enumerated value of 0."
			   ::= { gx2Rx1000DigitalEntry 7}

		fprvalueAttnSetting	            OBJECT-TYPE
			   SYNTAX       		INTEGER

			   ACCESS           	read-write
			   STATUS           	mandatory
			   DESCRIPTION
			   "The value of this object is the current value of the parameter. It is an integer
                      value from 0 to 40. Each increment represents 1/4 dB of attenuation from 0 to 10 dB.
			    Where 0 = 0db and 40 = 10db"
			   ::= { gx2Rx1000DigitalEntry 8}

		fprstateFlagAttnSetting	    	OBJECT-TYPE
			   SYNTAX         	INTEGER
								{
								hidden(1),
								read-only(2),
								updateable(3)
								}
			   ACCESS           	read-only
			   STATUS           	mandatory
			   DESCRIPTION
			   "The value of this object provides the state
			    of the the parameter. (0-Hidden 1-Read-Only, 2-Updateable)."
			   ::= { gx2Rx1000DigitalEntry 9}
-- New parameter
		fprlabelWavelength             	OBJECT-TYPE
			   SYNTAX         	DisplayString (SIZE (0..80))
			   ACCESS           	read-only
			   STATUS           	optional
			   DESCRIPTION
			   "The value of this object provides the label of the
			    RX1000's Wavelength  Digital parameter."
			   ::= { gx2Rx1000DigitalEntry 10}

		fprenumWavelength               	OBJECT-TYPE
			   SYNTAX         	DisplayString (SIZE (0..80))
			   ACCESS           	read-only
			   STATUS           	optional
			   DESCRIPTION
			   "The value of this object represents the Enumeration values
			    possible for the Digital parameter. Each Enumerated values is
			    separated by a comma. The first value has a enumerated value of 0."
			   ::= { gx2Rx1000DigitalEntry 11}

		fprvalueWavelength               OBJECT-TYPE
			   SYNTAX       		INTEGER
					    		{
							nM1310(1),
							nM1550(2)
					    		}
			   ACCESS           	read-write
			   STATUS           	mandatory
			   DESCRIPTION
			   "The value of this object is the current value of the parameter."
			   ::= { gx2Rx1000DigitalEntry 12}

		fprstateFlagWavelength	      OBJECT-TYPE
			   SYNTAX         	INTEGER
								{
								hidden(1),
								read-only(2),
								updateable(3)
								}
			   ACCESS           	read-only
			   STATUS           	mandatory
			   DESCRIPTION
			   "The value of this object provides the state
			    of the the parameter. (0-Hidden 1-Read-Only, 2-Updateable)."
			   ::= { gx2Rx1000DigitalEntry 13}
-- New parameter
		fprlabelFactoryDefault           OBJECT-TYPE
			   SYNTAX       		DisplayString (SIZE (0..80))
			   ACCESS           	read-only
			   STATUS           	optional
			   DESCRIPTION
			   "The value of this object provides the label of the
			    Factory Default Reset  Digital parameter."
			   ::= { gx2Rx1000DigitalEntry 14}

		fprenumFactoryDefault          	OBJECT-TYPE
			   SYNTAX       		DisplayString (SIZE (0..80))
			   ACCESS           	read-only
			   STATUS           	optional
			   DESCRIPTION
			   "The value of this object represents the Enumeration values
			    possible for the Digital parameter. Each Enumerated values is
			    separated by a common. The first value has a enumerated value of 1."
			   ::= { gx2Rx1000DigitalEntry 15}

		fprvalueFactoryDefault         	OBJECT-TYPE
			   SYNTAX       		INTEGER
					    		{
							off(1),
							on(2)
					    		}
			   ACCESS           	read-write
			   STATUS           	mandatory
			   DESCRIPTION
			   "The value of this object is the current value of the parameter."
			   ::= { gx2Rx1000DigitalEntry 16}

		fprstateFlagFactoryDefault     	OBJECT-TYPE
			   SYNTAX       		INTEGER
								{
								hidden(1),
								read-only(2),
								updateable(3)
								}
			   ACCESS           	read-only
			   STATUS           	mandatory
			   DESCRIPTION
			   "The value of this object provides the state
			    of the the parameter. (0-Hidden 1-Read-Only, 2-Updateable)."
			   ::= { gx2Rx1000DigitalEntry 17}
-- New parameter
		fprlabelSwModeThreshold	      OBJECT-TYPE
			   SYNTAX         	DisplayString (SIZE (0..80))
			   ACCESS           	read-only
			   STATUS           	optional
			   DESCRIPTION
			   "The value of this object provides the label of the
			    RX1000's Switch Mode Threshold  Digital parameter."
			   ::= { gx2Rx1000DigitalEntry 18}

		fprenumSwModeThreshold		OBJECT-TYPE
			   SYNTAX         	DisplayString (SIZE (0..80))
			   ACCESS           	read-only
			   STATUS           	optional
			   DESCRIPTION
			   "The value of this object represents the Enumeration values
			    possible for the Digital parameter. Each Enumerated values is
			    separated by a comma. The first value has a enumerated value of 0."
			   ::= { gx2Rx1000DigitalEntry 19}

		fprvalueSwModeThreshold	      OBJECT-TYPE
			   SYNTAX       		INTEGER
			   ACCESS           	read-write
			   STATUS           	mandatory
			   DESCRIPTION
			   "The value of this object reflects the setting of the threshold at
			    which the Optical Input Failed signal is sent. It is in 0.5 dB increments
                      ranging from -9 to +1 dB. The user can enter a number from 0 to 20,
			    where 0 = -9db and 20= +1db"
			   ::= { gx2Rx1000DigitalEntry 20}

		fprstateFlagSwModeThreshold	            OBJECT-TYPE
			   SYNTAX         	INTEGER
								{
								hidden(1),
								read-only(2),
								updateable(3)
								}
			   ACCESS           	read-only
			   STATUS           	mandatory
			   DESCRIPTION
			   "The value of this object provides the state
			    of the the parameter. (0-Hidden 1-Read-Only, 2-Updateable)."
			   ::= { gx2Rx1000DigitalEntry 21}
-- New parameter
		fprlabelSwModeSetting	     	OBJECT-TYPE
			   SYNTAX         	DisplayString (SIZE (0..80))
			   ACCESS           	read-only
			   STATUS           	optional
			   DESCRIPTION
			   "The value of this object provides the label of the
			    RX1000's Switch Mode Setting  Digital parameter."
			   ::= { gx2Rx1000DigitalEntry 22}

		fprenumSwModeSetting	           	OBJECT-TYPE
			   SYNTAX         	DisplayString (SIZE (0..80))
			   ACCESS           	read-only
			   STATUS           	optional
			   DESCRIPTION
			   "The value of this object represents the Enumeration values
			    possible for the Digital parameter. Each Enumerated values is
			    separated by a common. The first value has a enumerated value of 0."
			   ::= { gx2Rx1000DigitalEntry 23}

		fprvalueSwModeSetting	      OBJECT-TYPE
			   SYNTAX       		INTEGER
					    		{
							off(1),
							alarm-only(2),
							alarm-and-switch(3)
					    		}
			   ACCESS           	read-write
			   STATUS           	mandatory
			   DESCRIPTION
			   "The value of this object is the current value of the parameter."
			   ::= { gx2Rx1000DigitalEntry 24}

		fprstateFlagSwModeSetting	      OBJECT-TYPE
			   SYNTAX         	INTEGER
								{
								hidden(1),
								read-only(2),
								updateable(3)
								}
			   ACCESS           	read-only
			   STATUS           	mandatory
			   DESCRIPTION
			   "The value of this object provides the state
			    of the the parameter. (0-Hidden 1-Read-Only, 2-Updateable)."
			   ::= { gx2Rx1000DigitalEntry 25}


		--*********** STATUS *****************
		fprgx2Rx1000StatusTableIndex              OBJECT-TYPE
			   SYNTAX           INTEGER (1..4294967295)
			   ACCESS           read-only
			   STATUS           mandatory
			   DESCRIPTION
			   "The value of this object identifies the network
			    element. This index is equal to the
			    hfcCommonTableIndex for the same element."
			   ::= { gx2Rx1000StatusEntry 1}

--New Parameter
		fprlabelBoot               	OBJECT-TYPE
			   SYNTAX       		DisplayString (SIZE (0..80))
			   ACCESS           	read-only
			   STATUS           	optional
			   DESCRIPTION
			   "The value of this object provides the label of the
			    Boot Status  Status parameter."
			   ::= { gx2Rx1000StatusEntry 2}

		fprvalueBoot              		OBJECT-TYPE
			   SYNTAX       		INTEGER
									{
									ok(1),
									undetermined(2),
									warning(3),
									minor(4),
									major(5),
									critical(6)
									}
			   ACCESS           	read-only
			   STATUS           	mandatory
			   DESCRIPTION
			   "The value of this object provides the current state of
			    the parameter (0-Ok, 1-Undetermined
			    2-Warning, 3-Minor, 4-Major, 5-Critical)."
			   ::= { gx2Rx1000StatusEntry 3}

		fprstateflagBoot     	OBJECT-TYPE
			   SYNTAX       		INTEGER
								{
								hidden(1),
								read-only(2),
								updateable(3)
								}
			   ACCESS           	read-only
			   STATUS           	mandatory
			   DESCRIPTION
			   "The value of this object provides the state
			    of the the parameter. (0-Hidden 1-Read-Only, 2-Updateable)."
			   ::= { gx2Rx1000StatusEntry  4}


--New Parameter
		fprlabelFlash               	OBJECT-TYPE
			   SYNTAX       		DisplayString (SIZE (0..80))
			   ACCESS           	read-only
			   STATUS           	optional
			   DESCRIPTION
			   "The value of this object provides the label of the
			    Flash Status  Status parameter."
			   ::= { gx2Rx1000StatusEntry 5}

		fprvalueFlash              	OBJECT-TYPE
			   SYNTAX       		INTEGER
									{
									ok(1),
									undetermined(2),
									warning(3),
									minor(4),
									major(5),
									critical(6)
									}
			   ACCESS           	read-only
			   STATUS           	mandatory
			   DESCRIPTION
			   "The value of this object provides the current state of
			    the parameter (0-Ok, 1-Undetermined
			    2-Warning, 3-Minor, 4-Major, 5-Critical)."
			   ::= { gx2Rx1000StatusEntry 6}

		fprstateflagFlash     	OBJECT-TYPE
			   SYNTAX       		INTEGER
								{
								hidden(1),
								read-only(2),
								updateable(3)
								}
			   ACCESS           	read-only
			   STATUS           	mandatory
			   DESCRIPTION
			   "The value of this object provides the state
			    of the the parameter. (0-Hidden 1-Read-Only, 2-Updateable)."
			   ::= { gx2Rx1000StatusEntry 7}


--New Parameter
		fprlabelFactoryDataCRC           OBJECT-TYPE
			   SYNTAX       		DisplayString (SIZE (0..80))
			   ACCESS           	read-only
			   STATUS           	optional
			   DESCRIPTION
			   "The value of this object provides the label of the
			    Factory Data CRC Status parameter."
			   ::= { gx2Rx1000StatusEntry 8}

		fprvalueFactoryDataCRC          	OBJECT-TYPE
			   SYNTAX       		INTEGER
									{
									ok(1),
									undetermined(2),
									warning(3),
									minor(4),
									major(5),
									critical(6)
									}
			   ACCESS           	read-only
			   STATUS           	mandatory
			   DESCRIPTION
			   "The value of this object provides the current state of
			    the parameter (0-Ok, 1-Undetermined
			    2-Warning, 3-Minor, 4-Major, 5-Critical)."
			   ::= { gx2Rx1000StatusEntry 9}

		fprstateflagFactoryDataCRC     	OBJECT-TYPE
			   SYNTAX       		INTEGER
								{
								hidden(1),
								read-only(2),
								updateable(3)
								}
			   ACCESS           	read-only
			   STATUS           	mandatory
			   DESCRIPTION
			   "The value of this object provides the state
			    of the the parameter. (0-Hidden 1-Read-Only, 2-Updateable)."
			   ::= { gx2Rx1000StatusEntry 10}


--New Parameter
		fprlabelAlarmDataCRC             OBJECT-TYPE
			   SYNTAX       		DisplayString (SIZE (0..80))
			   ACCESS           	read-only
			   STATUS           	optional
			   DESCRIPTION
			   "The value of this object provides the label of the
			    Alarm Data CRC Status parameter."
			   ::= { gx2Rx1000StatusEntry 11}

		fprvalueAlarmDataCRC           	OBJECT-TYPE
			   SYNTAX       		INTEGER
									{
									ok(1),
									undetermined(2),
									warning(3),
									minor(4),
									major(5),
									critical(6)
									}
			   ACCESS           	read-only
			   STATUS           	mandatory
			   DESCRIPTION
			   "The value of this object provides the current state of
			    the parameter (0-Ok, 1-Undetermined
			    2-Warning, 3-Minor, 4-Major, 5-Critical)."
			   ::= { gx2Rx1000StatusEntry 12}

		fprstateflagAlarmDataCRC     	OBJECT-TYPE
			   SYNTAX       		INTEGER
								{
								hidden(1),
								read-only(2),
								updateable(3)
								}
			   ACCESS           	read-only
			   STATUS           	mandatory
			   DESCRIPTION
			   "The value of this object provides the state
			    of the the parameter. (0-Hidden 1-Read-Only, 2-Updateable)."
			   ::= { gx2Rx1000StatusEntry 13}


--New Parameter
		fprlabelCalibrationDataCRC       OBJECT-TYPE
			   SYNTAX       		DisplayString (SIZE (0..80))
			   ACCESS           	read-only
			   STATUS           	optional
			   DESCRIPTION
			   "The value of this object provides the label of the
			    Calibration Data CRC Status parameter."
			   ::= { gx2Rx1000StatusEntry 14}

		fprvalueCalibrationDataCRC      	OBJECT-TYPE
			   SYNTAX       		INTEGER
									{
									ok(1),
									undetermined(2),
									warning(3),
									minor(4),
									major(5),
									critical(6)
									}
			   ACCESS           	read-only
			   STATUS           	mandatory
			   DESCRIPTION
			   "The value of this object provides the current state of
			    the parameter (0-Ok, 1-Undetermined
			    2-Warning, 3-Minor, 4-Major, 5-Critical)."
			   ::= { gx2Rx1000StatusEntry 15}

		fprstateflagCalibrationDataCRC     	OBJECT-TYPE
			   SYNTAX       		INTEGER
								{
								hidden(1),
								read-only(2),
								updateable(3)
								}
			   ACCESS           	read-only
			   STATUS           	mandatory
			   DESCRIPTION
			   "The value of this object provides the state
			    of the the parameter. (0-Hidden 1-Read-Only, 2-Updateable)."
			   ::= { gx2Rx1000StatusEntry 16}


--New Parameter
		fprlabelFacCalSettingCRC       OBJECT-TYPE
			   SYNTAX       		DisplayString (SIZE (0..80))
			   ACCESS           	read-only
			   STATUS           	optional
			   DESCRIPTION
			   "The value of this object provides the label of the
			    Factor Cal Setting CRC Status parameter."
			   ::= { gx2Rx1000StatusEntry 17}

		fprvalueFacCalSettingCRC      	OBJECT-TYPE
			   SYNTAX       		INTEGER
									{
									ok(1),
									undetermined(2),
									warning(3),
									minor(4),
									major(5),
									critical(6)
									}
			   ACCESS           	read-only
			   STATUS           	mandatory
			   DESCRIPTION
			   "The value of this object provides the current state of
			    the parameter (0-Ok, 1-Undetermined
			    2-Warning, 3-Minor, 4-Major, 5-Critical)."
			   ::= { gx2Rx1000StatusEntry 18}

		fprstateflagFacCalSettingCRC    	OBJECT-TYPE
			   SYNTAX       		INTEGER
								{
								hidden(1),
								read-only(2),
								updateable(3)
								}
			   ACCESS           	read-only
			   STATUS           	mandatory
			   DESCRIPTION
			   "The value of this object provides the state
			    of the the parameter. (0-Hidden 1-Read-Only, 2-Updateable)."
			   ::= { gx2Rx1000StatusEntry 19}


--New Parameter
		fprlabelInputSig       OBJECT-TYPE
			   SYNTAX       		DisplayString (SIZE (0..80))
			   ACCESS           	read-only
			   STATUS           	optional
			   DESCRIPTION
			   "The value of this object provides the label of the
			    Input Sig Status parameter."
			   ::= { gx2Rx1000StatusEntry 20}

		fprvalueInputSig      	OBJECT-TYPE
			   SYNTAX       		INTEGER
									{
									ok(1),
									undetermined(2),
									warning(3),
									minor(4),
									major(5),
									critical(6)
									}
			   ACCESS           	read-only
			   STATUS           	mandatory
			   DESCRIPTION
			   "The value of this object provides the current state of
			    the parameter (0-Ok, 1-Undetermined
			    2-Warning, 3-Minor, 4-Major, 5-Critical)."
			   ::= { gx2Rx1000StatusEntry 21}

		fprstateflagInputSig    	OBJECT-TYPE
			   SYNTAX       		INTEGER
								{
								hidden(1),
								read-only(2),
								updateable(3)
								}
			   ACCESS           	read-only
			   STATUS           	mandatory
			   DESCRIPTION
			   "The value of this object provides the state
			    of the the parameter. (0-Hidden 1-Read-Only, 2-Updateable)."
			   ::= { gx2Rx1000StatusEntry 22}

            -- ************ FACTORY DATA ****************
		fprgx2Rx1000FactoryTableIndex              OBJECT-TYPE
			   SYNTAX           INTEGER (1..4294967295)
			   ACCESS           read-only
			   STATUS           mandatory
			   DESCRIPTION
			   "The value of this object identifies the network
			    element. This index is equal to the
			    hfcCommonTableIndex for the same element."
			   ::= { gx2Rx1000FactoryEntry 1}

		fprbootControlByte          	OBJECT-TYPE
			   SYNTAX       		INTEGER
			   ACCESS           	read-only
			   STATUS           	mandatory
			   DESCRIPTION
			   "The value of this object indicates which bank the firmware
			    is currently being boot from."
			   ::= { gx2Rx1000FactoryEntry 2}

		fprbootStatusByte          	OBJECT-TYPE
			   SYNTAX       		INTEGER
			   ACCESS           	read-only
			   STATUS           	mandatory
			   DESCRIPTION
			   "This object indicates the status of the last boot"
			   ::= { gx2Rx1000FactoryEntry 3}

		fprbank0CRC          		OBJECT-TYPE
			   SYNTAX       		INTEGER
			   ACCESS           	read-only
			   STATUS           	mandatory
			   DESCRIPTION
			   "This object provides the CRC code of bank 0."
			   ::= { gx2Rx1000FactoryEntry 4}

		fprbank1CRC          		OBJECT-TYPE
			   SYNTAX       		INTEGER
			   ACCESS           	read-only
			   STATUS           	mandatory
			   DESCRIPTION
			   "This object provides the CRC code of bank 1."
			   ::= { gx2Rx1000FactoryEntry 5}

		fprprgEEPROMByte          		OBJECT-TYPE
			   SYNTAX       		INTEGER
			   ACCESS           	read-only
			   STATUS           	mandatory
			   DESCRIPTION
			   "This object indicates if the EEPROM has been programmed"
			   ::= { gx2Rx1000FactoryEntry 6}

		fprfactoryCRC          		OBJECT-TYPE
			   SYNTAX       		INTEGER
			   ACCESS           	read-only
			   STATUS           	mandatory
			   DESCRIPTION
			   "This object provides the CRC code for the Factory data."
			   ::= { gx2Rx1000FactoryEntry 7}

		fprcalculateCRC          		OBJECT-TYPE
			   SYNTAX       		INTEGER
					    		{
                                          factory(1),
							calibration(2),
							alarmdata(3),
							calSetting(4)
					    		}
			   ACCESS           	read-only
			   STATUS           	mandatory
			   DESCRIPTION
			   "This object indicates which of the Emnums will have the CRC calculated."
			   ::= { gx2Rx1000FactoryEntry 8}

		fprhourMeter          		OBJECT-TYPE
			   SYNTAX       		INTEGER
			   ACCESS           	read-only
			   STATUS           	mandatory
			   DESCRIPTION
			   "This object provides the hour meter reading of the module."
			   ::= { gx2Rx1000FactoryEntry 9}

		fprflashPrgCntA          		OBJECT-TYPE
			   SYNTAX       		INTEGER
			   ACCESS           	read-only
			   STATUS           	mandatory
			   DESCRIPTION
			   "This object provides the number of times the flash has been
                      programmed on side A."
			   ::= { gx2Rx1000FactoryEntry 10}

		fprflashPrgCntB          		OBJECT-TYPE
			   SYNTAX       		INTEGER
			   ACCESS           	read-only
			   STATUS           	mandatory
			   DESCRIPTION
			   "This object provides the number of times the flash has been
                      programmed on side B."
			   ::= { gx2Rx1000FactoryEntry 11}

		fprfwRev0     		     		OBJECT-TYPE
			   SYNTAX       		DisplayString (SIZE (0..80))
			   ACCESS           	read-only
			   STATUS           	mandatory
			   DESCRIPTION
			   "This object provides the Revision of the firmware stores in bank 0."
			   ::= { gx2Rx1000FactoryEntry 12}

		fprfwRev1     		     		OBJECT-TYPE
			   SYNTAX       		DisplayString (SIZE (0..80))
			   ACCESS           	read-only
			   STATUS           	mandatory
			   DESCRIPTION
			   "This object provides the Revision of the firmware stores in bank 1."
			   ::= { gx2Rx1000FactoryEntry 13}

            -- ************ Hold Time DATA ****************
		gx2Rx1000HoldTimeTableIndex              OBJECT-TYPE
			   SYNTAX           INTEGER (1..4294967295)
			   ACCESS           read-only
			   STATUS           mandatory
			   DESCRIPTION
			   "The value of this object is the index of the data object."
			   ::= { gx2Rx1000HoldTimeEntry 1}

		gx2Rx1000HoldTimeSpecIndex              OBJECT-TYPE
			   SYNTAX           INTEGER (1..4294967295)
			   ACCESS           read-only
			   STATUS           mandatory
			   DESCRIPTION
			   "The value of this object identifies the index of the alarm object to be modified."
			   ::= { gx2Rx1000HoldTimeEntry 2}

		gx2Rx1000HoldTimeData          	OBJECT-TYPE
			   SYNTAX       		INTEGER
			   ACCESS           	read-write
			   STATUS           	mandatory
			   DESCRIPTION
			   "The value of this object provides access to the hold timers used
			   to suppress nose on analog objects. This object is a 32 bit object.
			   Validation data is entered into bytes zero and one of the object.
			   Bytes three and four are used to entering the hold time for the
			   specified alarm object. The Hold timer data ranges from 0 to 1300 seconds.
			   The index of this object corresponds to the alarm object to be modified.
			   Alarm Hold timers correspond to the index of this object as follows:
			   Index 1 = xxx, index 2 = xxxx, Index 3 = xxxx,
			   The hold time is represented in seconds."
			   ::= { gx2Rx1000HoldTimeEntry 3}

-- ****************************************************************
--
-- TRAP DEFINITIONS
--
--
-- Every trap generated by an HFC agents will include first 9 identical
-- fields. If particular variable is not supported in
-- particular TRAP-TYPE then default value will be returned.
--
-- DESCRIPTION will include explanation of use of generic
-- variables (trapAdditionalInfo******.)  If no
-- DESCRIPTION is given then generic variables will contain
-- default values.
--
-- *****************************************************************
-- **************************************************************************
--                              RX1000 Module traps
-- **************************************************************************
   trapRX1000ConfigChangeInteger TRAP-TYPE
       ENTERPRISE gx2Rx1000
       VARIABLES
	       {
		trapIdentifier,
		trapNetworkElemModelNumber,
		trapNetworkElemSerialNum,
		trapPerceivedSeverity,
		trapNetworkElemOperState,
		trapNetworkElemAlarmStatus,
		trapNetworkElemAdminState,
		trapNetworkElemAvailStatus,
		trapText,
		trapChangedObjectId,
		trapChangedValueInteger,
		trapNETrapLastTrapTimeStamp
	       }
       DESCRIPTION
	"This trap is issued if configuration of a single variable
	 with integer type was changed (via ANY interface).
	 TrapChangedValueInteger variable may contain current reading
	 of that variable.
	 trapPerceivedSeverity - 'indeterminate'"
  ::= 1

   trapRX1000ConfigChangeDisplayString TRAP-TYPE
       ENTERPRISE gx2Rx1000
       VARIABLES
	       {
		trapIdentifier,
		trapNetworkElemModelNumber,
		trapNetworkElemSerialNum,
		trapPerceivedSeverity,
		trapNetworkElemOperState,
		trapNetworkElemAlarmStatus,
		trapNetworkElemAdminState,
		trapNetworkElemAvailStatus,
		trapText,
		trapChangedObjectId,
		trapChangedValueDisplayString,
		trapNETrapLastTrapTimeStamp
	       }
       DESCRIPTION
	"This trap is issued if configuration of a single variable
	 with DispalayString type was changed (via ANY interface).
	 TrapChangedValueDisplayString variable may contain current reading
	 of that variable.
	 trapPerceivedSeverity - 'indeterminate'"
  ::= 2

  trapRX1000OpticalPowerAlarm TRAP-TYPE
	ENTERPRISE gx2Rx1000
	VARIABLES
		{
		 trapIdentifier,
		 trapNetworkElemModelNumber,
		 trapNetworkElemSerialNum,
		 trapPerceivedSeverity,
		 trapNetworkElemOperState,
		 trapNetworkElemAlarmStatus,
		 trapNetworkElemAdminState,
		 trapNetworkElemAvailStatus,
		 trapText,
		 trapChangedObjectId,
		 trapChangedValueInteger,
		 trapNETrapLastTrapTimeStamp
		}
	DESCRIPTION
	"This trap is issued when the input Optical Power parameter
	 goes out of range."
  ::= 3

  trapRX1000ModuleTemperatureAlarm TRAP-TYPE
	ENTERPRISE gx2Rx1000
	VARIABLES
		{
		 trapIdentifier,
		 trapNetworkElemModelNumber,
		 trapNetworkElemSerialNum,
		 trapPerceivedSeverity,
		 trapNetworkElemOperState,
		 trapNetworkElemAlarmStatus,
		 trapNetworkElemAdminState,
		 trapNetworkElemAvailStatus,
		 trapText,
		 trapChangedObjectId,
		 trapChangedValueInteger,
		 trapNETrapLastTrapTimeStamp
		}
	DESCRIPTION
	"This trap is issued when the RX1000 Module's Temperature goes out of range."
  ::= 4

  trapRX1000HeatSinkTemperatureAlarm TRAP-TYPE
	ENTERPRISE gx2Rx1000
	VARIABLES
		{
		 trapIdentifier,
		 trapNetworkElemModelNumber,
		 trapNetworkElemSerialNum,
		 trapPerceivedSeverity,
		 trapNetworkElemOperState,
		 trapNetworkElemAlarmStatus,
		 trapNetworkElemAdminState,
		 trapNetworkElemAvailStatus,
		 trapText,
		 trapChangedObjectId,
		 trapChangedValueInteger,
		 trapNETrapLastTrapTimeStamp
		}
	DESCRIPTION
	"This trap is issued when the RX1000 Heat Sink Temperature goes out of range."
  ::= 5

  trapRX1000FanCurrentAlarm TRAP-TYPE
	ENTERPRISE gx2Rx1000
	VARIABLES
		{
		 trapIdentifier,
		 trapNetworkElemModelNumber,
		 trapNetworkElemSerialNum,
		 trapPerceivedSeverity,
		 trapNetworkElemOperState,
		 trapNetworkElemAlarmStatus,
		 trapNetworkElemAdminState,
		 trapNetworkElemAvailStatus,
		 trapText,
		 trapChangedObjectId,
		 trapChangedValueInteger,
		 trapNETrapLastTrapTimeStamp
		}
	DESCRIPTION
	"This trap is issued when the RX1000 Module's Fan Currrent parameter
	 goes out of range."
  ::= 6

  trapRX1000Plus12CurrentAlarm TRAP-TYPE
	ENTERPRISE gx2Rx1000
	VARIABLES
		{
		 trapIdentifier,
		 trapNetworkElemModelNumber,
		 trapNetworkElemSerialNum,
		 trapPerceivedSeverity,
		 trapNetworkElemOperState,
		 trapNetworkElemAlarmStatus,
		 trapNetworkElemAdminState,
		 trapNetworkElemAvailStatus,
		 trapText,
		 trapChangedObjectId,
		 trapChangedValueInteger,
		 trapNETrapLastTrapTimeStamp
		}
	DESCRIPTION
	"This trap is issued when the RX1000 Module's positive 12 volt current parameter
	 goes out of range."
  ::= 7

  trapRX1000OpticalSwitchAlarm TRAP-TYPE
	ENTERPRISE gx2Rx1000
	VARIABLES
		{
		 trapIdentifier,
		 trapNetworkElemModelNumber,
		 trapNetworkElemSerialNum,
		 trapPerceivedSeverity,
		 trapNetworkElemOperState,
		 trapNetworkElemAlarmStatus,
		 trapNetworkElemAdminState,
		 trapNetworkElemAvailStatus,
		 trapText,
		 trapChangedObjectId,
		 trapChangedValueInteger,
		 trapNETrapLastTrapTimeStamp
		}
	DESCRIPTION
	"This trap is issued when the RX1000 Redundancy signal indicates a low input signal."
  ::= 8

  trapRX1000Boot0Alarm TRAP-TYPE
	ENTERPRISE gx2Rx1000
	VARIABLES
		{
		 trapIdentifier,
		 trapNetworkElemModelNumber,
		 trapNetworkElemSerialNum,
		 trapPerceivedSeverity,
		 trapNetworkElemOperState,
		 trapNetworkElemAlarmStatus,
		 trapNetworkElemAdminState,
		 trapNetworkElemAvailStatus,
		 trapText,
		 trapChangedObjectId,
		 trapChangedValueInteger,
		 trapNETrapLastTrapTimeStamp
		}
	DESCRIPTION
	"This trap is issued when the RX1000 Module's Bank 0 Boot sequence has detected an error."
  ::= 9

  trapRX1000Boot1Alarm TRAP-TYPE
	ENTERPRISE gx2Rx1000
	VARIABLES
		{
		 trapIdentifier,
		 trapNetworkElemModelNumber,
		 trapNetworkElemSerialNum,
		 trapPerceivedSeverity,
		 trapNetworkElemOperState,
		 trapNetworkElemAlarmStatus,
		 trapNetworkElemAdminState,
		 trapNetworkElemAvailStatus,
		 trapText,
		 trapChangedObjectId,
		 trapChangedValueInteger,
		 trapNETrapLastTrapTimeStamp
		}
	DESCRIPTION
	"This trap is issued when the RX1000 Module's Bank 1 Boot sequence has detected an error."
  ::= 10

  trapRX1000FlashAlarm TRAP-TYPE
	ENTERPRISE gx2Rx1000
	VARIABLES
		{
		 trapIdentifier,
		 trapNetworkElemModelNumber,
		 trapNetworkElemSerialNum,
		 trapPerceivedSeverity,
		 trapNetworkElemOperState,
		 trapNetworkElemAlarmStatus,
		 trapNetworkElemAdminState,
		 trapNetworkElemAvailStatus,
		 trapText,
		 trapChangedObjectId,
		 trapChangedValueInteger,
		 trapNETrapLastTrapTimeStamp
		}
	DESCRIPTION
	"This trap is issued when the RX1000 Module's boot or flash programming sequence has
       detected a Flash error."
  ::= 11

  trapRX1000AlarmDataCRCAlarm TRAP-TYPE
	ENTERPRISE gx2Rx1000
	VARIABLES
		{
		 trapIdentifier,
		 trapNetworkElemModelNumber,
		 trapNetworkElemSerialNum,
		 trapPerceivedSeverity,
		 trapNetworkElemOperState,
		 trapNetworkElemAlarmStatus,
		 trapNetworkElemAdminState,
		 trapNetworkElemAvailStatus,
		 trapText,
		 trapChangedObjectId,
		 trapChangedValueInteger,
		 trapNETrapLastTrapTimeStamp
		}
      DESCRIPTION
      "This trap is issued when the RX1000 Module detects an error calculating the alarm limit CRC."
  ::= 12

  trapRX1000FactoryDataCRCAlarm TRAP-TYPE
	ENTERPRISE gx2Rx1000
	VARIABLES
		{
		 trapIdentifier,
		 trapNetworkElemModelNumber,
		 trapNetworkElemSerialNum,
		 trapPerceivedSeverity,
		 trapNetworkElemOperState,
		 trapNetworkElemAlarmStatus,
		 trapNetworkElemAdminState,
		 trapNetworkElemAvailStatus,
		 trapText,
		 trapChangedObjectId,
		 trapChangedValueInteger,
		 trapNETrapLastTrapTimeStamp
		}
      DESCRIPTION
      "This trap is issued when the RX1000 Module detects an error calculating the Factory data CRC."
  ::= 13

  trapRX1000CalDataCRCAlarm TRAP-TYPE
	ENTERPRISE gx2Rx1000
	VARIABLES
		{
		 trapIdentifier,
		 trapNetworkElemModelNumber,
		 trapNetworkElemSerialNum,
		 trapPerceivedSeverity,
		 trapNetworkElemOperState,
		 trapNetworkElemAlarmStatus,
		 trapNetworkElemAdminState,
		 trapNetworkElemAvailStatus,
		 trapText,
		 trapChangedObjectId,
		 trapChangedValueInteger,
		 trapNETrapLastTrapTimeStamp
		}
      DESCRIPTION
      "This trap is issued when the RX1000 Module detects an error calculating the Calibration data CRC."
  ::= 14

    trapRX1000ResetFacDefault TRAP-TYPE
	ENTERPRISE gx2Rx1000
	VARIABLES
		{
		 trapIdentifier,
		 trapNetworkElemModelNumber,
		 trapNetworkElemSerialNum,
		 trapPerceivedSeverity,
		 trapNetworkElemOperState,
		 trapNetworkElemAlarmStatus,
		 trapNetworkElemAdminState,
		 trapNetworkElemAvailStatus,
		 trapText,
		 trapChangedObjectId,
		 trapChangedValueInteger,
		 trapNETrapLastTrapTimeStamp
		}
      DESCRIPTION
      "This trap is issued when the RX1000 resets to factory defaults"
  ::= 15

  trapRX1000FacCalSettingCRCAlarm TRAP-TYPE
	ENTERPRISE gx2Rx1000
	VARIABLES
		{
		 trapIdentifier,
		 trapNetworkElemModelNumber,
		 trapNetworkElemSerialNum,
		 trapPerceivedSeverity,
		 trapNetworkElemOperState,
		 trapNetworkElemAlarmStatus,
		 trapNetworkElemAdminState,
		 trapNetworkElemAvailStatus,
		 trapText,
		 trapChangedObjectId,
		 trapChangedValueInteger,
		 trapNETrapLastTrapTimeStamp
		}
      DESCRIPTION
      "This trap is issued when the RX1000 Module detects factory calibration setting CRC alarm."
  ::= 16


  END
