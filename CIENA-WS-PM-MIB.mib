-- This file was automatically generated from ciena-ws-pm.yang. Do not edit.

CIENA-WS-PM-MIB DEFINITIONS ::= BEGIN

IMPORTS
    cienaWsConfig
        FROM CIENA-WS-MIB
    ChannelsNumber, Decimal1Dig, Decimal3Dig, EnabledDisabledEnum, StringMaxl32, StringMaxl64, StringSci
        FROM CIENA-WS-TYPEDEFS-MIB
    MODULE-COMPLIANCE, OBJECT-GROUP
        FROM SNMPv2-CONF
    Counter64, Integer32, MODULE-IDENTITY, OBJECT-TYPE, Unsigned32
        FROM SNMPv2-SMI
    TEXTUAL-CONVENTION
        FROM SNMPv2-TC;

cienaWsPmMIB MODULE-IDENTITY
    LAST-UPDATED "201707070000Z"
    ORGANIZATION "Ciena Corporation"
    CONTACT-INFO "Web URL: http://www.ciena.com/
Postal:  7035 Ridge Road
       Hanover, Maryland 21076
       U.S.A.
Phone:   +1 800-921-1144
Fax:     +1 410-694-5750"
    DESCRIPTION "This module defines performance monitoring data for the Waveserver."
    REVISION "201707070000Z"
    DESCRIPTION "Waveserver Release 1.5
Added ncx:user-write to 'port-extended-tx-rx-instances', 'ptp-basic-instances', and 'ptp-advanced-instances'."
    REVISION "201703020000Z"
    DESCRIPTION "Waveserver Rel 1.4 revision.  
Obsolete: mac-layer container and its sub node unavailable-seconds leaf.
Added: unavailable-seconds leaf to container pcs-layer.
Added: average-link-utilization leaf to container interface-counts/rx and interface-counts/tx respectively. 
Added: odu-layer container which contains errored-seconds, severely-errored-seconds, unavailable-seconds leaves.
Aligned MIB node names to YANG module names.
Aligned MIB files to respect YANG read/write status."
    REVISION "201612120000Z"
    DESCRIPTION "Initial version."
    ::= { cienaWsConfig 22 }

PmAlignment ::= TEXTUAL-CONVENTION
    STATUS current
    DESCRIPTION "None"
    SYNTAX INTEGER { unknown(0), startTime(1), localClock(2) }

PmBinState ::= TEXTUAL-CONVENTION
    STATUS current
    DESCRIPTION "None"
    SYNTAX INTEGER { notValid(0), valid(1), partial(2), timeChange(3), cleared(4), idf(5), overflow(6) }

PmConfigurationMode ::= TEXTUAL-CONVENTION
    STATUS current
    DESCRIPTION "None"
    SYNTAX INTEGER { unknown(0), autoCreated(1), userCreated(2) }

PmInstanceType ::= TEXTUAL-CONVENTION
    STATUS current
    DESCRIPTION "None"
    SYNTAX INTEGER { proactive(0), onDemand(1), unknown(2) }

PmInterfaceType ::= TEXTUAL-CONVENTION
    STATUS current
    DESCRIPTION "None"
    SYNTAX INTEGER { port(0), subPort(1), pbtTransit(2), pbtService(3), dataSource(4), igmpVs(5), accessFlow(6), mplsVc(7), qosFlow(8), queueGroupInstance(9), lineModule(10), mplsTransitLsp(11), mplsTransitUnidirLsp(12), mplsTransitCoroutLsp(13), mplsEncapLsp(14), mplsDecapLsp(15), ptp(16), otu(17), odu(18), unknown(19) }

PmPersistenceState ::= TEXTUAL-CONVENTION
    STATUS current
    DESCRIPTION "None"
    SYNTAX INTEGER { notInitialized(0), initialized(1) }

PmPersistenceStatus ::= TEXTUAL-CONVENTION
    STATUS current
    DESCRIPTION "None"
    SYNTAX INTEGER { none(0), inprogress(1), complete(2), notFound(3), inaccessible(4), aborted(5), corrupt(6), failed(7), partial(8), notReady(9) }

PmProfileType ::= TEXTUAL-CONVENTION
    STATUS current
    DESCRIPTION "None"
    SYNTAX INTEGER { basicTxRx(0), basicTxRxBiDir(1), extendedTxRx(2), basicCounter(3), accessStats(4), igmpVsStats(5), floodContainer(6), basicRx(7), queueGroupStats(8), egressQueueStats(9), basicTx(10), basicPtp(11), advancePtp(12), basicOtu(13), basicOdu(14), unknown(15) }

cwsPmGlobalConfigTable OBJECT-TYPE
    SYNTAX SEQUENCE OF CwsPmGlobalConfigEntry
    MAX-ACCESS not-accessible
    STATUS current
    DESCRIPTION "Performance monitoring global configuration on the Waveserver."
    ::= { cienaWsPmMIB 3 }

cwsPmGlobalConfigEntry OBJECT-TYPE
    SYNTAX CwsPmGlobalConfigEntry
    MAX-ACCESS not-accessible
    STATUS current
    DESCRIPTION "Entry for cwsPmGlobalConfigTable."
    INDEX { cwsPmGlobalConfigTableSnmpKey }
    ::= { cwsPmGlobalConfigTable 1 }

CwsPmGlobalConfigEntry ::= SEQUENCE { 
    cwsPmGlobalConfigTableSnmpKey Integer32,
    cwsPmGlobalConfigAdminState EnabledDisabledEnum,
    cwsPmGlobalConfigPersistenceInterval Unsigned32,
    cwsPmGlobalConfigPersistenceStorageLocation INTEGER 
}

cwsPmGlobalConfigTableSnmpKey OBJECT-TYPE
    SYNTAX Integer32(0..2147483647)
    MAX-ACCESS not-accessible
    STATUS current
    DESCRIPTION "Unique key for cwsPmGlobalConfig"
    ::= { cwsPmGlobalConfigEntry 1 }

cwsPmGlobalConfigAdminState OBJECT-TYPE
    SYNTAX EnabledDisabledEnum
    MAX-ACCESS read-write
    STATUS current
    DESCRIPTION "Global admin state."
    ::= { cwsPmGlobalConfigEntry 2 }

cwsPmGlobalConfigPersistenceInterval OBJECT-TYPE
    SYNTAX Unsigned32
    MAX-ACCESS read-write
    STATUS current
    DESCRIPTION "Persistence interval."
    ::= { cwsPmGlobalConfigEntry 3 }

cwsPmGlobalConfigPersistenceStorageLocation OBJECT-TYPE
    SYNTAX INTEGER { onBoard(0), usbFlash(1), notFound(2) }
    MAX-ACCESS read-write
    STATUS current
    DESCRIPTION "Persistence storage location setting."
    ::= { cwsPmGlobalConfigEntry 4 }

cwsPmPersistenceStateTable OBJECT-TYPE
    SYNTAX SEQUENCE OF CwsPmPersistenceStateEntry
    MAX-ACCESS not-accessible
    STATUS current
    DESCRIPTION "Performance monitoring persistence state on the Waveserver."
    ::= { cienaWsPmMIB 4 }

cwsPmPersistenceStateEntry OBJECT-TYPE
    SYNTAX CwsPmPersistenceStateEntry
    MAX-ACCESS not-accessible
    STATUS current
    DESCRIPTION "Entry for cwsPmPersistenceStateTable."
    INDEX { cwsPmPersistenceStateTableSnmpKey }
    ::= { cwsPmPersistenceStateTable 1 }

CwsPmPersistenceStateEntry ::= SEQUENCE { 
    cwsPmPersistenceStateTableSnmpKey Integer32,
    cwsPmPersistenceStateState PmPersistenceState,
    cwsPmPersistenceStateNextHistoryBinSave Unsigned32,
    cwsPmPersistenceStateCurrentFileSize Unsigned32,
    cwsPmPersistenceStateSaveStatus PmPersistenceStatus,
    cwsPmPersistenceStateInstancesSaved Unsigned32,
    cwsPmPersistenceStateElapsedSaveTime Unsigned32,
    cwsPmPersistenceStateLoadStatus PmPersistenceStatus,
    cwsPmPersistenceStateInstancesInFile Unsigned32,
    cwsPmPersistenceStateInstancesLoaded Unsigned32,
    cwsPmPersistenceStateElapsedLoadTime Unsigned32 
}

cwsPmPersistenceStateTableSnmpKey OBJECT-TYPE
    SYNTAX Integer32(0..2147483647)
    MAX-ACCESS not-accessible
    STATUS current
    DESCRIPTION "Unique key for cwsPmPersistenceState"
    ::= { cwsPmPersistenceStateEntry 1 }

cwsPmPersistenceStateState OBJECT-TYPE
    SYNTAX PmPersistenceState
    MAX-ACCESS read-only
    STATUS current
    DESCRIPTION "Persistence state initialized or not."
    ::= { cwsPmPersistenceStateEntry 2 }

cwsPmPersistenceStateNextHistoryBinSave OBJECT-TYPE
    SYNTAX Unsigned32
    MAX-ACCESS read-only
    STATUS current
    DESCRIPTION "Number of seconds left before current bin is saved to history."
    ::= { cwsPmPersistenceStateEntry 3 }

cwsPmPersistenceStateCurrentFileSize OBJECT-TYPE
    SYNTAX Unsigned32
    MAX-ACCESS read-only
    STATUS current
    DESCRIPTION "Current file size."
    ::= { cwsPmPersistenceStateEntry 4 }

cwsPmPersistenceStateSaveStatus OBJECT-TYPE
    SYNTAX PmPersistenceStatus
    MAX-ACCESS read-only
    STATUS current
    DESCRIPTION "Persistence sotrage setting."
    ::= { cwsPmPersistenceStateEntry 5 }

cwsPmPersistenceStateInstancesSaved OBJECT-TYPE
    SYNTAX Unsigned32
    MAX-ACCESS read-only
    STATUS current
    DESCRIPTION "Number of the PM instances saved."
    ::= { cwsPmPersistenceStateEntry 6 }

cwsPmPersistenceStateElapsedSaveTime OBJECT-TYPE
    SYNTAX Unsigned32
    MAX-ACCESS read-only
    STATUS current
    DESCRIPTION "Number of seconds passed since the save begin."
    ::= { cwsPmPersistenceStateEntry 7 }

cwsPmPersistenceStateLoadStatus OBJECT-TYPE
    SYNTAX PmPersistenceStatus
    MAX-ACCESS read-only
    STATUS current
    DESCRIPTION "Persistence load status."
    ::= { cwsPmPersistenceStateEntry 8 }

cwsPmPersistenceStateInstancesInFile OBJECT-TYPE
    SYNTAX Unsigned32
    MAX-ACCESS read-only
    STATUS current
    DESCRIPTION "Total number of PM instances in file."
    ::= { cwsPmPersistenceStateEntry 9 }

cwsPmPersistenceStateInstancesLoaded OBJECT-TYPE
    SYNTAX Unsigned32
    MAX-ACCESS read-only
    STATUS current
    DESCRIPTION "Number of loaded instances."
    ::= { cwsPmPersistenceStateEntry 10 }

cwsPmPersistenceStateElapsedLoadTime OBJECT-TYPE
    SYNTAX Unsigned32
    MAX-ACCESS read-only
    STATUS current
    DESCRIPTION "Elaspsed Load Time."
    ::= { cwsPmPersistenceStateEntry 11 }

cwsPmInstancesTable OBJECT-TYPE
    SYNTAX SEQUENCE OF CwsPmInstancesEntry
    MAX-ACCESS not-accessible
    STATUS current
    DESCRIPTION "PM auto-created instance list."
    ::= { cienaWsPmMIB 5 }

cwsPmInstancesEntry OBJECT-TYPE
    SYNTAX CwsPmInstancesEntry
    MAX-ACCESS not-accessible
    STATUS current
    DESCRIPTION "Entry for cwsPmInstancesTable."
    INDEX { cwsPmInstancesInstanceId }
    ::= { cwsPmInstancesTable 1 }

CwsPmInstancesEntry ::= SEQUENCE { 
    cwsPmInstancesInstanceId Integer32,
    cwsPmInstancesInstanceName StringMaxl32,
    cwsPmInstancesAdminState EnabledDisabledEnum,
    cwsPmInstancesOperationalState EnabledDisabledEnum,
    cwsPmInstancesInstanceType PmInstanceType,
    cwsPmInstancesBinCount Unsigned32,
    cwsPmInstancesBinDuration Unsigned32,
    cwsPmInstancesAttachedInterfaceType PmInterfaceType,
    cwsPmInstancesAttachedInterfaceName StringMaxl32 
}

cwsPmInstancesInstanceId OBJECT-TYPE
    SYNTAX Integer32(0..2147483647)
    MAX-ACCESS not-accessible
    STATUS current
    DESCRIPTION "ID of the PM instance."
    ::= { cwsPmInstancesEntry 1 }

cwsPmInstancesInstanceName OBJECT-TYPE
    SYNTAX StringMaxl32
    MAX-ACCESS read-only
    STATUS current
    DESCRIPTION "The PM instance name."
    ::= { cwsPmInstancesEntry 2 }

cwsPmInstancesAdminState OBJECT-TYPE
    SYNTAX EnabledDisabledEnum
    MAX-ACCESS read-only
    STATUS current
    DESCRIPTION "The configured administrative state of the PM instance."
    ::= { cwsPmInstancesEntry 3 }

cwsPmInstancesOperationalState OBJECT-TYPE
    SYNTAX EnabledDisabledEnum
    MAX-ACCESS read-only
    STATUS current
    DESCRIPTION "The operational state of the PM instance."
    ::= { cwsPmInstancesEntry 4 }

cwsPmInstancesInstanceType OBJECT-TYPE
    SYNTAX PmInstanceType
    MAX-ACCESS read-only
    STATUS current
    DESCRIPTION "The instance type."
    ::= { cwsPmInstancesEntry 5 }

cwsPmInstancesBinCount OBJECT-TYPE
    SYNTAX Unsigned32
    MAX-ACCESS read-only
    STATUS current
    DESCRIPTION "The number of history bins."
    ::= { cwsPmInstancesEntry 6 }

cwsPmInstancesBinDuration OBJECT-TYPE
    SYNTAX Unsigned32
    MAX-ACCESS read-only
    STATUS current
    DESCRIPTION "The PM bin duration in minutes."
    ::= { cwsPmInstancesEntry 7 }

cwsPmInstancesAttachedInterfaceType OBJECT-TYPE
    SYNTAX PmInterfaceType
    MAX-ACCESS read-only
    STATUS current
    DESCRIPTION "Attached interface type."
    ::= { cwsPmInstancesEntry 8 }

cwsPmInstancesAttachedInterfaceName OBJECT-TYPE
    SYNTAX StringMaxl32
    MAX-ACCESS read-only
    STATUS current
    DESCRIPTION "Attached interface name."
    ::= { cwsPmInstancesEntry 9 }

cwsPmPortExtendedTxRxInstancesTable OBJECT-TYPE
    SYNTAX SEQUENCE OF CwsPmPortExtendedTxRxInstancesEntry
    MAX-ACCESS not-accessible
    STATUS current
    DESCRIPTION "PM Port TxRx instances."
    ::= { cienaWsPmMIB 6 }

cwsPmPortExtendedTxRxInstancesEntry OBJECT-TYPE
    SYNTAX CwsPmPortExtendedTxRxInstancesEntry
    MAX-ACCESS not-accessible
    STATUS current
    DESCRIPTION "Entry for cwsPmPortExtendedTxRxInstancesTable."
    INDEX { cwsPmPortExtendedTxRxInstancesInstanceName }
    ::= { cwsPmPortExtendedTxRxInstancesTable 1 }

CwsPmPortExtendedTxRxInstancesEntry ::= SEQUENCE { 
    cwsPmPortExtendedTxRxInstancesInstanceName Integer32 
}

cwsPmPortExtendedTxRxInstancesInstanceName OBJECT-TYPE
    SYNTAX Integer32(0..2147483647)
    MAX-ACCESS read-only
    STATUS current
    DESCRIPTION "Unique name for PM instance."
    ::= { cwsPmPortExtendedTxRxInstancesEntry 1 }

cwsPmExtendedIdTable OBJECT-TYPE
    SYNTAX SEQUENCE OF CwsPmExtendedIdEntry
    MAX-ACCESS not-accessible
    STATUS current
    DESCRIPTION "PM Extended TxRx instance identification."
    ::= { cienaWsPmMIB 7 }

cwsPmExtendedIdEntry OBJECT-TYPE
    SYNTAX CwsPmExtendedIdEntry
    MAX-ACCESS not-accessible
    STATUS current
    DESCRIPTION "Entry for cwsPmExtendedIdTable."
    INDEX { cwsPmPortExtendedTxRxInstancesInstanceName, cwsPmExtendedIdTableSnmpKey }
    ::= { cwsPmExtendedIdTable 1 }

CwsPmExtendedIdEntry ::= SEQUENCE { 
    cwsPmExtendedIdTableSnmpKey Integer32,
    cwsPmExtendedIdInstanceId Unsigned32,
    cwsPmExtendedIdInstanceType PmInstanceType,
    cwsPmExtendedIdProfileType PmProfileType 
}

cwsPmExtendedIdTableSnmpKey OBJECT-TYPE
    SYNTAX Integer32(0..2147483647)
    MAX-ACCESS not-accessible
    STATUS current
    DESCRIPTION "Unique key for cwsPmExtendedId"
    ::= { cwsPmExtendedIdEntry 1 }

cwsPmExtendedIdInstanceId OBJECT-TYPE
    SYNTAX Unsigned32
    MAX-ACCESS read-write
    STATUS current
    DESCRIPTION "ID of the PM instance."
    ::= { cwsPmExtendedIdEntry 2 }

cwsPmExtendedIdInstanceType OBJECT-TYPE
    SYNTAX PmInstanceType
    MAX-ACCESS read-write
    STATUS current
    DESCRIPTION "The PM instance type."
    ::= { cwsPmExtendedIdEntry 3 }

cwsPmExtendedIdProfileType OBJECT-TYPE
    SYNTAX PmProfileType
    MAX-ACCESS read-write
    STATUS current
    DESCRIPTION "The PM profile type."
    ::= { cwsPmExtendedIdEntry 4 }

cwsPmExtendedStateTable OBJECT-TYPE
    SYNTAX SEQUENCE OF CwsPmExtendedStateEntry
    MAX-ACCESS not-accessible
    STATUS current
    DESCRIPTION "Performance Monitoring Instance State."
    ::= { cienaWsPmMIB 8 }

cwsPmExtendedStateEntry OBJECT-TYPE
    SYNTAX CwsPmExtendedStateEntry
    MAX-ACCESS not-accessible
    STATUS current
    DESCRIPTION "Entry for cwsPmExtendedStateTable."
    INDEX { cwsPmPortExtendedTxRxInstancesInstanceName, cwsPmExtendedStateTableSnmpKey }
    ::= { cwsPmExtendedStateTable 1 }

CwsPmExtendedStateEntry ::= SEQUENCE { 
    cwsPmExtendedStateTableSnmpKey Integer32,
    cwsPmExtendedStateAdminState EnabledDisabledEnum,
    cwsPmExtendedStateOperationalState EnabledDisabledEnum,
    cwsPmExtendedStateCurrentBinId Unsigned32,
    cwsPmExtendedStateCollectionStartDateTime StringMaxl64,
    cwsPmExtendedStateCollectionEndDateTime StringMaxl64 
}

cwsPmExtendedStateTableSnmpKey OBJECT-TYPE
    SYNTAX Integer32(0..2147483647)
    MAX-ACCESS not-accessible
    STATUS current
    DESCRIPTION "Unique key for cwsPmExtendedState"
    ::= { cwsPmExtendedStateEntry 1 }

cwsPmExtendedStateAdminState OBJECT-TYPE
    SYNTAX EnabledDisabledEnum
    MAX-ACCESS read-write
    STATUS current
    DESCRIPTION "The configured administrative state of the port."
    ::= { cwsPmExtendedStateEntry 2 }

cwsPmExtendedStateOperationalState OBJECT-TYPE
    SYNTAX EnabledDisabledEnum
    MAX-ACCESS read-only
    STATUS current
    DESCRIPTION "The operational state of the PM instance."
    ::= { cwsPmExtendedStateEntry 3 }

cwsPmExtendedStateCurrentBinId OBJECT-TYPE
    SYNTAX Unsigned32
    MAX-ACCESS read-only
    STATUS current
    DESCRIPTION "The operational state of the PM instance."
    ::= { cwsPmExtendedStateEntry 4 }

cwsPmExtendedStateCollectionStartDateTime OBJECT-TYPE
    SYNTAX StringMaxl64
    MAX-ACCESS read-only
    STATUS current
    DESCRIPTION "The PM stats collection starting date and time."
    ::= { cwsPmExtendedStateEntry 5 }

cwsPmExtendedStateCollectionEndDateTime OBJECT-TYPE
    SYNTAX StringMaxl64
    MAX-ACCESS read-only
    STATUS current
    DESCRIPTION "The PM stats collection ending date and time."
    ::= { cwsPmExtendedStateEntry 6 }

cwsPmExtendedPropertiesTable OBJECT-TYPE
    SYNTAX SEQUENCE OF CwsPmExtendedPropertiesEntry
    MAX-ACCESS not-accessible
    STATUS current
    DESCRIPTION "PM instance properties."
    ::= { cienaWsPmMIB 9 }

cwsPmExtendedPropertiesEntry OBJECT-TYPE
    SYNTAX CwsPmExtendedPropertiesEntry
    MAX-ACCESS not-accessible
    STATUS current
    DESCRIPTION "Entry for cwsPmExtendedPropertiesTable."
    INDEX { cwsPmPortExtendedTxRxInstancesInstanceName, cwsPmExtendedPropertiesTableSnmpKey }
    ::= { cwsPmExtendedPropertiesTable 1 }

CwsPmExtendedPropertiesEntry ::= SEQUENCE { 
    cwsPmExtendedPropertiesTableSnmpKey Integer32,
    cwsPmExtendedPropertiesConfigurationMode PmConfigurationMode,
    cwsPmExtendedPropertiesAlignment PmAlignment,
    cwsPmExtendedPropertiesConfiguredBinCount Unsigned32,
    cwsPmExtendedPropertiesConfiguredBinDuration Unsigned32 
}

cwsPmExtendedPropertiesTableSnmpKey OBJECT-TYPE
    SYNTAX Integer32(0..2147483647)
    MAX-ACCESS not-accessible
    STATUS current
    DESCRIPTION "Unique key for cwsPmExtendedProperties"
    ::= { cwsPmExtendedPropertiesEntry 1 }

cwsPmExtendedPropertiesConfigurationMode OBJECT-TYPE
    SYNTAX PmConfigurationMode
    MAX-ACCESS read-write
    STATUS current
    DESCRIPTION "The PM instance configuration mode"
    ::= { cwsPmExtendedPropertiesEntry 2 }

cwsPmExtendedPropertiesAlignment OBJECT-TYPE
    SYNTAX PmAlignment
    MAX-ACCESS read-write
    STATUS current
    DESCRIPTION "The PM alignment."
    ::= { cwsPmExtendedPropertiesEntry 3 }

cwsPmExtendedPropertiesConfiguredBinCount OBJECT-TYPE
    SYNTAX Unsigned32
    MAX-ACCESS read-write
    STATUS current
    DESCRIPTION "The configured number of history bins."
    ::= { cwsPmExtendedPropertiesEntry 4 }

cwsPmExtendedPropertiesConfiguredBinDuration OBJECT-TYPE
    SYNTAX Unsigned32
    MAX-ACCESS read-write
    STATUS current
    DESCRIPTION "The configured PM bin duration in minutes."
    ::= { cwsPmExtendedPropertiesEntry 5 }

cwsPmExtendedPropertiesAttachedInterfacesTable OBJECT-TYPE
    SYNTAX SEQUENCE OF CwsPmExtendedPropertiesAttachedInterfacesEntry
    MAX-ACCESS not-accessible
    STATUS current
    DESCRIPTION "Attached interface."
    ::= { cienaWsPmMIB 10 }

cwsPmExtendedPropertiesAttachedInterfacesEntry OBJECT-TYPE
    SYNTAX CwsPmExtendedPropertiesAttachedInterfacesEntry
    MAX-ACCESS not-accessible
    STATUS current
    DESCRIPTION "Entry for cwsPmExtendedPropertiesAttachedInterfacesTable."
    INDEX { cwsPmPortExtendedTxRxInstancesInstanceName, cwsPmExtendedPropertiesAttachedInterfacesTableSnmpKey }
    ::= { cwsPmExtendedPropertiesAttachedInterfacesTable 1 }

CwsPmExtendedPropertiesAttachedInterfacesEntry ::= SEQUENCE { 
    cwsPmExtendedPropertiesAttachedInterfacesTableSnmpKey Integer32,
    cwsPmExtendedPropertiesAttachedInterfacesType PmInterfaceType,
    cwsPmExtendedPropertiesAttachedInterfacesName StringMaxl32,
    cwsPmExtendedPropertiesAttachedInterfacesOperationalState EnabledDisabledEnum 
}

cwsPmExtendedPropertiesAttachedInterfacesTableSnmpKey OBJECT-TYPE
    SYNTAX Integer32(0..2147483647)
    MAX-ACCESS not-accessible
    STATUS current
    DESCRIPTION "Unique key for cwsPmExtendedPropertiesAttachedInterfaces"
    ::= { cwsPmExtendedPropertiesAttachedInterfacesEntry 1 }

cwsPmExtendedPropertiesAttachedInterfacesType OBJECT-TYPE
    SYNTAX PmInterfaceType
    MAX-ACCESS read-write
    STATUS current
    DESCRIPTION "Attached interface type."
    ::= { cwsPmExtendedPropertiesAttachedInterfacesEntry 2 }

cwsPmExtendedPropertiesAttachedInterfacesName OBJECT-TYPE
    SYNTAX StringMaxl32
    MAX-ACCESS read-write
    STATUS current
    DESCRIPTION "Attached interface name."
    ::= { cwsPmExtendedPropertiesAttachedInterfacesEntry 3 }

cwsPmExtendedPropertiesAttachedInterfacesOperationalState OBJECT-TYPE
    SYNTAX EnabledDisabledEnum
    MAX-ACCESS read-write
    STATUS current
    DESCRIPTION "Attached interface operational state."
    ::= { cwsPmExtendedPropertiesAttachedInterfacesEntry 4 }

cwsPmExtendedCurrentIdTable OBJECT-TYPE
    SYNTAX SEQUENCE OF CwsPmExtendedCurrentIdEntry
    MAX-ACCESS not-accessible
    STATUS current
    DESCRIPTION "PM Bin identification."
    ::= { cienaWsPmMIB 11 }

cwsPmExtendedCurrentIdEntry OBJECT-TYPE
    SYNTAX CwsPmExtendedCurrentIdEntry
    MAX-ACCESS not-accessible
    STATUS current
    DESCRIPTION "Entry for cwsPmExtendedCurrentIdTable."
    INDEX { cwsPmPortExtendedTxRxInstancesInstanceName, cwsPmExtendedCurrentIdTableSnmpKey }
    ::= { cwsPmExtendedCurrentIdTable 1 }

CwsPmExtendedCurrentIdEntry ::= SEQUENCE { 
    cwsPmExtendedCurrentIdTableSnmpKey Integer32,
    cwsPmExtendedCurrentIdBinNumber Unsigned32,
    cwsPmExtendedCurrentIdBinName StringMaxl32 
}

cwsPmExtendedCurrentIdTableSnmpKey OBJECT-TYPE
    SYNTAX Integer32(0..2147483647)
    MAX-ACCESS not-accessible
    STATUS current
    DESCRIPTION "Unique key for cwsPmExtendedCurrentId"
    ::= { cwsPmExtendedCurrentIdEntry 1 }

cwsPmExtendedCurrentIdBinNumber OBJECT-TYPE
    SYNTAX Unsigned32
    MAX-ACCESS read-write
    STATUS current
    DESCRIPTION "The PM bin number."
    ::= { cwsPmExtendedCurrentIdEntry 2 }

cwsPmExtendedCurrentIdBinName OBJECT-TYPE
    SYNTAX StringMaxl32
    MAX-ACCESS read-write
    STATUS current
    DESCRIPTION "The PM bin name."
    ::= { cwsPmExtendedCurrentIdEntry 3 }

cwsPmExtendedCurrentStateTable OBJECT-TYPE
    SYNTAX SEQUENCE OF CwsPmExtendedCurrentStateEntry
    MAX-ACCESS not-accessible
    STATUS current
    DESCRIPTION "PM bin state."
    ::= { cienaWsPmMIB 12 }

cwsPmExtendedCurrentStateEntry OBJECT-TYPE
    SYNTAX CwsPmExtendedCurrentStateEntry
    MAX-ACCESS not-accessible
    STATUS current
    DESCRIPTION "Entry for cwsPmExtendedCurrentStateTable."
    INDEX { cwsPmPortExtendedTxRxInstancesInstanceName, cwsPmExtendedCurrentStateTableSnmpKey }
    ::= { cwsPmExtendedCurrentStateTable 1 }

CwsPmExtendedCurrentStateEntry ::= SEQUENCE { 
    cwsPmExtendedCurrentStateTableSnmpKey Integer32,
    cwsPmExtendedCurrentStateStartDateTime StringMaxl32,
    cwsPmExtendedCurrentStateClearedDateTime StringMaxl32,
    cwsPmExtendedCurrentStateState PmBinState 
}

cwsPmExtendedCurrentStateTableSnmpKey OBJECT-TYPE
    SYNTAX Integer32(0..2147483647)
    MAX-ACCESS not-accessible
    STATUS current
    DESCRIPTION "Unique key for cwsPmExtendedCurrentState"
    ::= { cwsPmExtendedCurrentStateEntry 1 }

cwsPmExtendedCurrentStateStartDateTime OBJECT-TYPE
    SYNTAX StringMaxl32
    MAX-ACCESS read-write
    STATUS current
    DESCRIPTION "Start date and time."
    ::= { cwsPmExtendedCurrentStateEntry 2 }

cwsPmExtendedCurrentStateClearedDateTime OBJECT-TYPE
    SYNTAX StringMaxl32
    MAX-ACCESS read-write
    STATUS current
    DESCRIPTION "Cleared date and time."
    ::= { cwsPmExtendedCurrentStateEntry 3 }

cwsPmExtendedCurrentStateState OBJECT-TYPE
    SYNTAX PmBinState
    MAX-ACCESS read-write
    STATUS current
    DESCRIPTION "The PM bin state."
    ::= { cwsPmExtendedCurrentStateEntry 4 }

cwsPmExtendedCurrentStatisticsTable OBJECT-TYPE
    SYNTAX SEQUENCE OF CwsPmExtendedCurrentStatisticsEntry
    MAX-ACCESS not-accessible
    STATUS current
    DESCRIPTION "Statistics data."
    ::= { cienaWsPmMIB 13 }

cwsPmExtendedCurrentStatisticsEntry OBJECT-TYPE
    SYNTAX CwsPmExtendedCurrentStatisticsEntry
    MAX-ACCESS not-accessible
    STATUS current
    DESCRIPTION "Entry for cwsPmExtendedCurrentStatisticsTable."
    INDEX { cwsPmPortExtendedTxRxInstancesInstanceName, cwsPmExtendedCurrentStatisticsTableSnmpKey }
    ::= { cwsPmExtendedCurrentStatisticsTable 1 }

CwsPmExtendedCurrentStatisticsEntry ::= SEQUENCE { 
    cwsPmExtendedCurrentStatisticsTableSnmpKey Integer32,
    cwsPmExtendedCurrentStatisticsFrameErrorRatio Counter64 
}

cwsPmExtendedCurrentStatisticsTableSnmpKey OBJECT-TYPE
    SYNTAX Integer32(0..2147483647)
    MAX-ACCESS not-accessible
    STATUS current
    DESCRIPTION "Unique key for cwsPmExtendedCurrentStatistics"
    ::= { cwsPmExtendedCurrentStatisticsEntry 1 }

cwsPmExtendedCurrentStatisticsFrameErrorRatio OBJECT-TYPE
    SYNTAX Counter64
    MAX-ACCESS read-only
    STATUS current
    DESCRIPTION "RMON frame error ratio."
    ::= { cwsPmExtendedCurrentStatisticsEntry 2 }

cwsPmExtendedCurrentRxIfCountsTable OBJECT-TYPE
    SYNTAX SEQUENCE OF CwsPmExtendedCurrentRxIfCountsEntry
    MAX-ACCESS not-accessible
    STATUS current
    DESCRIPTION "Rx counts."
    ::= { cienaWsPmMIB 14 }

cwsPmExtendedCurrentRxIfCountsEntry OBJECT-TYPE
    SYNTAX CwsPmExtendedCurrentRxIfCountsEntry
    MAX-ACCESS not-accessible
    STATUS current
    DESCRIPTION "Entry for cwsPmExtendedCurrentRxIfCountsTable."
    INDEX { cwsPmPortExtendedTxRxInstancesInstanceName, cwsPmExtendedCurrentRxIfCountsTableSnmpKey }
    ::= { cwsPmExtendedCurrentRxIfCountsTable 1 }

CwsPmExtendedCurrentRxIfCountsEntry ::= SEQUENCE { 
    cwsPmExtendedCurrentRxIfCountsTableSnmpKey Integer32,
    cwsPmExtendedCurrentRxIfCountsBytes Counter64,
    cwsPmExtendedCurrentRxIfCountsPackets Counter64,
    cwsPmExtendedCurrentRxIfCountsAverageLinkUtilization Decimal1Dig,
    cwsPmExtendedCurrentRxIfCountsCrcErroredPackets Counter64,
    cwsPmExtendedCurrentRxIfCountsMulticastPackets Counter64,
    cwsPmExtendedCurrentRxIfCountsBroadcastPackets Counter64,
    cwsPmExtendedCurrentRxIfCountsPausePackets Counter64,
    cwsPmExtendedCurrentRxIfCountsUndersizedPackets Counter64,
    cwsPmExtendedCurrentRxIfCountsOversizedPackets Counter64,
    cwsPmExtendedCurrentRxIfCountsFragmentPackets Counter64,
    cwsPmExtendedCurrentRxIfCountsJabberPackets Counter64,
    cwsPmExtendedCurrentRxIfCountsLengthOutRangePackets Counter64,
    cwsPmExtendedCurrentRxIfCountsPackets64Octet Counter64,
    cwsPmExtendedCurrentRxIfCountsPackets65127Octet Counter64,
    cwsPmExtendedCurrentRxIfCountsPackets128255Octet Counter64,
    cwsPmExtendedCurrentRxIfCountsPackets256511Octet Counter64,
    cwsPmExtendedCurrentRxIfCountsPackets5121023Octet Counter64,
    cwsPmExtendedCurrentRxIfCountsPackets10241518Octet Counter64 
}

cwsPmExtendedCurrentRxIfCountsTableSnmpKey OBJECT-TYPE
    SYNTAX Integer32(0..2147483647)
    MAX-ACCESS not-accessible
    STATUS current
    DESCRIPTION "Unique key for cwsPmExtendedCurrentRxIfCounts"
    ::= { cwsPmExtendedCurrentRxIfCountsEntry 1 }

cwsPmExtendedCurrentRxIfCountsBytes OBJECT-TYPE
    SYNTAX Counter64
    MAX-ACCESS read-write
    STATUS current
    DESCRIPTION "Number of bytes received including good and bad packets. This includes FCS bytes, but excludes framing bits."
    ::= { cwsPmExtendedCurrentRxIfCountsEntry 2 }

cwsPmExtendedCurrentRxIfCountsPackets OBJECT-TYPE
    SYNTAX Counter64
    MAX-ACCESS read-write
    STATUS current
    DESCRIPTION "Number of packets received, including all unicast, multicast, broadcast, MAC control, and bad packets"
    ::= { cwsPmExtendedCurrentRxIfCountsEntry 3 }

cwsPmExtendedCurrentRxIfCountsAverageLinkUtilization OBJECT-TYPE
    SYNTAX Decimal1Dig
    MAX-ACCESS read-write
    STATUS current
    DESCRIPTION "Average percent utilization derived from Rx bytes and port speed."
    ::= { cwsPmExtendedCurrentRxIfCountsEntry 19 }

cwsPmExtendedCurrentRxIfCountsCrcErroredPackets OBJECT-TYPE
    SYNTAX Counter64
    MAX-ACCESS read-write
    STATUS current
    DESCRIPTION "Number of packets received which contained an FCS error and were between 64 and 1518 bytes in length."
    ::= { cwsPmExtendedCurrentRxIfCountsEntry 4 }

cwsPmExtendedCurrentRxIfCountsMulticastPackets OBJECT-TYPE
    SYNTAX Counter64
    MAX-ACCESS read-write
    STATUS current
    DESCRIPTION "Number of good multicast packets received that were between 64 and 1518 bytes in length. Excludes MAC control frames"
    ::= { cwsPmExtendedCurrentRxIfCountsEntry 5 }

cwsPmExtendedCurrentRxIfCountsBroadcastPackets OBJECT-TYPE
    SYNTAX Counter64
    MAX-ACCESS read-write
    STATUS current
    DESCRIPTION "Number of good broadcast packets received that were between 64 and 1518 bytes in length. Excludes MAC control frames"
    ::= { cwsPmExtendedCurrentRxIfCountsEntry 6 }

cwsPmExtendedCurrentRxIfCountsPausePackets OBJECT-TYPE
    SYNTAX Counter64
    MAX-ACCESS read-write
    STATUS current
    DESCRIPTION "Number of received valid pause packets that were between 64 and 1518 bytes in length"
    ::= { cwsPmExtendedCurrentRxIfCountsEntry 7 }

cwsPmExtendedCurrentRxIfCountsUndersizedPackets OBJECT-TYPE
    SYNTAX Counter64
    MAX-ACCESS read-write
    STATUS current
    DESCRIPTION "Number of packets received that were less than 64 bytes (excluding framing bits but including FCS bytes) and were otherwise well formed. This counter also includes the number of packets discarded because of Ethernet length check errors. Undersize packets are discarded."
    ::= { cwsPmExtendedCurrentRxIfCountsEntry 8 }

cwsPmExtendedCurrentRxIfCountsOversizedPackets OBJECT-TYPE
    SYNTAX Counter64
    MAX-ACCESS read-write
    STATUS current
    DESCRIPTION "Number of packets received (including unicast, multicast, and broadcast packets) that were longer than 1518 bytes up to the configured maximum frame size, that contained a valid FCS (excluding framing bits but including FCS bytes), and that were otherwise well formed"
    ::= { cwsPmExtendedCurrentRxIfCountsEntry 9 }

cwsPmExtendedCurrentRxIfCountsFragmentPackets OBJECT-TYPE
    SYNTAX Counter64
    MAX-ACCESS read-write
    STATUS current
    DESCRIPTION "Number of packets received between 10 and 63 bytes in length (excluding framing bits but including FCS bytes) that had either a bad FCS with an integral number of bytes (FCS Error) or a bad FCS with a non-integral number of bytes (Alignment Error). Fragment packets are discarded."
    ::= { cwsPmExtendedCurrentRxIfCountsEntry 10 }

cwsPmExtendedCurrentRxIfCountsJabberPackets OBJECT-TYPE
    SYNTAX Counter64
    MAX-ACCESS read-write
    STATUS current
    DESCRIPTION "Number of packets received that were longer than 1518 bytes up to the configured maximum frame size (excluding framing bits, but including FCS bytes), and had either a bad FCS with an integral number of bytes (FCS Error) or a bad FCS with a non-integral number of bytes (Alignment Error). Jabber packets are discarded"
    ::= { cwsPmExtendedCurrentRxIfCountsEntry 11 }

cwsPmExtendedCurrentRxIfCountsLengthOutRangePackets OBJECT-TYPE
    SYNTAX Counter64
    MAX-ACCESS read-write
    STATUS current
    DESCRIPTION "Number of packets received that exceeded the maximum frame size and contained a valid or invalid FCS"
    ::= { cwsPmExtendedCurrentRxIfCountsEntry 12 }

cwsPmExtendedCurrentRxIfCountsPackets64Octet OBJECT-TYPE
    SYNTAX Counter64
    MAX-ACCESS read-write
    STATUS current
    DESCRIPTION "Number of packets (including bad packets) received that were 64 bytes in length (excluding framing bits but including FCS bytes)."
    ::= { cwsPmExtendedCurrentRxIfCountsEntry 13 }

cwsPmExtendedCurrentRxIfCountsPackets65127Octet OBJECT-TYPE
    SYNTAX Counter64
    MAX-ACCESS read-write
    STATUS current
    DESCRIPTION "Number of good and bad packets received that were between 65 and 127 bytes in length (excluding framing bits but including FCS bytes)."
    ::= { cwsPmExtendedCurrentRxIfCountsEntry 14 }

cwsPmExtendedCurrentRxIfCountsPackets128255Octet OBJECT-TYPE
    SYNTAX Counter64
    MAX-ACCESS read-write
    STATUS current
    DESCRIPTION "Number of good and bad packets received that were between 128 and 255 bytes in length inclusive (excluding framing bits but including FCS bytes)."
    ::= { cwsPmExtendedCurrentRxIfCountsEntry 15 }

cwsPmExtendedCurrentRxIfCountsPackets256511Octet OBJECT-TYPE
    SYNTAX Counter64
    MAX-ACCESS read-write
    STATUS current
    DESCRIPTION "Number of good and bad packets received that were between 256 and 511 bytes in length inclusive (excluding framing bits but including FCS bytes)."
    ::= { cwsPmExtendedCurrentRxIfCountsEntry 16 }

cwsPmExtendedCurrentRxIfCountsPackets5121023Octet OBJECT-TYPE
    SYNTAX Counter64
    MAX-ACCESS read-write
    STATUS current
    DESCRIPTION "Number of good and bad packets received that were between 512 and 1023 bytes in length inclusive (excluding framing bits but including FCS bytes)."
    ::= { cwsPmExtendedCurrentRxIfCountsEntry 17 }

cwsPmExtendedCurrentRxIfCountsPackets10241518Octet OBJECT-TYPE
    SYNTAX Counter64
    MAX-ACCESS read-write
    STATUS current
    DESCRIPTION "Number of good and bad packets received that were between 1024 and 1518 bytes in length inclusive (excluding framing bits but including FCS bytes)."
    ::= { cwsPmExtendedCurrentRxIfCountsEntry 18 }

cwsPmExtendedCurrentTxIfCountsTable OBJECT-TYPE
    SYNTAX SEQUENCE OF CwsPmExtendedCurrentTxIfCountsEntry
    MAX-ACCESS not-accessible
    STATUS current
    DESCRIPTION "Tx counts."
    ::= { cienaWsPmMIB 15 }

cwsPmExtendedCurrentTxIfCountsEntry OBJECT-TYPE
    SYNTAX CwsPmExtendedCurrentTxIfCountsEntry
    MAX-ACCESS not-accessible
    STATUS current
    DESCRIPTION "Entry for cwsPmExtendedCurrentTxIfCountsTable."
    INDEX { cwsPmPortExtendedTxRxInstancesInstanceName, cwsPmExtendedCurrentTxIfCountsTableSnmpKey }
    ::= { cwsPmExtendedCurrentTxIfCountsTable 1 }

CwsPmExtendedCurrentTxIfCountsEntry ::= SEQUENCE { 
    cwsPmExtendedCurrentTxIfCountsTableSnmpKey Integer32,
    cwsPmExtendedCurrentTxIfCountsBytes Counter64,
    cwsPmExtendedCurrentTxIfCountsPackets Counter64,
    cwsPmExtendedCurrentTxIfCountsAverageLinkUtilization Decimal1Dig,
    cwsPmExtendedCurrentTxIfCountsCrcErroredPackets Counter64,
    cwsPmExtendedCurrentTxIfCountsMulticastPackets Counter64,
    cwsPmExtendedCurrentTxIfCountsBroadcastPackets Counter64,
    cwsPmExtendedCurrentTxIfCountsPausePackets Counter64,
    cwsPmExtendedCurrentTxIfCountsExcessiveDeferredPackets Counter64,
    cwsPmExtendedCurrentTxIfCountsGiantPackets Counter64,
    cwsPmExtendedCurrentTxIfCountsUnderrunPackets Counter64,
    cwsPmExtendedCurrentTxIfCountsLengthCheckErrorPackets Counter64,
    cwsPmExtendedCurrentTxIfCountsLengthOutRangePackets Counter64 
}

cwsPmExtendedCurrentTxIfCountsTableSnmpKey OBJECT-TYPE
    SYNTAX Integer32(0..2147483647)
    MAX-ACCESS not-accessible
    STATUS current
    DESCRIPTION "Unique key for cwsPmExtendedCurrentTxIfCounts"
    ::= { cwsPmExtendedCurrentTxIfCountsEntry 1 }

cwsPmExtendedCurrentTxIfCountsBytes OBJECT-TYPE
    SYNTAX Counter64
    MAX-ACCESS read-write
    STATUS current
    DESCRIPTION "Number of transmitted bytes in good and bad packets including FCS bytes and excluding frame bits."
    ::= { cwsPmExtendedCurrentTxIfCountsEntry 2 }

cwsPmExtendedCurrentTxIfCountsPackets OBJECT-TYPE
    SYNTAX Counter64
    MAX-ACCESS read-write
    STATUS current
    DESCRIPTION "Number of transmitted packets, including all unicast, multicast, broadcast, MAC control, and bad packets"
    ::= { cwsPmExtendedCurrentTxIfCountsEntry 3 }

cwsPmExtendedCurrentTxIfCountsAverageLinkUtilization OBJECT-TYPE
    SYNTAX Decimal1Dig
    MAX-ACCESS read-write
    STATUS current
    DESCRIPTION "Average percent utilization derived from Tx bytes and port speed."
    ::= { cwsPmExtendedCurrentTxIfCountsEntry 13 }

cwsPmExtendedCurrentTxIfCountsCrcErroredPackets OBJECT-TYPE
    SYNTAX Counter64
    MAX-ACCESS read-write
    STATUS current
    DESCRIPTION "Number of transmitted packets with an FCS error"
    ::= { cwsPmExtendedCurrentTxIfCountsEntry 4 }

cwsPmExtendedCurrentTxIfCountsMulticastPackets OBJECT-TYPE
    SYNTAX Counter64
    MAX-ACCESS read-write
    STATUS current
    DESCRIPTION "Number of good multicast packets transmitted"
    ::= { cwsPmExtendedCurrentTxIfCountsEntry 5 }

cwsPmExtendedCurrentTxIfCountsBroadcastPackets OBJECT-TYPE
    SYNTAX Counter64
    MAX-ACCESS read-write
    STATUS current
    DESCRIPTION "Number of good broadcast packets transmitted"
    ::= { cwsPmExtendedCurrentTxIfCountsEntry 6 }

cwsPmExtendedCurrentTxIfCountsPausePackets OBJECT-TYPE
    SYNTAX Counter64
    MAX-ACCESS read-write
    STATUS current
    DESCRIPTION "Number of pause packets transmitted"
    ::= { cwsPmExtendedCurrentTxIfCountsEntry 7 }

cwsPmExtendedCurrentTxIfCountsExcessiveDeferredPackets OBJECT-TYPE
    SYNTAX Counter64
    MAX-ACCESS read-write
    STATUS current
    DESCRIPTION "Number of transmitted packets experiencing two or more deferrals. Applicable to copper ports only"
    ::= { cwsPmExtendedCurrentTxIfCountsEntry 8 }

cwsPmExtendedCurrentTxIfCountsGiantPackets OBJECT-TYPE
    SYNTAX Counter64
    MAX-ACCESS read-write
    STATUS current
    DESCRIPTION "Number of well-formed packets larger than 1518 bytes, including FCS bytes but excluding framing bits."
    ::= { cwsPmExtendedCurrentTxIfCountsEntry 9 }

cwsPmExtendedCurrentTxIfCountsUnderrunPackets OBJECT-TYPE
    SYNTAX Counter64
    MAX-ACCESS read-write
    STATUS current
    DESCRIPTION "Number of underrun packets transmitted"
    ::= { cwsPmExtendedCurrentTxIfCountsEntry 10 }

cwsPmExtendedCurrentTxIfCountsLengthCheckErrorPackets OBJECT-TYPE
    SYNTAX Counter64
    MAX-ACCESS read-write
    STATUS current
    DESCRIPTION "Number of length check packets transmitted"
    ::= { cwsPmExtendedCurrentTxIfCountsEntry 11 }

cwsPmExtendedCurrentTxIfCountsLengthOutRangePackets OBJECT-TYPE
    SYNTAX Counter64
    MAX-ACCESS read-write
    STATUS current
    DESCRIPTION "Number of length out-of-range packets transmitted"
    ::= { cwsPmExtendedCurrentTxIfCountsEntry 12 }

cwsPmExtendedCurrentTxQueueTable OBJECT-TYPE
    SYNTAX SEQUENCE OF CwsPmExtendedCurrentTxQueueEntry
    MAX-ACCESS not-accessible
    STATUS current
    DESCRIPTION "Tx queue."
    ::= { cienaWsPmMIB 16 }

cwsPmExtendedCurrentTxQueueEntry OBJECT-TYPE
    SYNTAX CwsPmExtendedCurrentTxQueueEntry
    MAX-ACCESS not-accessible
    STATUS current
    DESCRIPTION "Entry for cwsPmExtendedCurrentTxQueueTable."
    INDEX { cwsPmPortExtendedTxRxInstancesInstanceName, cwsPmExtendedCurrentTxQueueTableSnmpKey }
    ::= { cwsPmExtendedCurrentTxQueueTable 1 }

CwsPmExtendedCurrentTxQueueEntry ::= SEQUENCE { 
    cwsPmExtendedCurrentTxQueueTableSnmpKey Integer32,
    cwsPmExtendedCurrentTxQueuePacketDropCountSummary Counter64,
    cwsPmExtendedCurrentTxQueueQ0PacketDropCount Counter64,
    cwsPmExtendedCurrentTxQueueQ1PacketDropCount Counter64,
    cwsPmExtendedCurrentTxQueueQ2PacketDropCount Counter64,
    cwsPmExtendedCurrentTxQueueQ3PacketDropCount Counter64,
    cwsPmExtendedCurrentTxQueueQ4PacketDropCount Counter64,
    cwsPmExtendedCurrentTxQueueQ5PacketDropCount Counter64,
    cwsPmExtendedCurrentTxQueueQ6PacketDropCount Counter64,
    cwsPmExtendedCurrentTxQueueQ7PacketDropCount Counter64 
}

cwsPmExtendedCurrentTxQueueTableSnmpKey OBJECT-TYPE
    SYNTAX Integer32(0..2147483647)
    MAX-ACCESS not-accessible
    STATUS current
    DESCRIPTION "Unique key for cwsPmExtendedCurrentTxQueue"
    ::= { cwsPmExtendedCurrentTxQueueEntry 1 }

cwsPmExtendedCurrentTxQueuePacketDropCountSummary OBJECT-TYPE
    SYNTAX Counter64
    MAX-ACCESS read-write
    STATUS current
    DESCRIPTION "Summary of the number of bytes dropped from queues 0 to 3 (Q0, Q1, Q2, and Q3)"
    ::= { cwsPmExtendedCurrentTxQueueEntry 2 }

cwsPmExtendedCurrentTxQueueQ0PacketDropCount OBJECT-TYPE
    SYNTAX Counter64
    MAX-ACCESS read-write
    STATUS current
    DESCRIPTION "The number of bytes dropped from queue 0 (Q0)"
    ::= { cwsPmExtendedCurrentTxQueueEntry 3 }

cwsPmExtendedCurrentTxQueueQ1PacketDropCount OBJECT-TYPE
    SYNTAX Counter64
    MAX-ACCESS read-write
    STATUS current
    DESCRIPTION "The number of bytes dropped from queue 1 (Q1)"
    ::= { cwsPmExtendedCurrentTxQueueEntry 4 }

cwsPmExtendedCurrentTxQueueQ2PacketDropCount OBJECT-TYPE
    SYNTAX Counter64
    MAX-ACCESS read-write
    STATUS current
    DESCRIPTION "The number of bytes dropped from queue 2 (Q2)"
    ::= { cwsPmExtendedCurrentTxQueueEntry 5 }

cwsPmExtendedCurrentTxQueueQ3PacketDropCount OBJECT-TYPE
    SYNTAX Counter64
    MAX-ACCESS read-write
    STATUS current
    DESCRIPTION "The number of bytes dropped from queue 3 (Q3)"
    ::= { cwsPmExtendedCurrentTxQueueEntry 6 }

cwsPmExtendedCurrentTxQueueQ4PacketDropCount OBJECT-TYPE
    SYNTAX Counter64
    MAX-ACCESS read-write
    STATUS current
    DESCRIPTION "The number of bytes dropped from queue 4 (Q4)"
    ::= { cwsPmExtendedCurrentTxQueueEntry 7 }

cwsPmExtendedCurrentTxQueueQ5PacketDropCount OBJECT-TYPE
    SYNTAX Counter64
    MAX-ACCESS read-write
    STATUS current
    DESCRIPTION "The number of bytes dropped from queue 5 (Q5)"
    ::= { cwsPmExtendedCurrentTxQueueEntry 8 }

cwsPmExtendedCurrentTxQueueQ6PacketDropCount OBJECT-TYPE
    SYNTAX Counter64
    MAX-ACCESS read-write
    STATUS current
    DESCRIPTION "The number of bytes dropped from queue 6 (Q6)"
    ::= { cwsPmExtendedCurrentTxQueueEntry 9 }

cwsPmExtendedCurrentTxQueueQ7PacketDropCount OBJECT-TYPE
    SYNTAX Counter64
    MAX-ACCESS read-write
    STATUS current
    DESCRIPTION "The number of bytes dropped from queue 7 (Q7)"
    ::= { cwsPmExtendedCurrentTxQueueEntry 10 }

cwsPmExtendedCurrentMacLayerTable OBJECT-TYPE
    SYNTAX SEQUENCE OF CwsPmExtendedCurrentMacLayerEntry
    MAX-ACCESS not-accessible
    STATUS obsolete
    DESCRIPTION "None"
    ::= { cienaWsPmMIB 17 }

cwsPmExtendedCurrentMacLayerEntry OBJECT-TYPE
    SYNTAX CwsPmExtendedCurrentMacLayerEntry
    MAX-ACCESS not-accessible
    STATUS obsolete
    DESCRIPTION "Entry for cwsPmExtendedCurrentMacLayerTable."
    INDEX { cwsPmPortExtendedTxRxInstancesInstanceName, cwsPmExtendedCurrentMacLayerTableSnmpKey }
    ::= { cwsPmExtendedCurrentMacLayerTable 1 }

CwsPmExtendedCurrentMacLayerEntry ::= SEQUENCE { 
    cwsPmExtendedCurrentMacLayerTableSnmpKey Integer32,
    cwsPmExtendedCurrentMacLayerUnavailableSeconds Counter64 
}

cwsPmExtendedCurrentMacLayerTableSnmpKey OBJECT-TYPE
    SYNTAX Integer32(0..2147483647)
    MAX-ACCESS not-accessible
    STATUS current
    DESCRIPTION "Unique key for cwsPmExtendedCurrentMacLayer"
    ::= { cwsPmExtendedCurrentMacLayerEntry 1 }

cwsPmExtendedCurrentMacLayerUnavailableSeconds OBJECT-TYPE
    SYNTAX Counter64
    MAX-ACCESS read-only
    STATUS obsolete
    DESCRIPTION "The number of seconds that the interface was unavailable."
    ::= { cwsPmExtendedCurrentMacLayerEntry 2 }

cwsPmExtendedCurrentPcsLayerTable OBJECT-TYPE
    SYNTAX SEQUENCE OF CwsPmExtendedCurrentPcsLayerEntry
    MAX-ACCESS not-accessible
    STATUS current
    DESCRIPTION "None"
    ::= { cienaWsPmMIB 18 }

cwsPmExtendedCurrentPcsLayerEntry OBJECT-TYPE
    SYNTAX CwsPmExtendedCurrentPcsLayerEntry
    MAX-ACCESS not-accessible
    STATUS current
    DESCRIPTION "Entry for cwsPmExtendedCurrentPcsLayerTable."
    INDEX { cwsPmPortExtendedTxRxInstancesInstanceName, cwsPmExtendedCurrentPcsLayerTableSnmpKey }
    ::= { cwsPmExtendedCurrentPcsLayerTable 1 }

CwsPmExtendedCurrentPcsLayerEntry ::= SEQUENCE { 
    cwsPmExtendedCurrentPcsLayerTableSnmpKey Integer32,
    cwsPmExtendedCurrentPcsLayerErroredSeconds Counter64,
    cwsPmExtendedCurrentPcsLayerSeverelyErroredSeconds Counter64,
    cwsPmExtendedCurrentPcsLayerUnavailableSeconds Counter64 
}

cwsPmExtendedCurrentPcsLayerTableSnmpKey OBJECT-TYPE
    SYNTAX Integer32(0..2147483647)
    MAX-ACCESS not-accessible
    STATUS current
    DESCRIPTION "Unique key for cwsPmExtendedCurrentPcsLayer"
    ::= { cwsPmExtendedCurrentPcsLayerEntry 1 }

cwsPmExtendedCurrentPcsLayerErroredSeconds OBJECT-TYPE
    SYNTAX Counter64
    MAX-ACCESS read-write
    STATUS current
    DESCRIPTION "Number of seconds that error happened."
    ::= { cwsPmExtendedCurrentPcsLayerEntry 2 }

cwsPmExtendedCurrentPcsLayerSeverelyErroredSeconds OBJECT-TYPE
    SYNTAX Counter64
    MAX-ACCESS read-write
    STATUS current
    DESCRIPTION "Number of seconds that severe error happened."
    ::= { cwsPmExtendedCurrentPcsLayerEntry 3 }

cwsPmExtendedCurrentPcsLayerUnavailableSeconds OBJECT-TYPE
    SYNTAX Counter64
    MAX-ACCESS read-write
    STATUS current
    DESCRIPTION "Number of seconds that the interface was unavailable."
    ::= { cwsPmExtendedCurrentPcsLayerEntry 4 }

cwsPmExtendedCurrentPcsSyncHeaderErrorsTable OBJECT-TYPE
    SYNTAX SEQUENCE OF CwsPmExtendedCurrentPcsSyncHeaderErrorsEntry
    MAX-ACCESS not-accessible
    STATUS current
    DESCRIPTION "None"
    ::= { cienaWsPmMIB 19 }

cwsPmExtendedCurrentPcsSyncHeaderErrorsEntry OBJECT-TYPE
    SYNTAX CwsPmExtendedCurrentPcsSyncHeaderErrorsEntry
    MAX-ACCESS not-accessible
    STATUS current
    DESCRIPTION "Entry for cwsPmExtendedCurrentPcsSyncHeaderErrorsTable."
    INDEX { cwsPmPortExtendedTxRxInstancesInstanceName, cwsPmExtendedCurrentPcsSyncHeaderErrorsTableSnmpKey }
    ::= { cwsPmExtendedCurrentPcsSyncHeaderErrorsTable 1 }

CwsPmExtendedCurrentPcsSyncHeaderErrorsEntry ::= SEQUENCE { 
    cwsPmExtendedCurrentPcsSyncHeaderErrorsTableSnmpKey Integer32,
    cwsPmExtendedCurrentPcsSyncHeaderErrorsCount Counter64 
}

cwsPmExtendedCurrentPcsSyncHeaderErrorsTableSnmpKey OBJECT-TYPE
    SYNTAX Integer32(0..2147483647)
    MAX-ACCESS not-accessible
    STATUS current
    DESCRIPTION "Unique key for cwsPmExtendedCurrentPcsSyncHeaderErrors"
    ::= { cwsPmExtendedCurrentPcsSyncHeaderErrorsEntry 1 }

cwsPmExtendedCurrentPcsSyncHeaderErrorsCount OBJECT-TYPE
    SYNTAX Counter64
    MAX-ACCESS read-only
    STATUS current
    DESCRIPTION "Sync header errors count value."
    ::= { cwsPmExtendedCurrentPcsSyncHeaderErrorsEntry 2 }

cwsPmExtendedCurrentPcsBlockErrorsTable OBJECT-TYPE
    SYNTAX SEQUENCE OF CwsPmExtendedCurrentPcsBlockErrorsEntry
    MAX-ACCESS not-accessible
    STATUS current
    DESCRIPTION "None"
    ::= { cienaWsPmMIB 20 }

cwsPmExtendedCurrentPcsBlockErrorsEntry OBJECT-TYPE
    SYNTAX CwsPmExtendedCurrentPcsBlockErrorsEntry
    MAX-ACCESS not-accessible
    STATUS current
    DESCRIPTION "Entry for cwsPmExtendedCurrentPcsBlockErrorsTable."
    INDEX { cwsPmPortExtendedTxRxInstancesInstanceName, cwsPmExtendedCurrentPcsBlockErrorsTableSnmpKey }
    ::= { cwsPmExtendedCurrentPcsBlockErrorsTable 1 }

CwsPmExtendedCurrentPcsBlockErrorsEntry ::= SEQUENCE { 
    cwsPmExtendedCurrentPcsBlockErrorsTableSnmpKey Integer32,
    cwsPmExtendedCurrentPcsBlockErrorsCount Counter64 
}

cwsPmExtendedCurrentPcsBlockErrorsTableSnmpKey OBJECT-TYPE
    SYNTAX Integer32(0..2147483647)
    MAX-ACCESS not-accessible
    STATUS current
    DESCRIPTION "Unique key for cwsPmExtendedCurrentPcsBlockErrors"
    ::= { cwsPmExtendedCurrentPcsBlockErrorsEntry 1 }

cwsPmExtendedCurrentPcsBlockErrorsCount OBJECT-TYPE
    SYNTAX Counter64
    MAX-ACCESS read-only
    STATUS current
    DESCRIPTION "Block errors count value."
    ::= { cwsPmExtendedCurrentPcsBlockErrorsEntry 2 }

cwsPmExtendedCurrentPcsMultilaneBipErrorsTable OBJECT-TYPE
    SYNTAX SEQUENCE OF CwsPmExtendedCurrentPcsMultilaneBipErrorsEntry
    MAX-ACCESS not-accessible
    STATUS current
    DESCRIPTION "None"
    ::= { cienaWsPmMIB 21 }

cwsPmExtendedCurrentPcsMultilaneBipErrorsEntry OBJECT-TYPE
    SYNTAX CwsPmExtendedCurrentPcsMultilaneBipErrorsEntry
    MAX-ACCESS not-accessible
    STATUS current
    DESCRIPTION "Entry for cwsPmExtendedCurrentPcsMultilaneBipErrorsTable."
    INDEX { cwsPmPortExtendedTxRxInstancesInstanceName, cwsPmExtendedCurrentPcsMultilaneBipErrorsTableSnmpKey }
    ::= { cwsPmExtendedCurrentPcsMultilaneBipErrorsTable 1 }

CwsPmExtendedCurrentPcsMultilaneBipErrorsEntry ::= SEQUENCE { 
    cwsPmExtendedCurrentPcsMultilaneBipErrorsTableSnmpKey Integer32,
    cwsPmExtendedCurrentPcsMultilaneBipErrorsCount Counter64 
}

cwsPmExtendedCurrentPcsMultilaneBipErrorsTableSnmpKey OBJECT-TYPE
    SYNTAX Integer32(0..2147483647)
    MAX-ACCESS not-accessible
    STATUS current
    DESCRIPTION "Unique key for cwsPmExtendedCurrentPcsMultilaneBipErrors"
    ::= { cwsPmExtendedCurrentPcsMultilaneBipErrorsEntry 1 }

cwsPmExtendedCurrentPcsMultilaneBipErrorsCount OBJECT-TYPE
    SYNTAX Counter64
    MAX-ACCESS read-only
    STATUS current
    DESCRIPTION "Multilane bip errors count value."
    ::= { cwsPmExtendedCurrentPcsMultilaneBipErrorsEntry 2 }

cwsPmExtendedCurrentOduLayerTable OBJECT-TYPE
    SYNTAX SEQUENCE OF CwsPmExtendedCurrentOduLayerEntry
    MAX-ACCESS not-accessible
    STATUS current
    DESCRIPTION "None"
    ::= { cienaWsPmMIB 121 }

cwsPmExtendedCurrentOduLayerEntry OBJECT-TYPE
    SYNTAX CwsPmExtendedCurrentOduLayerEntry
    MAX-ACCESS not-accessible
    STATUS current
    DESCRIPTION "Entry for cwsPmExtendedCurrentOduLayerTable."
    INDEX { cwsPmPortExtendedTxRxInstancesInstanceName, cwsPmExtendedCurrentOduLayerTableSnmpKey }
    ::= { cwsPmExtendedCurrentOduLayerTable 1 }

CwsPmExtendedCurrentOduLayerEntry ::= SEQUENCE { 
    cwsPmExtendedCurrentOduLayerTableSnmpKey Integer32,
    cwsPmExtendedCurrentOduLayerErroredSeconds Counter64,
    cwsPmExtendedCurrentOduLayerSeverelyErroredSeconds Counter64,
    cwsPmExtendedCurrentOduLayerUnavailableSeconds Counter64 
}

cwsPmExtendedCurrentOduLayerTableSnmpKey OBJECT-TYPE
    SYNTAX Integer32(0..2147483647)
    MAX-ACCESS not-accessible
    STATUS current
    DESCRIPTION "Unique key for cwsPmExtendedCurrentOduLayer"
    ::= { cwsPmExtendedCurrentOduLayerEntry 1 }

cwsPmExtendedCurrentOduLayerErroredSeconds OBJECT-TYPE
    SYNTAX Counter64
    MAX-ACCESS read-write
    STATUS current
    DESCRIPTION "Number of seconds that error happened."
    ::= { cwsPmExtendedCurrentOduLayerEntry 2 }

cwsPmExtendedCurrentOduLayerSeverelyErroredSeconds OBJECT-TYPE
    SYNTAX Counter64
    MAX-ACCESS read-write
    STATUS current
    DESCRIPTION "Number of seconds that severe error happened."
    ::= { cwsPmExtendedCurrentOduLayerEntry 3 }

cwsPmExtendedCurrentOduLayerUnavailableSeconds OBJECT-TYPE
    SYNTAX Counter64
    MAX-ACCESS read-write
    STATUS current
    DESCRIPTION "Number of seconds that the interface was unavailable."
    ::= { cwsPmExtendedCurrentOduLayerEntry 4 }

cwsPmExtendedCurrentFecLayerTable OBJECT-TYPE
    SYNTAX SEQUENCE OF CwsPmExtendedCurrentFecLayerEntry
    MAX-ACCESS not-accessible
    STATUS current
    DESCRIPTION "None"
    ::= { cienaWsPmMIB 22 }

cwsPmExtendedCurrentFecLayerEntry OBJECT-TYPE
    SYNTAX CwsPmExtendedCurrentFecLayerEntry
    MAX-ACCESS not-accessible
    STATUS current
    DESCRIPTION "Entry for cwsPmExtendedCurrentFecLayerTable."
    INDEX { cwsPmPortExtendedTxRxInstancesInstanceName, cwsPmExtendedCurrentFecLayerTableSnmpKey }
    ::= { cwsPmExtendedCurrentFecLayerTable 1 }

CwsPmExtendedCurrentFecLayerEntry ::= SEQUENCE { 
    cwsPmExtendedCurrentFecLayerTableSnmpKey Integer32,
    cwsPmExtendedCurrentFecLayerCorrectedBlockCount Counter64,
    cwsPmExtendedCurrentFecLayerUncorrectedBlockCount Counter64,
    cwsPmExtendedCurrentFecLayerSymbolErrorCount Counter64 
}

cwsPmExtendedCurrentFecLayerTableSnmpKey OBJECT-TYPE
    SYNTAX Integer32(0..2147483647)
    MAX-ACCESS not-accessible
    STATUS current
    DESCRIPTION "Unique key for cwsPmExtendedCurrentFecLayer"
    ::= { cwsPmExtendedCurrentFecLayerEntry 1 }

cwsPmExtendedCurrentFecLayerCorrectedBlockCount OBJECT-TYPE
    SYNTAX Counter64
    MAX-ACCESS read-write
    STATUS current
    DESCRIPTION "Fec layer corrected block count"
    ::= { cwsPmExtendedCurrentFecLayerEntry 2 }

cwsPmExtendedCurrentFecLayerUncorrectedBlockCount OBJECT-TYPE
    SYNTAX Counter64
    MAX-ACCESS read-write
    STATUS current
    DESCRIPTION "Fec layer uncorrected block count"
    ::= { cwsPmExtendedCurrentFecLayerEntry 3 }

cwsPmExtendedCurrentFecLayerSymbolErrorCount OBJECT-TYPE
    SYNTAX Counter64
    MAX-ACCESS read-write
    STATUS current
    DESCRIPTION "Fec layer symbol error count"
    ::= { cwsPmExtendedCurrentFecLayerEntry 4 }

cwsPmExtendedCurrent24hIdTable OBJECT-TYPE
    SYNTAX SEQUENCE OF CwsPmExtendedCurrent24hIdEntry
    MAX-ACCESS not-accessible
    STATUS current
    DESCRIPTION "PM Bin identification."
    ::= { cienaWsPmMIB 23 }

cwsPmExtendedCurrent24hIdEntry OBJECT-TYPE
    SYNTAX CwsPmExtendedCurrent24hIdEntry
    MAX-ACCESS not-accessible
    STATUS current
    DESCRIPTION "Entry for cwsPmExtendedCurrent24hIdTable."
    INDEX { cwsPmPortExtendedTxRxInstancesInstanceName, cwsPmExtendedCurrent24hIdTableSnmpKey }
    ::= { cwsPmExtendedCurrent24hIdTable 1 }

CwsPmExtendedCurrent24hIdEntry ::= SEQUENCE { 
    cwsPmExtendedCurrent24hIdTableSnmpKey Integer32,
    cwsPmExtendedCurrent24hIdBinNumber Unsigned32,
    cwsPmExtendedCurrent24hIdBinName StringMaxl32 
}

cwsPmExtendedCurrent24hIdTableSnmpKey OBJECT-TYPE
    SYNTAX Integer32(0..2147483647)
    MAX-ACCESS not-accessible
    STATUS current
    DESCRIPTION "Unique key for cwsPmExtendedCurrent24hId"
    ::= { cwsPmExtendedCurrent24hIdEntry 1 }

cwsPmExtendedCurrent24hIdBinNumber OBJECT-TYPE
    SYNTAX Unsigned32
    MAX-ACCESS read-write
    STATUS current
    DESCRIPTION "The PM bin number."
    ::= { cwsPmExtendedCurrent24hIdEntry 2 }

cwsPmExtendedCurrent24hIdBinName OBJECT-TYPE
    SYNTAX StringMaxl32
    MAX-ACCESS read-write
    STATUS current
    DESCRIPTION "The PM bin name."
    ::= { cwsPmExtendedCurrent24hIdEntry 3 }

cwsPmExtendedCurrent24hStateTable OBJECT-TYPE
    SYNTAX SEQUENCE OF CwsPmExtendedCurrent24hStateEntry
    MAX-ACCESS not-accessible
    STATUS current
    DESCRIPTION "PM bin state."
    ::= { cienaWsPmMIB 24 }

cwsPmExtendedCurrent24hStateEntry OBJECT-TYPE
    SYNTAX CwsPmExtendedCurrent24hStateEntry
    MAX-ACCESS not-accessible
    STATUS current
    DESCRIPTION "Entry for cwsPmExtendedCurrent24hStateTable."
    INDEX { cwsPmPortExtendedTxRxInstancesInstanceName, cwsPmExtendedCurrent24hStateTableSnmpKey }
    ::= { cwsPmExtendedCurrent24hStateTable 1 }

CwsPmExtendedCurrent24hStateEntry ::= SEQUENCE { 
    cwsPmExtendedCurrent24hStateTableSnmpKey Integer32,
    cwsPmExtendedCurrent24hStateStartDateTime StringMaxl32,
    cwsPmExtendedCurrent24hStateClearedDateTime StringMaxl32,
    cwsPmExtendedCurrent24hStateState PmBinState 
}

cwsPmExtendedCurrent24hStateTableSnmpKey OBJECT-TYPE
    SYNTAX Integer32(0..2147483647)
    MAX-ACCESS not-accessible
    STATUS current
    DESCRIPTION "Unique key for cwsPmExtendedCurrent24hState"
    ::= { cwsPmExtendedCurrent24hStateEntry 1 }

cwsPmExtendedCurrent24hStateStartDateTime OBJECT-TYPE
    SYNTAX StringMaxl32
    MAX-ACCESS read-write
    STATUS current
    DESCRIPTION "Start date and time."
    ::= { cwsPmExtendedCurrent24hStateEntry 2 }

cwsPmExtendedCurrent24hStateClearedDateTime OBJECT-TYPE
    SYNTAX StringMaxl32
    MAX-ACCESS read-write
    STATUS current
    DESCRIPTION "Cleared date and time."
    ::= { cwsPmExtendedCurrent24hStateEntry 3 }

cwsPmExtendedCurrent24hStateState OBJECT-TYPE
    SYNTAX PmBinState
    MAX-ACCESS read-write
    STATUS current
    DESCRIPTION "The PM bin state."
    ::= { cwsPmExtendedCurrent24hStateEntry 4 }

cwsPmExtendedCurrent24hStatisticsTable OBJECT-TYPE
    SYNTAX SEQUENCE OF CwsPmExtendedCurrent24hStatisticsEntry
    MAX-ACCESS not-accessible
    STATUS current
    DESCRIPTION "Statistics data."
    ::= { cienaWsPmMIB 25 }

cwsPmExtendedCurrent24hStatisticsEntry OBJECT-TYPE
    SYNTAX CwsPmExtendedCurrent24hStatisticsEntry
    MAX-ACCESS not-accessible
    STATUS current
    DESCRIPTION "Entry for cwsPmExtendedCurrent24hStatisticsTable."
    INDEX { cwsPmPortExtendedTxRxInstancesInstanceName, cwsPmExtendedCurrent24hStatisticsTableSnmpKey }
    ::= { cwsPmExtendedCurrent24hStatisticsTable 1 }

CwsPmExtendedCurrent24hStatisticsEntry ::= SEQUENCE { 
    cwsPmExtendedCurrent24hStatisticsTableSnmpKey Integer32,
    cwsPmExtendedCurrent24hStatisticsFrameErrorRatio Counter64 
}

cwsPmExtendedCurrent24hStatisticsTableSnmpKey OBJECT-TYPE
    SYNTAX Integer32(0..2147483647)
    MAX-ACCESS not-accessible
    STATUS current
    DESCRIPTION "Unique key for cwsPmExtendedCurrent24hStatistics"
    ::= { cwsPmExtendedCurrent24hStatisticsEntry 1 }

cwsPmExtendedCurrent24hStatisticsFrameErrorRatio OBJECT-TYPE
    SYNTAX Counter64
    MAX-ACCESS read-only
    STATUS current
    DESCRIPTION "RMON frame error ratio."
    ::= { cwsPmExtendedCurrent24hStatisticsEntry 2 }

cwsPmExtendedCurrent24hRxIfCountsTable OBJECT-TYPE
    SYNTAX SEQUENCE OF CwsPmExtendedCurrent24hRxIfCountsEntry
    MAX-ACCESS not-accessible
    STATUS current
    DESCRIPTION "Rx counts."
    ::= { cienaWsPmMIB 26 }

cwsPmExtendedCurrent24hRxIfCountsEntry OBJECT-TYPE
    SYNTAX CwsPmExtendedCurrent24hRxIfCountsEntry
    MAX-ACCESS not-accessible
    STATUS current
    DESCRIPTION "Entry for cwsPmExtendedCurrent24hRxIfCountsTable."
    INDEX { cwsPmPortExtendedTxRxInstancesInstanceName, cwsPmExtendedCurrent24hRxIfCountsTableSnmpKey }
    ::= { cwsPmExtendedCurrent24hRxIfCountsTable 1 }

CwsPmExtendedCurrent24hRxIfCountsEntry ::= SEQUENCE { 
    cwsPmExtendedCurrent24hRxIfCountsTableSnmpKey Integer32,
    cwsPmExtendedCurrent24hRxIfCountsBytes Counter64,
    cwsPmExtendedCurrent24hRxIfCountsPackets Counter64,
    cwsPmExtendedCurrent24hRxIfCountsAverageLinkUtilization Decimal1Dig,
    cwsPmExtendedCurrent24hRxIfCountsCrcErroredPackets Counter64,
    cwsPmExtendedCurrent24hRxIfCountsMulticastPackets Counter64,
    cwsPmExtendedCurrent24hRxIfCountsBroadcastPackets Counter64,
    cwsPmExtendedCurrent24hRxIfCountsPausePackets Counter64,
    cwsPmExtendedCurrent24hRxIfCountsUndersizedPackets Counter64,
    cwsPmExtendedCurrent24hRxIfCountsOversizedPackets Counter64,
    cwsPmExtendedCurrent24hRxIfCountsFragmentPackets Counter64,
    cwsPmExtendedCurrent24hRxIfCountsJabberPackets Counter64,
    cwsPmExtendedCurrent24hRxIfCountsLengthOutRangePackets Counter64,
    cwsPmExtendedCurrent24hRxIfCountsPackets64Octet Counter64,
    cwsPmExtendedCurrent24hRxIfCountsPackets65127Octet Counter64,
    cwsPmExtendedCurrent24hRxIfCountsPackets128255Octet Counter64,
    cwsPmExtendedCurrent24hRxIfCountsPackets256511Octet Counter64,
    cwsPmExtendedCurrent24hRxIfCountsPackets5121023Octet Counter64,
    cwsPmExtendedCurrent24hRxIfCountsPackets10241518Octet Counter64 
}

cwsPmExtendedCurrent24hRxIfCountsTableSnmpKey OBJECT-TYPE
    SYNTAX Integer32(0..2147483647)
    MAX-ACCESS not-accessible
    STATUS current
    DESCRIPTION "Unique key for cwsPmExtendedCurrent24hRxIfCounts"
    ::= { cwsPmExtendedCurrent24hRxIfCountsEntry 1 }

cwsPmExtendedCurrent24hRxIfCountsBytes OBJECT-TYPE
    SYNTAX Counter64
    MAX-ACCESS read-write
    STATUS current
    DESCRIPTION "Number of bytes received including good and bad packets. This includes FCS bytes, but excludes framing bits."
    ::= { cwsPmExtendedCurrent24hRxIfCountsEntry 2 }

cwsPmExtendedCurrent24hRxIfCountsPackets OBJECT-TYPE
    SYNTAX Counter64
    MAX-ACCESS read-write
    STATUS current
    DESCRIPTION "Number of packets received, including all unicast, multicast, broadcast, MAC control, and bad packets"
    ::= { cwsPmExtendedCurrent24hRxIfCountsEntry 3 }

cwsPmExtendedCurrent24hRxIfCountsAverageLinkUtilization OBJECT-TYPE
    SYNTAX Decimal1Dig
    MAX-ACCESS read-write
    STATUS current
    DESCRIPTION "Average percent utilization derived from Rx bytes and port speed."
    ::= { cwsPmExtendedCurrent24hRxIfCountsEntry 19 }

cwsPmExtendedCurrent24hRxIfCountsCrcErroredPackets OBJECT-TYPE
    SYNTAX Counter64
    MAX-ACCESS read-write
    STATUS current
    DESCRIPTION "Number of packets received which contained an FCS error and were between 64 and 1518 bytes in length."
    ::= { cwsPmExtendedCurrent24hRxIfCountsEntry 4 }

cwsPmExtendedCurrent24hRxIfCountsMulticastPackets OBJECT-TYPE
    SYNTAX Counter64
    MAX-ACCESS read-write
    STATUS current
    DESCRIPTION "Number of good multicast packets received that were between 64 and 1518 bytes in length. Excludes MAC control frames"
    ::= { cwsPmExtendedCurrent24hRxIfCountsEntry 5 }

cwsPmExtendedCurrent24hRxIfCountsBroadcastPackets OBJECT-TYPE
    SYNTAX Counter64
    MAX-ACCESS read-write
    STATUS current
    DESCRIPTION "Number of good broadcast packets received that were between 64 and 1518 bytes in length. Excludes MAC control frames"
    ::= { cwsPmExtendedCurrent24hRxIfCountsEntry 6 }

cwsPmExtendedCurrent24hRxIfCountsPausePackets OBJECT-TYPE
    SYNTAX Counter64
    MAX-ACCESS read-write
    STATUS current
    DESCRIPTION "Number of received valid pause packets that were between 64 and 1518 bytes in length"
    ::= { cwsPmExtendedCurrent24hRxIfCountsEntry 7 }

cwsPmExtendedCurrent24hRxIfCountsUndersizedPackets OBJECT-TYPE
    SYNTAX Counter64
    MAX-ACCESS read-write
    STATUS current
    DESCRIPTION "Number of packets received that were less than 64 bytes (excluding framing bits but including FCS bytes) and were otherwise well formed. This counter also includes the number of packets discarded because of Ethernet length check errors. Undersize packets are discarded."
    ::= { cwsPmExtendedCurrent24hRxIfCountsEntry 8 }

cwsPmExtendedCurrent24hRxIfCountsOversizedPackets OBJECT-TYPE
    SYNTAX Counter64
    MAX-ACCESS read-write
    STATUS current
    DESCRIPTION "Number of packets received (including unicast, multicast, and broadcast packets) that were longer than 1518 bytes up to the configured maximum frame size, that contained a valid FCS (excluding framing bits but including FCS bytes), and that were otherwise well formed"
    ::= { cwsPmExtendedCurrent24hRxIfCountsEntry 9 }

cwsPmExtendedCurrent24hRxIfCountsFragmentPackets OBJECT-TYPE
    SYNTAX Counter64
    MAX-ACCESS read-write
    STATUS current
    DESCRIPTION "Number of packets received between 10 and 63 bytes in length (excluding framing bits but including FCS bytes) that had either a bad FCS with an integral number of bytes (FCS Error) or a bad FCS with a non-integral number of bytes (Alignment Error). Fragment packets are discarded."
    ::= { cwsPmExtendedCurrent24hRxIfCountsEntry 10 }

cwsPmExtendedCurrent24hRxIfCountsJabberPackets OBJECT-TYPE
    SYNTAX Counter64
    MAX-ACCESS read-write
    STATUS current
    DESCRIPTION "Number of packets received that were longer than 1518 bytes up to the configured maximum frame size (excluding framing bits, but including FCS bytes), and had either a bad FCS with an integral number of bytes (FCS Error) or a bad FCS with a non-integral number of bytes (Alignment Error). Jabber packets are discarded"
    ::= { cwsPmExtendedCurrent24hRxIfCountsEntry 11 }

cwsPmExtendedCurrent24hRxIfCountsLengthOutRangePackets OBJECT-TYPE
    SYNTAX Counter64
    MAX-ACCESS read-write
    STATUS current
    DESCRIPTION "Number of packets received that exceeded the maximum frame size and contained a valid or invalid FCS"
    ::= { cwsPmExtendedCurrent24hRxIfCountsEntry 12 }

cwsPmExtendedCurrent24hRxIfCountsPackets64Octet OBJECT-TYPE
    SYNTAX Counter64
    MAX-ACCESS read-write
    STATUS current
    DESCRIPTION "Number of packets (including bad packets) received that were 64 bytes in length (excluding framing bits but including FCS bytes)."
    ::= { cwsPmExtendedCurrent24hRxIfCountsEntry 13 }

cwsPmExtendedCurrent24hRxIfCountsPackets65127Octet OBJECT-TYPE
    SYNTAX Counter64
    MAX-ACCESS read-write
    STATUS current
    DESCRIPTION "Number of good and bad packets received that were between 65 and 127 bytes in length (excluding framing bits but including FCS bytes)."
    ::= { cwsPmExtendedCurrent24hRxIfCountsEntry 14 }

cwsPmExtendedCurrent24hRxIfCountsPackets128255Octet OBJECT-TYPE
    SYNTAX Counter64
    MAX-ACCESS read-write
    STATUS current
    DESCRIPTION "Number of good and bad packets received that were between 128 and 255 bytes in length inclusive (excluding framing bits but including FCS bytes)."
    ::= { cwsPmExtendedCurrent24hRxIfCountsEntry 15 }

cwsPmExtendedCurrent24hRxIfCountsPackets256511Octet OBJECT-TYPE
    SYNTAX Counter64
    MAX-ACCESS read-write
    STATUS current
    DESCRIPTION "Number of good and bad packets received that were between 256 and 511 bytes in length inclusive (excluding framing bits but including FCS bytes)."
    ::= { cwsPmExtendedCurrent24hRxIfCountsEntry 16 }

cwsPmExtendedCurrent24hRxIfCountsPackets5121023Octet OBJECT-TYPE
    SYNTAX Counter64
    MAX-ACCESS read-write
    STATUS current
    DESCRIPTION "Number of good and bad packets received that were between 512 and 1023 bytes in length inclusive (excluding framing bits but including FCS bytes)."
    ::= { cwsPmExtendedCurrent24hRxIfCountsEntry 17 }

cwsPmExtendedCurrent24hRxIfCountsPackets10241518Octet OBJECT-TYPE
    SYNTAX Counter64
    MAX-ACCESS read-write
    STATUS current
    DESCRIPTION "Number of good and bad packets received that were between 1024 and 1518 bytes in length inclusive (excluding framing bits but including FCS bytes)."
    ::= { cwsPmExtendedCurrent24hRxIfCountsEntry 18 }

cwsPmExtendedCurrent24hTxIfCountsTable OBJECT-TYPE
    SYNTAX SEQUENCE OF CwsPmExtendedCurrent24hTxIfCountsEntry
    MAX-ACCESS not-accessible
    STATUS current
    DESCRIPTION "Tx counts."
    ::= { cienaWsPmMIB 27 }

cwsPmExtendedCurrent24hTxIfCountsEntry OBJECT-TYPE
    SYNTAX CwsPmExtendedCurrent24hTxIfCountsEntry
    MAX-ACCESS not-accessible
    STATUS current
    DESCRIPTION "Entry for cwsPmExtendedCurrent24hTxIfCountsTable."
    INDEX { cwsPmPortExtendedTxRxInstancesInstanceName, cwsPmExtendedCurrent24hTxIfCountsTableSnmpKey }
    ::= { cwsPmExtendedCurrent24hTxIfCountsTable 1 }

CwsPmExtendedCurrent24hTxIfCountsEntry ::= SEQUENCE { 
    cwsPmExtendedCurrent24hTxIfCountsTableSnmpKey Integer32,
    cwsPmExtendedCurrent24hTxIfCountsBytes Counter64,
    cwsPmExtendedCurrent24hTxIfCountsPackets Counter64,
    cwsPmExtendedCurrent24hTxIfCountsAverageLinkUtilization Decimal1Dig,
    cwsPmExtendedCurrent24hTxIfCountsCrcErroredPackets Counter64,
    cwsPmExtendedCurrent24hTxIfCountsMulticastPackets Counter64,
    cwsPmExtendedCurrent24hTxIfCountsBroadcastPackets Counter64,
    cwsPmExtendedCurrent24hTxIfCountsPausePackets Counter64,
    cwsPmExtendedCurrent24hTxIfCountsExcessiveDeferredPackets Counter64,
    cwsPmExtendedCurrent24hTxIfCountsGiantPackets Counter64,
    cwsPmExtendedCurrent24hTxIfCountsUnderrunPackets Counter64,
    cwsPmExtendedCurrent24hTxIfCountsLengthCheckErrorPackets Counter64,
    cwsPmExtendedCurrent24hTxIfCountsLengthOutRangePackets Counter64 
}

cwsPmExtendedCurrent24hTxIfCountsTableSnmpKey OBJECT-TYPE
    SYNTAX Integer32(0..2147483647)
    MAX-ACCESS not-accessible
    STATUS current
    DESCRIPTION "Unique key for cwsPmExtendedCurrent24hTxIfCounts"
    ::= { cwsPmExtendedCurrent24hTxIfCountsEntry 1 }

cwsPmExtendedCurrent24hTxIfCountsBytes OBJECT-TYPE
    SYNTAX Counter64
    MAX-ACCESS read-write
    STATUS current
    DESCRIPTION "Number of transmitted bytes in good and bad packets including FCS bytes and excluding frame bits."
    ::= { cwsPmExtendedCurrent24hTxIfCountsEntry 2 }

cwsPmExtendedCurrent24hTxIfCountsPackets OBJECT-TYPE
    SYNTAX Counter64
    MAX-ACCESS read-write
    STATUS current
    DESCRIPTION "Number of transmitted packets, including all unicast, multicast, broadcast, MAC control, and bad packets"
    ::= { cwsPmExtendedCurrent24hTxIfCountsEntry 3 }

cwsPmExtendedCurrent24hTxIfCountsAverageLinkUtilization OBJECT-TYPE
    SYNTAX Decimal1Dig
    MAX-ACCESS read-write
    STATUS current
    DESCRIPTION "Average percent utilization derived from Tx bytes and port speed."
    ::= { cwsPmExtendedCurrent24hTxIfCountsEntry 13 }

cwsPmExtendedCurrent24hTxIfCountsCrcErroredPackets OBJECT-TYPE
    SYNTAX Counter64
    MAX-ACCESS read-write
    STATUS current
    DESCRIPTION "Number of transmitted packets with an FCS error"
    ::= { cwsPmExtendedCurrent24hTxIfCountsEntry 4 }

cwsPmExtendedCurrent24hTxIfCountsMulticastPackets OBJECT-TYPE
    SYNTAX Counter64
    MAX-ACCESS read-write
    STATUS current
    DESCRIPTION "Number of good multicast packets transmitted"
    ::= { cwsPmExtendedCurrent24hTxIfCountsEntry 5 }

cwsPmExtendedCurrent24hTxIfCountsBroadcastPackets OBJECT-TYPE
    SYNTAX Counter64
    MAX-ACCESS read-write
    STATUS current
    DESCRIPTION "Number of good broadcast packets transmitted"
    ::= { cwsPmExtendedCurrent24hTxIfCountsEntry 6 }

cwsPmExtendedCurrent24hTxIfCountsPausePackets OBJECT-TYPE
    SYNTAX Counter64
    MAX-ACCESS read-write
    STATUS current
    DESCRIPTION "Number of pause packets transmitted"
    ::= { cwsPmExtendedCurrent24hTxIfCountsEntry 7 }

cwsPmExtendedCurrent24hTxIfCountsExcessiveDeferredPackets OBJECT-TYPE
    SYNTAX Counter64
    MAX-ACCESS read-write
    STATUS current
    DESCRIPTION "Number of transmitted packets experiencing two or more deferrals. Applicable to copper ports only"
    ::= { cwsPmExtendedCurrent24hTxIfCountsEntry 8 }

cwsPmExtendedCurrent24hTxIfCountsGiantPackets OBJECT-TYPE
    SYNTAX Counter64
    MAX-ACCESS read-write
    STATUS current
    DESCRIPTION "Number of well-formed packets larger than 1518 bytes, including FCS bytes but excluding framing bits."
    ::= { cwsPmExtendedCurrent24hTxIfCountsEntry 9 }

cwsPmExtendedCurrent24hTxIfCountsUnderrunPackets OBJECT-TYPE
    SYNTAX Counter64
    MAX-ACCESS read-write
    STATUS current
    DESCRIPTION "Number of underrun packets transmitted"
    ::= { cwsPmExtendedCurrent24hTxIfCountsEntry 10 }

cwsPmExtendedCurrent24hTxIfCountsLengthCheckErrorPackets OBJECT-TYPE
    SYNTAX Counter64
    MAX-ACCESS read-write
    STATUS current
    DESCRIPTION "Number of length check packets transmitted"
    ::= { cwsPmExtendedCurrent24hTxIfCountsEntry 11 }

cwsPmExtendedCurrent24hTxIfCountsLengthOutRangePackets OBJECT-TYPE
    SYNTAX Counter64
    MAX-ACCESS read-write
    STATUS current
    DESCRIPTION "Number of length out-of-range packets transmitted"
    ::= { cwsPmExtendedCurrent24hTxIfCountsEntry 12 }

cwsPmExtendedCurrent24hTxQueueTable OBJECT-TYPE
    SYNTAX SEQUENCE OF CwsPmExtendedCurrent24hTxQueueEntry
    MAX-ACCESS not-accessible
    STATUS current
    DESCRIPTION "Tx queue."
    ::= { cienaWsPmMIB 28 }

cwsPmExtendedCurrent24hTxQueueEntry OBJECT-TYPE
    SYNTAX CwsPmExtendedCurrent24hTxQueueEntry
    MAX-ACCESS not-accessible
    STATUS current
    DESCRIPTION "Entry for cwsPmExtendedCurrent24hTxQueueTable."
    INDEX { cwsPmPortExtendedTxRxInstancesInstanceName, cwsPmExtendedCurrent24hTxQueueTableSnmpKey }
    ::= { cwsPmExtendedCurrent24hTxQueueTable 1 }

CwsPmExtendedCurrent24hTxQueueEntry ::= SEQUENCE { 
    cwsPmExtendedCurrent24hTxQueueTableSnmpKey Integer32,
    cwsPmExtendedCurrent24hTxQueuePacketDropCountSummary Counter64,
    cwsPmExtendedCurrent24hTxQueueQ0PacketDropCount Counter64,
    cwsPmExtendedCurrent24hTxQueueQ1PacketDropCount Counter64,
    cwsPmExtendedCurrent24hTxQueueQ2PacketDropCount Counter64,
    cwsPmExtendedCurrent24hTxQueueQ3PacketDropCount Counter64,
    cwsPmExtendedCurrent24hTxQueueQ4PacketDropCount Counter64,
    cwsPmExtendedCurrent24hTxQueueQ5PacketDropCount Counter64,
    cwsPmExtendedCurrent24hTxQueueQ6PacketDropCount Counter64,
    cwsPmExtendedCurrent24hTxQueueQ7PacketDropCount Counter64 
}

cwsPmExtendedCurrent24hTxQueueTableSnmpKey OBJECT-TYPE
    SYNTAX Integer32(0..2147483647)
    MAX-ACCESS not-accessible
    STATUS current
    DESCRIPTION "Unique key for cwsPmExtendedCurrent24hTxQueue"
    ::= { cwsPmExtendedCurrent24hTxQueueEntry 1 }

cwsPmExtendedCurrent24hTxQueuePacketDropCountSummary OBJECT-TYPE
    SYNTAX Counter64
    MAX-ACCESS read-write
    STATUS current
    DESCRIPTION "Summary of the number of bytes dropped from queues 0 to 3 (Q0, Q1, Q2, and Q3)"
    ::= { cwsPmExtendedCurrent24hTxQueueEntry 2 }

cwsPmExtendedCurrent24hTxQueueQ0PacketDropCount OBJECT-TYPE
    SYNTAX Counter64
    MAX-ACCESS read-write
    STATUS current
    DESCRIPTION "The number of bytes dropped from queue 0 (Q0)"
    ::= { cwsPmExtendedCurrent24hTxQueueEntry 3 }

cwsPmExtendedCurrent24hTxQueueQ1PacketDropCount OBJECT-TYPE
    SYNTAX Counter64
    MAX-ACCESS read-write
    STATUS current
    DESCRIPTION "The number of bytes dropped from queue 1 (Q1)"
    ::= { cwsPmExtendedCurrent24hTxQueueEntry 4 }

cwsPmExtendedCurrent24hTxQueueQ2PacketDropCount OBJECT-TYPE
    SYNTAX Counter64
    MAX-ACCESS read-write
    STATUS current
    DESCRIPTION "The number of bytes dropped from queue 2 (Q2)"
    ::= { cwsPmExtendedCurrent24hTxQueueEntry 5 }

cwsPmExtendedCurrent24hTxQueueQ3PacketDropCount OBJECT-TYPE
    SYNTAX Counter64
    MAX-ACCESS read-write
    STATUS current
    DESCRIPTION "The number of bytes dropped from queue 3 (Q3)"
    ::= { cwsPmExtendedCurrent24hTxQueueEntry 6 }

cwsPmExtendedCurrent24hTxQueueQ4PacketDropCount OBJECT-TYPE
    SYNTAX Counter64
    MAX-ACCESS read-write
    STATUS current
    DESCRIPTION "The number of bytes dropped from queue 4 (Q4)"
    ::= { cwsPmExtendedCurrent24hTxQueueEntry 7 }

cwsPmExtendedCurrent24hTxQueueQ5PacketDropCount OBJECT-TYPE
    SYNTAX Counter64
    MAX-ACCESS read-write
    STATUS current
    DESCRIPTION "The number of bytes dropped from queue 5 (Q5)"
    ::= { cwsPmExtendedCurrent24hTxQueueEntry 8 }

cwsPmExtendedCurrent24hTxQueueQ6PacketDropCount OBJECT-TYPE
    SYNTAX Counter64
    MAX-ACCESS read-write
    STATUS current
    DESCRIPTION "The number of bytes dropped from queue 6 (Q6)"
    ::= { cwsPmExtendedCurrent24hTxQueueEntry 9 }

cwsPmExtendedCurrent24hTxQueueQ7PacketDropCount OBJECT-TYPE
    SYNTAX Counter64
    MAX-ACCESS read-write
    STATUS current
    DESCRIPTION "The number of bytes dropped from queue 7 (Q7)"
    ::= { cwsPmExtendedCurrent24hTxQueueEntry 10 }

cwsPmExtendedCurrent24hMacLayerTable OBJECT-TYPE
    SYNTAX SEQUENCE OF CwsPmExtendedCurrent24hMacLayerEntry
    MAX-ACCESS not-accessible
    STATUS obsolete
    DESCRIPTION "None"
    ::= { cienaWsPmMIB 29 }

cwsPmExtendedCurrent24hMacLayerEntry OBJECT-TYPE
    SYNTAX CwsPmExtendedCurrent24hMacLayerEntry
    MAX-ACCESS not-accessible
    STATUS obsolete
    DESCRIPTION "Entry for cwsPmExtendedCurrent24hMacLayerTable."
    INDEX { cwsPmPortExtendedTxRxInstancesInstanceName, cwsPmExtendedCurrent24hMacLayerTableSnmpKey }
    ::= { cwsPmExtendedCurrent24hMacLayerTable 1 }

CwsPmExtendedCurrent24hMacLayerEntry ::= SEQUENCE { 
    cwsPmExtendedCurrent24hMacLayerTableSnmpKey Integer32,
    cwsPmExtendedCurrent24hMacLayerUnavailableSeconds Counter64 
}

cwsPmExtendedCurrent24hMacLayerTableSnmpKey OBJECT-TYPE
    SYNTAX Integer32(0..2147483647)
    MAX-ACCESS not-accessible
    STATUS current
    DESCRIPTION "Unique key for cwsPmExtendedCurrent24hMacLayer"
    ::= { cwsPmExtendedCurrent24hMacLayerEntry 1 }

cwsPmExtendedCurrent24hMacLayerUnavailableSeconds OBJECT-TYPE
    SYNTAX Counter64
    MAX-ACCESS read-only
    STATUS obsolete
    DESCRIPTION "The number of seconds that the interface was unavailable."
    ::= { cwsPmExtendedCurrent24hMacLayerEntry 2 }

cwsPmExtendedCurrent24hPcsLayerTable OBJECT-TYPE
    SYNTAX SEQUENCE OF CwsPmExtendedCurrent24hPcsLayerEntry
    MAX-ACCESS not-accessible
    STATUS current
    DESCRIPTION "None"
    ::= { cienaWsPmMIB 30 }

cwsPmExtendedCurrent24hPcsLayerEntry OBJECT-TYPE
    SYNTAX CwsPmExtendedCurrent24hPcsLayerEntry
    MAX-ACCESS not-accessible
    STATUS current
    DESCRIPTION "Entry for cwsPmExtendedCurrent24hPcsLayerTable."
    INDEX { cwsPmPortExtendedTxRxInstancesInstanceName, cwsPmExtendedCurrent24hPcsLayerTableSnmpKey }
    ::= { cwsPmExtendedCurrent24hPcsLayerTable 1 }

CwsPmExtendedCurrent24hPcsLayerEntry ::= SEQUENCE { 
    cwsPmExtendedCurrent24hPcsLayerTableSnmpKey Integer32,
    cwsPmExtendedCurrent24hPcsLayerErroredSeconds Counter64,
    cwsPmExtendedCurrent24hPcsLayerSeverelyErroredSeconds Counter64,
    cwsPmExtendedCurrent24hPcsLayerUnavailableSeconds Counter64 
}

cwsPmExtendedCurrent24hPcsLayerTableSnmpKey OBJECT-TYPE
    SYNTAX Integer32(0..2147483647)
    MAX-ACCESS not-accessible
    STATUS current
    DESCRIPTION "Unique key for cwsPmExtendedCurrent24hPcsLayer"
    ::= { cwsPmExtendedCurrent24hPcsLayerEntry 1 }

cwsPmExtendedCurrent24hPcsLayerErroredSeconds OBJECT-TYPE
    SYNTAX Counter64
    MAX-ACCESS read-write
    STATUS current
    DESCRIPTION "Number of seconds that error happened."
    ::= { cwsPmExtendedCurrent24hPcsLayerEntry 2 }

cwsPmExtendedCurrent24hPcsLayerSeverelyErroredSeconds OBJECT-TYPE
    SYNTAX Counter64
    MAX-ACCESS read-write
    STATUS current
    DESCRIPTION "Number of seconds that severe error happened."
    ::= { cwsPmExtendedCurrent24hPcsLayerEntry 3 }

cwsPmExtendedCurrent24hPcsLayerUnavailableSeconds OBJECT-TYPE
    SYNTAX Counter64
    MAX-ACCESS read-write
    STATUS current
    DESCRIPTION "Number of seconds that the interface was unavailable."
    ::= { cwsPmExtendedCurrent24hPcsLayerEntry 4 }

cwsPmExtendedCurrent24hPcsSyncHeaderErrorsTable OBJECT-TYPE
    SYNTAX SEQUENCE OF CwsPmExtendedCurrent24hPcsSyncHeaderErrorsEntry
    MAX-ACCESS not-accessible
    STATUS current
    DESCRIPTION "None"
    ::= { cienaWsPmMIB 31 }

cwsPmExtendedCurrent24hPcsSyncHeaderErrorsEntry OBJECT-TYPE
    SYNTAX CwsPmExtendedCurrent24hPcsSyncHeaderErrorsEntry
    MAX-ACCESS not-accessible
    STATUS current
    DESCRIPTION "Entry for cwsPmExtendedCurrent24hPcsSyncHeaderErrorsTable."
    INDEX { cwsPmPortExtendedTxRxInstancesInstanceName, cwsPmExtendedCurrent24hPcsSyncHeaderErrorsTableSnmpKey }
    ::= { cwsPmExtendedCurrent24hPcsSyncHeaderErrorsTable 1 }

CwsPmExtendedCurrent24hPcsSyncHeaderErrorsEntry ::= SEQUENCE { 
    cwsPmExtendedCurrent24hPcsSyncHeaderErrorsTableSnmpKey Integer32,
    cwsPmExtendedCurrent24hPcsSyncHeaderErrorsCount Counter64 
}

cwsPmExtendedCurrent24hPcsSyncHeaderErrorsTableSnmpKey OBJECT-TYPE
    SYNTAX Integer32(0..2147483647)
    MAX-ACCESS not-accessible
    STATUS current
    DESCRIPTION "Unique key for cwsPmExtendedCurrent24hPcsSyncHeaderErrors"
    ::= { cwsPmExtendedCurrent24hPcsSyncHeaderErrorsEntry 1 }

cwsPmExtendedCurrent24hPcsSyncHeaderErrorsCount OBJECT-TYPE
    SYNTAX Counter64
    MAX-ACCESS read-only
    STATUS current
    DESCRIPTION "Sync header errors count value."
    ::= { cwsPmExtendedCurrent24hPcsSyncHeaderErrorsEntry 2 }

cwsPmExtendedCurrent24hPcsBlockErrorsTable OBJECT-TYPE
    SYNTAX SEQUENCE OF CwsPmExtendedCurrent24hPcsBlockErrorsEntry
    MAX-ACCESS not-accessible
    STATUS current
    DESCRIPTION "None"
    ::= { cienaWsPmMIB 32 }

cwsPmExtendedCurrent24hPcsBlockErrorsEntry OBJECT-TYPE
    SYNTAX CwsPmExtendedCurrent24hPcsBlockErrorsEntry
    MAX-ACCESS not-accessible
    STATUS current
    DESCRIPTION "Entry for cwsPmExtendedCurrent24hPcsBlockErrorsTable."
    INDEX { cwsPmPortExtendedTxRxInstancesInstanceName, cwsPmExtendedCurrent24hPcsBlockErrorsTableSnmpKey }
    ::= { cwsPmExtendedCurrent24hPcsBlockErrorsTable 1 }

CwsPmExtendedCurrent24hPcsBlockErrorsEntry ::= SEQUENCE { 
    cwsPmExtendedCurrent24hPcsBlockErrorsTableSnmpKey Integer32,
    cwsPmExtendedCurrent24hPcsBlockErrorsCount Counter64 
}

cwsPmExtendedCurrent24hPcsBlockErrorsTableSnmpKey OBJECT-TYPE
    SYNTAX Integer32(0..2147483647)
    MAX-ACCESS not-accessible
    STATUS current
    DESCRIPTION "Unique key for cwsPmExtendedCurrent24hPcsBlockErrors"
    ::= { cwsPmExtendedCurrent24hPcsBlockErrorsEntry 1 }

cwsPmExtendedCurrent24hPcsBlockErrorsCount OBJECT-TYPE
    SYNTAX Counter64
    MAX-ACCESS read-only
    STATUS current
    DESCRIPTION "Block errors count value."
    ::= { cwsPmExtendedCurrent24hPcsBlockErrorsEntry 2 }

cwsPmExtendedCurrent24hPcsMultilaneBipErrorsTable OBJECT-TYPE
    SYNTAX SEQUENCE OF CwsPmExtendedCurrent24hPcsMultilaneBipErrorsEntry
    MAX-ACCESS not-accessible
    STATUS current
    DESCRIPTION "None"
    ::= { cienaWsPmMIB 33 }

cwsPmExtendedCurrent24hPcsMultilaneBipErrorsEntry OBJECT-TYPE
    SYNTAX CwsPmExtendedCurrent24hPcsMultilaneBipErrorsEntry
    MAX-ACCESS not-accessible
    STATUS current
    DESCRIPTION "Entry for cwsPmExtendedCurrent24hPcsMultilaneBipErrorsTable."
    INDEX { cwsPmPortExtendedTxRxInstancesInstanceName, cwsPmExtendedCurrent24hPcsMultilaneBipErrorsTableSnmpKey }
    ::= { cwsPmExtendedCurrent24hPcsMultilaneBipErrorsTable 1 }

CwsPmExtendedCurrent24hPcsMultilaneBipErrorsEntry ::= SEQUENCE { 
    cwsPmExtendedCurrent24hPcsMultilaneBipErrorsTableSnmpKey Integer32,
    cwsPmExtendedCurrent24hPcsMultilaneBipErrorsCount Counter64 
}

cwsPmExtendedCurrent24hPcsMultilaneBipErrorsTableSnmpKey OBJECT-TYPE
    SYNTAX Integer32(0..2147483647)
    MAX-ACCESS not-accessible
    STATUS current
    DESCRIPTION "Unique key for cwsPmExtendedCurrent24hPcsMultilaneBipErrors"
    ::= { cwsPmExtendedCurrent24hPcsMultilaneBipErrorsEntry 1 }

cwsPmExtendedCurrent24hPcsMultilaneBipErrorsCount OBJECT-TYPE
    SYNTAX Counter64
    MAX-ACCESS read-only
    STATUS current
    DESCRIPTION "Multilane bip errors count value."
    ::= { cwsPmExtendedCurrent24hPcsMultilaneBipErrorsEntry 2 }

cwsPmExtendedCurrent24hOduLayerTable OBJECT-TYPE
    SYNTAX SEQUENCE OF CwsPmExtendedCurrent24hOduLayerEntry
    MAX-ACCESS not-accessible
    STATUS current
    DESCRIPTION "None"
    ::= { cienaWsPmMIB 122 }

cwsPmExtendedCurrent24hOduLayerEntry OBJECT-TYPE
    SYNTAX CwsPmExtendedCurrent24hOduLayerEntry
    MAX-ACCESS not-accessible
    STATUS current
    DESCRIPTION "Entry for cwsPmExtendedCurrent24hOduLayerTable."
    INDEX { cwsPmPortExtendedTxRxInstancesInstanceName, cwsPmExtendedCurrent24hOduLayerTableSnmpKey }
    ::= { cwsPmExtendedCurrent24hOduLayerTable 1 }

CwsPmExtendedCurrent24hOduLayerEntry ::= SEQUENCE { 
    cwsPmExtendedCurrent24hOduLayerTableSnmpKey Integer32,
    cwsPmExtendedCurrent24hOduLayerErroredSeconds Counter64,
    cwsPmExtendedCurrent24hOduLayerSeverelyErroredSeconds Counter64,
    cwsPmExtendedCurrent24hOduLayerUnavailableSeconds Counter64 
}

cwsPmExtendedCurrent24hOduLayerTableSnmpKey OBJECT-TYPE
    SYNTAX Integer32(0..2147483647)
    MAX-ACCESS not-accessible
    STATUS current
    DESCRIPTION "Unique key for cwsPmExtendedCurrent24hOduLayer"
    ::= { cwsPmExtendedCurrent24hOduLayerEntry 1 }

cwsPmExtendedCurrent24hOduLayerErroredSeconds OBJECT-TYPE
    SYNTAX Counter64
    MAX-ACCESS read-write
    STATUS current
    DESCRIPTION "Number of seconds that error happened."
    ::= { cwsPmExtendedCurrent24hOduLayerEntry 2 }

cwsPmExtendedCurrent24hOduLayerSeverelyErroredSeconds OBJECT-TYPE
    SYNTAX Counter64
    MAX-ACCESS read-write
    STATUS current
    DESCRIPTION "Number of seconds that severe error happened."
    ::= { cwsPmExtendedCurrent24hOduLayerEntry 3 }

cwsPmExtendedCurrent24hOduLayerUnavailableSeconds OBJECT-TYPE
    SYNTAX Counter64
    MAX-ACCESS read-write
    STATUS current
    DESCRIPTION "Number of seconds that the interface was unavailable."
    ::= { cwsPmExtendedCurrent24hOduLayerEntry 4 }

cwsPmExtendedCurrent24hFecLayerTable OBJECT-TYPE
    SYNTAX SEQUENCE OF CwsPmExtendedCurrent24hFecLayerEntry
    MAX-ACCESS not-accessible
    STATUS current
    DESCRIPTION "None"
    ::= { cienaWsPmMIB 34 }

cwsPmExtendedCurrent24hFecLayerEntry OBJECT-TYPE
    SYNTAX CwsPmExtendedCurrent24hFecLayerEntry
    MAX-ACCESS not-accessible
    STATUS current
    DESCRIPTION "Entry for cwsPmExtendedCurrent24hFecLayerTable."
    INDEX { cwsPmPortExtendedTxRxInstancesInstanceName, cwsPmExtendedCurrent24hFecLayerTableSnmpKey }
    ::= { cwsPmExtendedCurrent24hFecLayerTable 1 }

CwsPmExtendedCurrent24hFecLayerEntry ::= SEQUENCE { 
    cwsPmExtendedCurrent24hFecLayerTableSnmpKey Integer32,
    cwsPmExtendedCurrent24hFecLayerCorrectedBlockCount Counter64,
    cwsPmExtendedCurrent24hFecLayerUncorrectedBlockCount Counter64,
    cwsPmExtendedCurrent24hFecLayerSymbolErrorCount Counter64 
}

cwsPmExtendedCurrent24hFecLayerTableSnmpKey OBJECT-TYPE
    SYNTAX Integer32(0..2147483647)
    MAX-ACCESS not-accessible
    STATUS current
    DESCRIPTION "Unique key for cwsPmExtendedCurrent24hFecLayer"
    ::= { cwsPmExtendedCurrent24hFecLayerEntry 1 }

cwsPmExtendedCurrent24hFecLayerCorrectedBlockCount OBJECT-TYPE
    SYNTAX Counter64
    MAX-ACCESS read-write
    STATUS current
    DESCRIPTION "Fec layer corrected block count"
    ::= { cwsPmExtendedCurrent24hFecLayerEntry 2 }

cwsPmExtendedCurrent24hFecLayerUncorrectedBlockCount OBJECT-TYPE
    SYNTAX Counter64
    MAX-ACCESS read-write
    STATUS current
    DESCRIPTION "Fec layer uncorrected block count"
    ::= { cwsPmExtendedCurrent24hFecLayerEntry 3 }

cwsPmExtendedCurrent24hFecLayerSymbolErrorCount OBJECT-TYPE
    SYNTAX Counter64
    MAX-ACCESS read-write
    STATUS current
    DESCRIPTION "Fec layer symbol error count"
    ::= { cwsPmExtendedCurrent24hFecLayerEntry 4 }

cwsPmBinsTable OBJECT-TYPE
    SYNTAX SEQUENCE OF CwsPmBinsEntry
    MAX-ACCESS not-accessible
    STATUS current
    DESCRIPTION "Performance Monitoring instance for port."
    ::= { cienaWsPmMIB 35 }

cwsPmBinsEntry OBJECT-TYPE
    SYNTAX CwsPmBinsEntry
    MAX-ACCESS not-accessible
    STATUS current
    DESCRIPTION "Entry for cwsPmBinsTable."
    INDEX { cwsPmPortExtendedTxRxInstancesInstanceName, cwsPmBinsBinNumber }
    ::= { cwsPmBinsTable 1 }

CwsPmBinsEntry ::= SEQUENCE { 
    cwsPmBinsBinNumber Integer32 
}

cwsPmBinsBinNumber OBJECT-TYPE
    SYNTAX Integer32(0..2147483647)
    MAX-ACCESS read-only
    STATUS current
    DESCRIPTION "PM history bins."
    ::= { cwsPmBinsEntry 1 }

cwsPmExtendedHistoryStateTable OBJECT-TYPE
    SYNTAX SEQUENCE OF CwsPmExtendedHistoryStateEntry
    MAX-ACCESS not-accessible
    STATUS current
    DESCRIPTION "PM bin state."
    ::= { cienaWsPmMIB 36 }

cwsPmExtendedHistoryStateEntry OBJECT-TYPE
    SYNTAX CwsPmExtendedHistoryStateEntry
    MAX-ACCESS not-accessible
    STATUS current
    DESCRIPTION "Entry for cwsPmExtendedHistoryStateTable."
    INDEX { cwsPmPortExtendedTxRxInstancesInstanceName, cwsPmBinsBinNumber, cwsPmExtendedHistoryStateTableSnmpKey }
    ::= { cwsPmExtendedHistoryStateTable 1 }

CwsPmExtendedHistoryStateEntry ::= SEQUENCE { 
    cwsPmExtendedHistoryStateTableSnmpKey Integer32,
    cwsPmExtendedHistoryStateStartDateTime StringMaxl32,
    cwsPmExtendedHistoryStateEndDateTime StringMaxl32,
    cwsPmExtendedHistoryStateState PmBinState 
}

cwsPmExtendedHistoryStateTableSnmpKey OBJECT-TYPE
    SYNTAX Integer32(0..2147483647)
    MAX-ACCESS not-accessible
    STATUS current
    DESCRIPTION "Unique key for cwsPmExtendedHistoryState"
    ::= { cwsPmExtendedHistoryStateEntry 1 }

cwsPmExtendedHistoryStateStartDateTime OBJECT-TYPE
    SYNTAX StringMaxl32
    MAX-ACCESS read-write
    STATUS current
    DESCRIPTION "Start date and time."
    ::= { cwsPmExtendedHistoryStateEntry 2 }

cwsPmExtendedHistoryStateEndDateTime OBJECT-TYPE
    SYNTAX StringMaxl32
    MAX-ACCESS read-write
    STATUS current
    DESCRIPTION "End date and time."
    ::= { cwsPmExtendedHistoryStateEntry 3 }

cwsPmExtendedHistoryStateState OBJECT-TYPE
    SYNTAX PmBinState
    MAX-ACCESS read-write
    STATUS current
    DESCRIPTION "The PM bin state."
    ::= { cwsPmExtendedHistoryStateEntry 4 }

cwsPmExtendedHistoryStatisticsTable OBJECT-TYPE
    SYNTAX SEQUENCE OF CwsPmExtendedHistoryStatisticsEntry
    MAX-ACCESS not-accessible
    STATUS current
    DESCRIPTION "PM statistics data saved in a history bin."
    ::= { cienaWsPmMIB 37 }

cwsPmExtendedHistoryStatisticsEntry OBJECT-TYPE
    SYNTAX CwsPmExtendedHistoryStatisticsEntry
    MAX-ACCESS not-accessible
    STATUS current
    DESCRIPTION "Entry for cwsPmExtendedHistoryStatisticsTable."
    INDEX { cwsPmPortExtendedTxRxInstancesInstanceName, cwsPmBinsBinNumber, cwsPmExtendedHistoryStatisticsTableSnmpKey }
    ::= { cwsPmExtendedHistoryStatisticsTable 1 }

CwsPmExtendedHistoryStatisticsEntry ::= SEQUENCE { 
    cwsPmExtendedHistoryStatisticsTableSnmpKey Integer32,
    cwsPmExtendedHistoryStatisticsFrameErrorRatio Counter64 
}

cwsPmExtendedHistoryStatisticsTableSnmpKey OBJECT-TYPE
    SYNTAX Integer32(0..2147483647)
    MAX-ACCESS not-accessible
    STATUS current
    DESCRIPTION "Unique key for cwsPmExtendedHistoryStatistics"
    ::= { cwsPmExtendedHistoryStatisticsEntry 1 }

cwsPmExtendedHistoryStatisticsFrameErrorRatio OBJECT-TYPE
    SYNTAX Counter64
    MAX-ACCESS read-only
    STATUS current
    DESCRIPTION "RMON frame error ratio."
    ::= { cwsPmExtendedHistoryStatisticsEntry 2 }

cwsPmExtendedHistoryRxIfCountsTable OBJECT-TYPE
    SYNTAX SEQUENCE OF CwsPmExtendedHistoryRxIfCountsEntry
    MAX-ACCESS not-accessible
    STATUS current
    DESCRIPTION "Rx counts."
    ::= { cienaWsPmMIB 38 }

cwsPmExtendedHistoryRxIfCountsEntry OBJECT-TYPE
    SYNTAX CwsPmExtendedHistoryRxIfCountsEntry
    MAX-ACCESS not-accessible
    STATUS current
    DESCRIPTION "Entry for cwsPmExtendedHistoryRxIfCountsTable."
    INDEX { cwsPmPortExtendedTxRxInstancesInstanceName, cwsPmBinsBinNumber, cwsPmExtendedHistoryRxIfCountsTableSnmpKey }
    ::= { cwsPmExtendedHistoryRxIfCountsTable 1 }

CwsPmExtendedHistoryRxIfCountsEntry ::= SEQUENCE { 
    cwsPmExtendedHistoryRxIfCountsTableSnmpKey Integer32,
    cwsPmExtendedHistoryRxIfCountsBytes Counter64,
    cwsPmExtendedHistoryRxIfCountsPackets Counter64,
    cwsPmExtendedHistoryRxIfCountsAverageLinkUtilization Decimal1Dig,
    cwsPmExtendedHistoryRxIfCountsCrcErroredPackets Counter64,
    cwsPmExtendedHistoryRxIfCountsMulticastPackets Counter64,
    cwsPmExtendedHistoryRxIfCountsBroadcastPackets Counter64,
    cwsPmExtendedHistoryRxIfCountsPausePackets Counter64,
    cwsPmExtendedHistoryRxIfCountsUndersizedPackets Counter64,
    cwsPmExtendedHistoryRxIfCountsOversizedPackets Counter64,
    cwsPmExtendedHistoryRxIfCountsFragmentPackets Counter64,
    cwsPmExtendedHistoryRxIfCountsJabberPackets Counter64,
    cwsPmExtendedHistoryRxIfCountsLengthOutRangePackets Counter64,
    cwsPmExtendedHistoryRxIfCountsPackets64Octet Counter64,
    cwsPmExtendedHistoryRxIfCountsPackets65127Octet Counter64,
    cwsPmExtendedHistoryRxIfCountsPackets128255Octet Counter64,
    cwsPmExtendedHistoryRxIfCountsPackets256511Octet Counter64,
    cwsPmExtendedHistoryRxIfCountsPackets5121023Octet Counter64,
    cwsPmExtendedHistoryRxIfCountsPackets10241518Octet Counter64 
}

cwsPmExtendedHistoryRxIfCountsTableSnmpKey OBJECT-TYPE
    SYNTAX Integer32(0..2147483647)
    MAX-ACCESS not-accessible
    STATUS current
    DESCRIPTION "Unique key for cwsPmExtendedHistoryRxIfCounts"
    ::= { cwsPmExtendedHistoryRxIfCountsEntry 1 }

cwsPmExtendedHistoryRxIfCountsBytes OBJECT-TYPE
    SYNTAX Counter64
    MAX-ACCESS read-write
    STATUS current
    DESCRIPTION "Number of bytes received including good and bad packets. This includes FCS bytes, but excludes framing bits."
    ::= { cwsPmExtendedHistoryRxIfCountsEntry 2 }

cwsPmExtendedHistoryRxIfCountsPackets OBJECT-TYPE
    SYNTAX Counter64
    MAX-ACCESS read-write
    STATUS current
    DESCRIPTION "Number of packets received, including all unicast, multicast, broadcast, MAC control, and bad packets"
    ::= { cwsPmExtendedHistoryRxIfCountsEntry 3 }

cwsPmExtendedHistoryRxIfCountsAverageLinkUtilization OBJECT-TYPE
    SYNTAX Decimal1Dig
    MAX-ACCESS read-write
    STATUS current
    DESCRIPTION "Average percent utilization derived from Rx bytes and port speed."
    ::= { cwsPmExtendedHistoryRxIfCountsEntry 19 }

cwsPmExtendedHistoryRxIfCountsCrcErroredPackets OBJECT-TYPE
    SYNTAX Counter64
    MAX-ACCESS read-write
    STATUS current
    DESCRIPTION "Number of packets received which contained an FCS error and were between 64 and 1518 bytes in length."
    ::= { cwsPmExtendedHistoryRxIfCountsEntry 4 }

cwsPmExtendedHistoryRxIfCountsMulticastPackets OBJECT-TYPE
    SYNTAX Counter64
    MAX-ACCESS read-write
    STATUS current
    DESCRIPTION "Number of good multicast packets received that were between 64 and 1518 bytes in length. Excludes MAC control frames"
    ::= { cwsPmExtendedHistoryRxIfCountsEntry 5 }

cwsPmExtendedHistoryRxIfCountsBroadcastPackets OBJECT-TYPE
    SYNTAX Counter64
    MAX-ACCESS read-write
    STATUS current
    DESCRIPTION "Number of good broadcast packets received that were between 64 and 1518 bytes in length. Excludes MAC control frames"
    ::= { cwsPmExtendedHistoryRxIfCountsEntry 6 }

cwsPmExtendedHistoryRxIfCountsPausePackets OBJECT-TYPE
    SYNTAX Counter64
    MAX-ACCESS read-write
    STATUS current
    DESCRIPTION "Number of received valid pause packets that were between 64 and 1518 bytes in length"
    ::= { cwsPmExtendedHistoryRxIfCountsEntry 7 }

cwsPmExtendedHistoryRxIfCountsUndersizedPackets OBJECT-TYPE
    SYNTAX Counter64
    MAX-ACCESS read-write
    STATUS current
    DESCRIPTION "Number of packets received that were less than 64 bytes (excluding framing bits but including FCS bytes) and were otherwise well formed. This counter also includes the number of packets discarded because of Ethernet length check errors. Undersize packets are discarded."
    ::= { cwsPmExtendedHistoryRxIfCountsEntry 8 }

cwsPmExtendedHistoryRxIfCountsOversizedPackets OBJECT-TYPE
    SYNTAX Counter64
    MAX-ACCESS read-write
    STATUS current
    DESCRIPTION "Number of packets received (including unicast, multicast, and broadcast packets) that were longer than 1518 bytes up to the configured maximum frame size, that contained a valid FCS (excluding framing bits but including FCS bytes), and that were otherwise well formed"
    ::= { cwsPmExtendedHistoryRxIfCountsEntry 9 }

cwsPmExtendedHistoryRxIfCountsFragmentPackets OBJECT-TYPE
    SYNTAX Counter64
    MAX-ACCESS read-write
    STATUS current
    DESCRIPTION "Number of packets received between 10 and 63 bytes in length (excluding framing bits but including FCS bytes) that had either a bad FCS with an integral number of bytes (FCS Error) or a bad FCS with a non-integral number of bytes (Alignment Error). Fragment packets are discarded."
    ::= { cwsPmExtendedHistoryRxIfCountsEntry 10 }

cwsPmExtendedHistoryRxIfCountsJabberPackets OBJECT-TYPE
    SYNTAX Counter64
    MAX-ACCESS read-write
    STATUS current
    DESCRIPTION "Number of packets received that were longer than 1518 bytes up to the configured maximum frame size (excluding framing bits, but including FCS bytes), and had either a bad FCS with an integral number of bytes (FCS Error) or a bad FCS with a non-integral number of bytes (Alignment Error). Jabber packets are discarded"
    ::= { cwsPmExtendedHistoryRxIfCountsEntry 11 }

cwsPmExtendedHistoryRxIfCountsLengthOutRangePackets OBJECT-TYPE
    SYNTAX Counter64
    MAX-ACCESS read-write
    STATUS current
    DESCRIPTION "Number of packets received that exceeded the maximum frame size and contained a valid or invalid FCS"
    ::= { cwsPmExtendedHistoryRxIfCountsEntry 12 }

cwsPmExtendedHistoryRxIfCountsPackets64Octet OBJECT-TYPE
    SYNTAX Counter64
    MAX-ACCESS read-write
    STATUS current
    DESCRIPTION "Number of packets (including bad packets) received that were 64 bytes in length (excluding framing bits but including FCS bytes)."
    ::= { cwsPmExtendedHistoryRxIfCountsEntry 13 }

cwsPmExtendedHistoryRxIfCountsPackets65127Octet OBJECT-TYPE
    SYNTAX Counter64
    MAX-ACCESS read-write
    STATUS current
    DESCRIPTION "Number of good and bad packets received that were between 65 and 127 bytes in length (excluding framing bits but including FCS bytes)."
    ::= { cwsPmExtendedHistoryRxIfCountsEntry 14 }

cwsPmExtendedHistoryRxIfCountsPackets128255Octet OBJECT-TYPE
    SYNTAX Counter64
    MAX-ACCESS read-write
    STATUS current
    DESCRIPTION "Number of good and bad packets received that were between 128 and 255 bytes in length inclusive (excluding framing bits but including FCS bytes)."
    ::= { cwsPmExtendedHistoryRxIfCountsEntry 15 }

cwsPmExtendedHistoryRxIfCountsPackets256511Octet OBJECT-TYPE
    SYNTAX Counter64
    MAX-ACCESS read-write
    STATUS current
    DESCRIPTION "Number of good and bad packets received that were between 256 and 511 bytes in length inclusive (excluding framing bits but including FCS bytes)."
    ::= { cwsPmExtendedHistoryRxIfCountsEntry 16 }

cwsPmExtendedHistoryRxIfCountsPackets5121023Octet OBJECT-TYPE
    SYNTAX Counter64
    MAX-ACCESS read-write
    STATUS current
    DESCRIPTION "Number of good and bad packets received that were between 512 and 1023 bytes in length inclusive (excluding framing bits but including FCS bytes)."
    ::= { cwsPmExtendedHistoryRxIfCountsEntry 17 }

cwsPmExtendedHistoryRxIfCountsPackets10241518Octet OBJECT-TYPE
    SYNTAX Counter64
    MAX-ACCESS read-write
    STATUS current
    DESCRIPTION "Number of good and bad packets received that were between 1024 and 1518 bytes in length inclusive (excluding framing bits but including FCS bytes)."
    ::= { cwsPmExtendedHistoryRxIfCountsEntry 18 }

cwsPmExtendedHistoryTxIfCountsTable OBJECT-TYPE
    SYNTAX SEQUENCE OF CwsPmExtendedHistoryTxIfCountsEntry
    MAX-ACCESS not-accessible
    STATUS current
    DESCRIPTION "Tx counts."
    ::= { cienaWsPmMIB 39 }

cwsPmExtendedHistoryTxIfCountsEntry OBJECT-TYPE
    SYNTAX CwsPmExtendedHistoryTxIfCountsEntry
    MAX-ACCESS not-accessible
    STATUS current
    DESCRIPTION "Entry for cwsPmExtendedHistoryTxIfCountsTable."
    INDEX { cwsPmPortExtendedTxRxInstancesInstanceName, cwsPmBinsBinNumber, cwsPmExtendedHistoryTxIfCountsTableSnmpKey }
    ::= { cwsPmExtendedHistoryTxIfCountsTable 1 }

CwsPmExtendedHistoryTxIfCountsEntry ::= SEQUENCE { 
    cwsPmExtendedHistoryTxIfCountsTableSnmpKey Integer32,
    cwsPmExtendedHistoryTxIfCountsBytes Counter64,
    cwsPmExtendedHistoryTxIfCountsPackets Counter64,
    cwsPmExtendedHistoryTxIfCountsAverageLinkUtilization Decimal1Dig,
    cwsPmExtendedHistoryTxIfCountsCrcErroredPackets Counter64,
    cwsPmExtendedHistoryTxIfCountsMulticastPackets Counter64,
    cwsPmExtendedHistoryTxIfCountsBroadcastPackets Counter64,
    cwsPmExtendedHistoryTxIfCountsPausePackets Counter64,
    cwsPmExtendedHistoryTxIfCountsExcessiveDeferredPackets Counter64,
    cwsPmExtendedHistoryTxIfCountsGiantPackets Counter64,
    cwsPmExtendedHistoryTxIfCountsUnderrunPackets Counter64,
    cwsPmExtendedHistoryTxIfCountsLengthCheckErrorPackets Counter64,
    cwsPmExtendedHistoryTxIfCountsLengthOutRangePackets Counter64 
}

cwsPmExtendedHistoryTxIfCountsTableSnmpKey OBJECT-TYPE
    SYNTAX Integer32(0..2147483647)
    MAX-ACCESS not-accessible
    STATUS current
    DESCRIPTION "Unique key for cwsPmExtendedHistoryTxIfCounts"
    ::= { cwsPmExtendedHistoryTxIfCountsEntry 1 }

cwsPmExtendedHistoryTxIfCountsBytes OBJECT-TYPE
    SYNTAX Counter64
    MAX-ACCESS read-write
    STATUS current
    DESCRIPTION "Number of transmitted bytes in good and bad packets including FCS bytes and excluding frame bits."
    ::= { cwsPmExtendedHistoryTxIfCountsEntry 2 }

cwsPmExtendedHistoryTxIfCountsPackets OBJECT-TYPE
    SYNTAX Counter64
    MAX-ACCESS read-write
    STATUS current
    DESCRIPTION "Number of transmitted packets, including all unicast, multicast, broadcast, MAC control, and bad packets"
    ::= { cwsPmExtendedHistoryTxIfCountsEntry 3 }

cwsPmExtendedHistoryTxIfCountsAverageLinkUtilization OBJECT-TYPE
    SYNTAX Decimal1Dig
    MAX-ACCESS read-write
    STATUS current
    DESCRIPTION "Average percent utilization derived from Tx bytes and port speed."
    ::= { cwsPmExtendedHistoryTxIfCountsEntry 13 }

cwsPmExtendedHistoryTxIfCountsCrcErroredPackets OBJECT-TYPE
    SYNTAX Counter64
    MAX-ACCESS read-write
    STATUS current
    DESCRIPTION "Number of transmitted packets with an FCS error"
    ::= { cwsPmExtendedHistoryTxIfCountsEntry 4 }

cwsPmExtendedHistoryTxIfCountsMulticastPackets OBJECT-TYPE
    SYNTAX Counter64
    MAX-ACCESS read-write
    STATUS current
    DESCRIPTION "Number of good multicast packets transmitted"
    ::= { cwsPmExtendedHistoryTxIfCountsEntry 5 }

cwsPmExtendedHistoryTxIfCountsBroadcastPackets OBJECT-TYPE
    SYNTAX Counter64
    MAX-ACCESS read-write
    STATUS current
    DESCRIPTION "Number of good broadcast packets transmitted"
    ::= { cwsPmExtendedHistoryTxIfCountsEntry 6 }

cwsPmExtendedHistoryTxIfCountsPausePackets OBJECT-TYPE
    SYNTAX Counter64
    MAX-ACCESS read-write
    STATUS current
    DESCRIPTION "Number of pause packets transmitted"
    ::= { cwsPmExtendedHistoryTxIfCountsEntry 7 }

cwsPmExtendedHistoryTxIfCountsExcessiveDeferredPackets OBJECT-TYPE
    SYNTAX Counter64
    MAX-ACCESS read-write
    STATUS current
    DESCRIPTION "Number of transmitted packets experiencing two or more deferrals. Applicable to copper ports only"
    ::= { cwsPmExtendedHistoryTxIfCountsEntry 8 }

cwsPmExtendedHistoryTxIfCountsGiantPackets OBJECT-TYPE
    SYNTAX Counter64
    MAX-ACCESS read-write
    STATUS current
    DESCRIPTION "Number of well-formed packets larger than 1518 bytes, including FCS bytes but excluding framing bits."
    ::= { cwsPmExtendedHistoryTxIfCountsEntry 9 }

cwsPmExtendedHistoryTxIfCountsUnderrunPackets OBJECT-TYPE
    SYNTAX Counter64
    MAX-ACCESS read-write
    STATUS current
    DESCRIPTION "Number of underrun packets transmitted"
    ::= { cwsPmExtendedHistoryTxIfCountsEntry 10 }

cwsPmExtendedHistoryTxIfCountsLengthCheckErrorPackets OBJECT-TYPE
    SYNTAX Counter64
    MAX-ACCESS read-write
    STATUS current
    DESCRIPTION "Number of length check packets transmitted"
    ::= { cwsPmExtendedHistoryTxIfCountsEntry 11 }

cwsPmExtendedHistoryTxIfCountsLengthOutRangePackets OBJECT-TYPE
    SYNTAX Counter64
    MAX-ACCESS read-write
    STATUS current
    DESCRIPTION "Number of length out-of-range packets transmitted"
    ::= { cwsPmExtendedHistoryTxIfCountsEntry 12 }

cwsPmCurrentBinTxQueueTable OBJECT-TYPE
    SYNTAX SEQUENCE OF CwsPmCurrentBinTxQueueEntry
    MAX-ACCESS not-accessible
    STATUS current
    DESCRIPTION "Tx queue."
    ::= { cienaWsPmMIB 40 }

cwsPmCurrentBinTxQueueEntry OBJECT-TYPE
    SYNTAX CwsPmCurrentBinTxQueueEntry
    MAX-ACCESS not-accessible
    STATUS current
    DESCRIPTION "Entry for cwsPmCurrentBinTxQueueTable."
    INDEX { cwsPmPortExtendedTxRxInstancesInstanceName, cwsPmBinsBinNumber, cwsPmCurrentBinTxQueueTableSnmpKey }
    ::= { cwsPmCurrentBinTxQueueTable 1 }

CwsPmCurrentBinTxQueueEntry ::= SEQUENCE { 
    cwsPmCurrentBinTxQueueTableSnmpKey Integer32,
    cwsPmCurrentBinTxQueuePacketDropCountSummary Counter64,
    cwsPmCurrentBinTxQueueQ0PacketDropCount Counter64,
    cwsPmCurrentBinTxQueueQ1PacketDropCount Counter64,
    cwsPmCurrentBinTxQueueQ2PacketDropCount Counter64,
    cwsPmCurrentBinTxQueueQ3PacketDropCount Counter64,
    cwsPmCurrentBinTxQueueQ4PacketDropCount Counter64,
    cwsPmCurrentBinTxQueueQ5PacketDropCount Counter64,
    cwsPmCurrentBinTxQueueQ6PacketDropCount Counter64,
    cwsPmCurrentBinTxQueueQ7PacketDropCount Counter64 
}

cwsPmCurrentBinTxQueueTableSnmpKey OBJECT-TYPE
    SYNTAX Integer32(0..2147483647)
    MAX-ACCESS not-accessible
    STATUS current
    DESCRIPTION "Unique key for cwsPmCurrentBinTxQueue"
    ::= { cwsPmCurrentBinTxQueueEntry 1 }

cwsPmCurrentBinTxQueuePacketDropCountSummary OBJECT-TYPE
    SYNTAX Counter64
    MAX-ACCESS read-write
    STATUS current
    DESCRIPTION "Summary of the number of bytes dropped from queues 0 to 3 (Q0, Q1, Q2, and Q3)"
    ::= { cwsPmCurrentBinTxQueueEntry 2 }

cwsPmCurrentBinTxQueueQ0PacketDropCount OBJECT-TYPE
    SYNTAX Counter64
    MAX-ACCESS read-write
    STATUS current
    DESCRIPTION "The number of bytes dropped from queue 0 (Q0)"
    ::= { cwsPmCurrentBinTxQueueEntry 3 }

cwsPmCurrentBinTxQueueQ1PacketDropCount OBJECT-TYPE
    SYNTAX Counter64
    MAX-ACCESS read-write
    STATUS current
    DESCRIPTION "The number of bytes dropped from queue 1 (Q1)"
    ::= { cwsPmCurrentBinTxQueueEntry 4 }

cwsPmCurrentBinTxQueueQ2PacketDropCount OBJECT-TYPE
    SYNTAX Counter64
    MAX-ACCESS read-write
    STATUS current
    DESCRIPTION "The number of bytes dropped from queue 2 (Q2)"
    ::= { cwsPmCurrentBinTxQueueEntry 5 }

cwsPmCurrentBinTxQueueQ3PacketDropCount OBJECT-TYPE
    SYNTAX Counter64
    MAX-ACCESS read-write
    STATUS current
    DESCRIPTION "The number of bytes dropped from queue 3 (Q3)"
    ::= { cwsPmCurrentBinTxQueueEntry 6 }

cwsPmCurrentBinTxQueueQ4PacketDropCount OBJECT-TYPE
    SYNTAX Counter64
    MAX-ACCESS read-write
    STATUS current
    DESCRIPTION "The number of bytes dropped from queue 4 (Q4)"
    ::= { cwsPmCurrentBinTxQueueEntry 7 }

cwsPmCurrentBinTxQueueQ5PacketDropCount OBJECT-TYPE
    SYNTAX Counter64
    MAX-ACCESS read-write
    STATUS current
    DESCRIPTION "The number of bytes dropped from queue 5 (Q5)"
    ::= { cwsPmCurrentBinTxQueueEntry 8 }

cwsPmCurrentBinTxQueueQ6PacketDropCount OBJECT-TYPE
    SYNTAX Counter64
    MAX-ACCESS read-write
    STATUS current
    DESCRIPTION "The number of bytes dropped from queue 6 (Q6)"
    ::= { cwsPmCurrentBinTxQueueEntry 9 }

cwsPmCurrentBinTxQueueQ7PacketDropCount OBJECT-TYPE
    SYNTAX Counter64
    MAX-ACCESS read-write
    STATUS current
    DESCRIPTION "The number of bytes dropped from queue 7 (Q7)"
    ::= { cwsPmCurrentBinTxQueueEntry 10 }

cwsPmExtendedHistoryMacLayerTable OBJECT-TYPE
    SYNTAX SEQUENCE OF CwsPmExtendedHistoryMacLayerEntry
    MAX-ACCESS not-accessible
    STATUS obsolete
    DESCRIPTION "None"
    ::= { cienaWsPmMIB 41 }

cwsPmExtendedHistoryMacLayerEntry OBJECT-TYPE
    SYNTAX CwsPmExtendedHistoryMacLayerEntry
    MAX-ACCESS not-accessible
    STATUS obsolete
    DESCRIPTION "Entry for cwsPmExtendedHistoryMacLayerTable."
    INDEX { cwsPmPortExtendedTxRxInstancesInstanceName, cwsPmBinsBinNumber, cwsPmExtendedHistoryMacLayerTableSnmpKey }
    ::= { cwsPmExtendedHistoryMacLayerTable 1 }

CwsPmExtendedHistoryMacLayerEntry ::= SEQUENCE { 
    cwsPmExtendedHistoryMacLayerTableSnmpKey Integer32,
    cwsPmExtendedHistoryMacLayerUnavailableSeconds Counter64 
}

cwsPmExtendedHistoryMacLayerTableSnmpKey OBJECT-TYPE
    SYNTAX Integer32(0..2147483647)
    MAX-ACCESS not-accessible
    STATUS current
    DESCRIPTION "Unique key for cwsPmExtendedHistoryMacLayer"
    ::= { cwsPmExtendedHistoryMacLayerEntry 1 }

cwsPmExtendedHistoryMacLayerUnavailableSeconds OBJECT-TYPE
    SYNTAX Counter64
    MAX-ACCESS read-only
    STATUS obsolete
    DESCRIPTION "The number of seconds that the interface was unavailable."
    ::= { cwsPmExtendedHistoryMacLayerEntry 2 }

cwsPmExtendedHistoryPcsLayerTable OBJECT-TYPE
    SYNTAX SEQUENCE OF CwsPmExtendedHistoryPcsLayerEntry
    MAX-ACCESS not-accessible
    STATUS current
    DESCRIPTION "None"
    ::= { cienaWsPmMIB 42 }

cwsPmExtendedHistoryPcsLayerEntry OBJECT-TYPE
    SYNTAX CwsPmExtendedHistoryPcsLayerEntry
    MAX-ACCESS not-accessible
    STATUS current
    DESCRIPTION "Entry for cwsPmExtendedHistoryPcsLayerTable."
    INDEX { cwsPmPortExtendedTxRxInstancesInstanceName, cwsPmBinsBinNumber, cwsPmExtendedHistoryPcsLayerTableSnmpKey }
    ::= { cwsPmExtendedHistoryPcsLayerTable 1 }

CwsPmExtendedHistoryPcsLayerEntry ::= SEQUENCE { 
    cwsPmExtendedHistoryPcsLayerTableSnmpKey Integer32,
    cwsPmExtendedHistoryPcsLayerErroredSeconds Counter64,
    cwsPmExtendedHistoryPcsLayerSeverelyErroredSeconds Counter64,
    cwsPmExtendedHistoryPcsLayerUnavailableSeconds Counter64 
}

cwsPmExtendedHistoryPcsLayerTableSnmpKey OBJECT-TYPE
    SYNTAX Integer32(0..2147483647)
    MAX-ACCESS not-accessible
    STATUS current
    DESCRIPTION "Unique key for cwsPmExtendedHistoryPcsLayer"
    ::= { cwsPmExtendedHistoryPcsLayerEntry 1 }

cwsPmExtendedHistoryPcsLayerErroredSeconds OBJECT-TYPE
    SYNTAX Counter64
    MAX-ACCESS read-write
    STATUS current
    DESCRIPTION "Number of seconds that error happened."
    ::= { cwsPmExtendedHistoryPcsLayerEntry 2 }

cwsPmExtendedHistoryPcsLayerSeverelyErroredSeconds OBJECT-TYPE
    SYNTAX Counter64
    MAX-ACCESS read-write
    STATUS current
    DESCRIPTION "Number of seconds that severe error happened."
    ::= { cwsPmExtendedHistoryPcsLayerEntry 3 }

cwsPmExtendedHistoryPcsLayerUnavailableSeconds OBJECT-TYPE
    SYNTAX Counter64
    MAX-ACCESS read-write
    STATUS current
    DESCRIPTION "Number of seconds that the interface was unavailable."
    ::= { cwsPmExtendedHistoryPcsLayerEntry 4 }

cwsPmExtendedHistoryPcsSyncHeaderErrorsTable OBJECT-TYPE
    SYNTAX SEQUENCE OF CwsPmExtendedHistoryPcsSyncHeaderErrorsEntry
    MAX-ACCESS not-accessible
    STATUS current
    DESCRIPTION "None"
    ::= { cienaWsPmMIB 43 }

cwsPmExtendedHistoryPcsSyncHeaderErrorsEntry OBJECT-TYPE
    SYNTAX CwsPmExtendedHistoryPcsSyncHeaderErrorsEntry
    MAX-ACCESS not-accessible
    STATUS current
    DESCRIPTION "Entry for cwsPmExtendedHistoryPcsSyncHeaderErrorsTable."
    INDEX { cwsPmPortExtendedTxRxInstancesInstanceName, cwsPmBinsBinNumber, cwsPmExtendedHistoryPcsSyncHeaderErrorsTableSnmpKey }
    ::= { cwsPmExtendedHistoryPcsSyncHeaderErrorsTable 1 }

CwsPmExtendedHistoryPcsSyncHeaderErrorsEntry ::= SEQUENCE { 
    cwsPmExtendedHistoryPcsSyncHeaderErrorsTableSnmpKey Integer32,
    cwsPmExtendedHistoryPcsSyncHeaderErrorsCount Counter64 
}

cwsPmExtendedHistoryPcsSyncHeaderErrorsTableSnmpKey OBJECT-TYPE
    SYNTAX Integer32(0..2147483647)
    MAX-ACCESS not-accessible
    STATUS current
    DESCRIPTION "Unique key for cwsPmExtendedHistoryPcsSyncHeaderErrors"
    ::= { cwsPmExtendedHistoryPcsSyncHeaderErrorsEntry 1 }

cwsPmExtendedHistoryPcsSyncHeaderErrorsCount OBJECT-TYPE
    SYNTAX Counter64
    MAX-ACCESS read-only
    STATUS current
    DESCRIPTION "Sync header errors count value."
    ::= { cwsPmExtendedHistoryPcsSyncHeaderErrorsEntry 2 }

cwsPmExtendedHistoryPcsBlockErrorsTable OBJECT-TYPE
    SYNTAX SEQUENCE OF CwsPmExtendedHistoryPcsBlockErrorsEntry
    MAX-ACCESS not-accessible
    STATUS current
    DESCRIPTION "None"
    ::= { cienaWsPmMIB 44 }

cwsPmExtendedHistoryPcsBlockErrorsEntry OBJECT-TYPE
    SYNTAX CwsPmExtendedHistoryPcsBlockErrorsEntry
    MAX-ACCESS not-accessible
    STATUS current
    DESCRIPTION "Entry for cwsPmExtendedHistoryPcsBlockErrorsTable."
    INDEX { cwsPmPortExtendedTxRxInstancesInstanceName, cwsPmBinsBinNumber, cwsPmExtendedHistoryPcsBlockErrorsTableSnmpKey }
    ::= { cwsPmExtendedHistoryPcsBlockErrorsTable 1 }

CwsPmExtendedHistoryPcsBlockErrorsEntry ::= SEQUENCE { 
    cwsPmExtendedHistoryPcsBlockErrorsTableSnmpKey Integer32,
    cwsPmExtendedHistoryPcsBlockErrorsCount Counter64 
}

cwsPmExtendedHistoryPcsBlockErrorsTableSnmpKey OBJECT-TYPE
    SYNTAX Integer32(0..2147483647)
    MAX-ACCESS not-accessible
    STATUS current
    DESCRIPTION "Unique key for cwsPmExtendedHistoryPcsBlockErrors"
    ::= { cwsPmExtendedHistoryPcsBlockErrorsEntry 1 }

cwsPmExtendedHistoryPcsBlockErrorsCount OBJECT-TYPE
    SYNTAX Counter64
    MAX-ACCESS read-only
    STATUS current
    DESCRIPTION "Block errors count value."
    ::= { cwsPmExtendedHistoryPcsBlockErrorsEntry 2 }

cwsPmExtendedHistoryPcsMultilaneBipErrorsTable OBJECT-TYPE
    SYNTAX SEQUENCE OF CwsPmExtendedHistoryPcsMultilaneBipErrorsEntry
    MAX-ACCESS not-accessible
    STATUS current
    DESCRIPTION "None"
    ::= { cienaWsPmMIB 45 }

cwsPmExtendedHistoryPcsMultilaneBipErrorsEntry OBJECT-TYPE
    SYNTAX CwsPmExtendedHistoryPcsMultilaneBipErrorsEntry
    MAX-ACCESS not-accessible
    STATUS current
    DESCRIPTION "Entry for cwsPmExtendedHistoryPcsMultilaneBipErrorsTable."
    INDEX { cwsPmPortExtendedTxRxInstancesInstanceName, cwsPmBinsBinNumber, cwsPmExtendedHistoryPcsMultilaneBipErrorsTableSnmpKey }
    ::= { cwsPmExtendedHistoryPcsMultilaneBipErrorsTable 1 }

CwsPmExtendedHistoryPcsMultilaneBipErrorsEntry ::= SEQUENCE { 
    cwsPmExtendedHistoryPcsMultilaneBipErrorsTableSnmpKey Integer32,
    cwsPmExtendedHistoryPcsMultilaneBipErrorsCount Counter64 
}

cwsPmExtendedHistoryPcsMultilaneBipErrorsTableSnmpKey OBJECT-TYPE
    SYNTAX Integer32(0..2147483647)
    MAX-ACCESS not-accessible
    STATUS current
    DESCRIPTION "Unique key for cwsPmExtendedHistoryPcsMultilaneBipErrors"
    ::= { cwsPmExtendedHistoryPcsMultilaneBipErrorsEntry 1 }

cwsPmExtendedHistoryPcsMultilaneBipErrorsCount OBJECT-TYPE
    SYNTAX Counter64
    MAX-ACCESS read-only
    STATUS current
    DESCRIPTION "Multilane bip errors count value."
    ::= { cwsPmExtendedHistoryPcsMultilaneBipErrorsEntry 2 }

cwsPmExtendedHistoryOduLayerTable OBJECT-TYPE
    SYNTAX SEQUENCE OF CwsPmExtendedHistoryOduLayerEntry
    MAX-ACCESS not-accessible
    STATUS current
    DESCRIPTION "None"
    ::= { cienaWsPmMIB 123 }

cwsPmExtendedHistoryOduLayerEntry OBJECT-TYPE
    SYNTAX CwsPmExtendedHistoryOduLayerEntry
    MAX-ACCESS not-accessible
    STATUS current
    DESCRIPTION "Entry for cwsPmExtendedHistoryOduLayerTable."
    INDEX { cwsPmPortExtendedTxRxInstancesInstanceName, cwsPmBinsBinNumber, cwsPmExtendedHistoryOduLayerTableSnmpKey }
    ::= { cwsPmExtendedHistoryOduLayerTable 1 }

CwsPmExtendedHistoryOduLayerEntry ::= SEQUENCE { 
    cwsPmExtendedHistoryOduLayerTableSnmpKey Integer32,
    cwsPmExtendedHistoryOduLayerErroredSeconds Counter64,
    cwsPmExtendedHistoryOduLayerSeverelyErroredSeconds Counter64,
    cwsPmExtendedHistoryOduLayerUnavailableSeconds Counter64 
}

cwsPmExtendedHistoryOduLayerTableSnmpKey OBJECT-TYPE
    SYNTAX Integer32(0..2147483647)
    MAX-ACCESS not-accessible
    STATUS current
    DESCRIPTION "Unique key for cwsPmExtendedHistoryOduLayer"
    ::= { cwsPmExtendedHistoryOduLayerEntry 1 }

cwsPmExtendedHistoryOduLayerErroredSeconds OBJECT-TYPE
    SYNTAX Counter64
    MAX-ACCESS read-write
    STATUS current
    DESCRIPTION "Number of seconds that error happened."
    ::= { cwsPmExtendedHistoryOduLayerEntry 2 }

cwsPmExtendedHistoryOduLayerSeverelyErroredSeconds OBJECT-TYPE
    SYNTAX Counter64
    MAX-ACCESS read-write
    STATUS current
    DESCRIPTION "Number of seconds that severe error happened."
    ::= { cwsPmExtendedHistoryOduLayerEntry 3 }

cwsPmExtendedHistoryOduLayerUnavailableSeconds OBJECT-TYPE
    SYNTAX Counter64
    MAX-ACCESS read-write
    STATUS current
    DESCRIPTION "Number of seconds that the interface was unavailable."
    ::= { cwsPmExtendedHistoryOduLayerEntry 4 }

cwsPmExtendedHistoryFecLayerTable OBJECT-TYPE
    SYNTAX SEQUENCE OF CwsPmExtendedHistoryFecLayerEntry
    MAX-ACCESS not-accessible
    STATUS current
    DESCRIPTION "None"
    ::= { cienaWsPmMIB 46 }

cwsPmExtendedHistoryFecLayerEntry OBJECT-TYPE
    SYNTAX CwsPmExtendedHistoryFecLayerEntry
    MAX-ACCESS not-accessible
    STATUS current
    DESCRIPTION "Entry for cwsPmExtendedHistoryFecLayerTable."
    INDEX { cwsPmPortExtendedTxRxInstancesInstanceName, cwsPmBinsBinNumber, cwsPmExtendedHistoryFecLayerTableSnmpKey }
    ::= { cwsPmExtendedHistoryFecLayerTable 1 }

CwsPmExtendedHistoryFecLayerEntry ::= SEQUENCE { 
    cwsPmExtendedHistoryFecLayerTableSnmpKey Integer32,
    cwsPmExtendedHistoryFecLayerCorrectedBlockCount Counter64,
    cwsPmExtendedHistoryFecLayerUncorrectedBlockCount Counter64,
    cwsPmExtendedHistoryFecLayerSymbolErrorCount Counter64 
}

cwsPmExtendedHistoryFecLayerTableSnmpKey OBJECT-TYPE
    SYNTAX Integer32(0..2147483647)
    MAX-ACCESS not-accessible
    STATUS current
    DESCRIPTION "Unique key for cwsPmExtendedHistoryFecLayer"
    ::= { cwsPmExtendedHistoryFecLayerEntry 1 }

cwsPmExtendedHistoryFecLayerCorrectedBlockCount OBJECT-TYPE
    SYNTAX Counter64
    MAX-ACCESS read-write
    STATUS current
    DESCRIPTION "Fec layer corrected block count"
    ::= { cwsPmExtendedHistoryFecLayerEntry 2 }

cwsPmExtendedHistoryFecLayerUncorrectedBlockCount OBJECT-TYPE
    SYNTAX Counter64
    MAX-ACCESS read-write
    STATUS current
    DESCRIPTION "Fec layer uncorrected block count"
    ::= { cwsPmExtendedHistoryFecLayerEntry 3 }

cwsPmExtendedHistoryFecLayerSymbolErrorCount OBJECT-TYPE
    SYNTAX Counter64
    MAX-ACCESS read-write
    STATUS current
    DESCRIPTION "Fec layer symbol error count"
    ::= { cwsPmExtendedHistoryFecLayerEntry 4 }

cwsPmExtendedHistory24hIdTable OBJECT-TYPE
    SYNTAX SEQUENCE OF CwsPmExtendedHistory24hIdEntry
    MAX-ACCESS not-accessible
    STATUS current
    DESCRIPTION "PM Bin identification."
    ::= { cienaWsPmMIB 47 }

cwsPmExtendedHistory24hIdEntry OBJECT-TYPE
    SYNTAX CwsPmExtendedHistory24hIdEntry
    MAX-ACCESS not-accessible
    STATUS current
    DESCRIPTION "Entry for cwsPmExtendedHistory24hIdTable."
    INDEX { cwsPmPortExtendedTxRxInstancesInstanceName, cwsPmExtendedHistory24hIdTableSnmpKey }
    ::= { cwsPmExtendedHistory24hIdTable 1 }

CwsPmExtendedHistory24hIdEntry ::= SEQUENCE { 
    cwsPmExtendedHistory24hIdTableSnmpKey Integer32,
    cwsPmExtendedHistory24hIdBinNumber Unsigned32,
    cwsPmExtendedHistory24hIdBinName StringMaxl32 
}

cwsPmExtendedHistory24hIdTableSnmpKey OBJECT-TYPE
    SYNTAX Integer32(0..2147483647)
    MAX-ACCESS not-accessible
    STATUS current
    DESCRIPTION "Unique key for cwsPmExtendedHistory24hId"
    ::= { cwsPmExtendedHistory24hIdEntry 1 }

cwsPmExtendedHistory24hIdBinNumber OBJECT-TYPE
    SYNTAX Unsigned32
    MAX-ACCESS read-write
    STATUS current
    DESCRIPTION "The PM bin number."
    ::= { cwsPmExtendedHistory24hIdEntry 2 }

cwsPmExtendedHistory24hIdBinName OBJECT-TYPE
    SYNTAX StringMaxl32
    MAX-ACCESS read-write
    STATUS current
    DESCRIPTION "The PM bin name."
    ::= { cwsPmExtendedHistory24hIdEntry 3 }

cwsPmExtendedHistory24hStateTable OBJECT-TYPE
    SYNTAX SEQUENCE OF CwsPmExtendedHistory24hStateEntry
    MAX-ACCESS not-accessible
    STATUS current
    DESCRIPTION "PM bin state."
    ::= { cienaWsPmMIB 48 }

cwsPmExtendedHistory24hStateEntry OBJECT-TYPE
    SYNTAX CwsPmExtendedHistory24hStateEntry
    MAX-ACCESS not-accessible
    STATUS current
    DESCRIPTION "Entry for cwsPmExtendedHistory24hStateTable."
    INDEX { cwsPmPortExtendedTxRxInstancesInstanceName, cwsPmExtendedHistory24hStateTableSnmpKey }
    ::= { cwsPmExtendedHistory24hStateTable 1 }

CwsPmExtendedHistory24hStateEntry ::= SEQUENCE { 
    cwsPmExtendedHistory24hStateTableSnmpKey Integer32,
    cwsPmExtendedHistory24hStateStartDateTime StringMaxl32,
    cwsPmExtendedHistory24hStateEndDateTime StringMaxl32,
    cwsPmExtendedHistory24hStateState PmBinState 
}

cwsPmExtendedHistory24hStateTableSnmpKey OBJECT-TYPE
    SYNTAX Integer32(0..2147483647)
    MAX-ACCESS not-accessible
    STATUS current
    DESCRIPTION "Unique key for cwsPmExtendedHistory24hState"
    ::= { cwsPmExtendedHistory24hStateEntry 1 }

cwsPmExtendedHistory24hStateStartDateTime OBJECT-TYPE
    SYNTAX StringMaxl32
    MAX-ACCESS read-write
    STATUS current
    DESCRIPTION "Start date and time."
    ::= { cwsPmExtendedHistory24hStateEntry 2 }

cwsPmExtendedHistory24hStateEndDateTime OBJECT-TYPE
    SYNTAX StringMaxl32
    MAX-ACCESS read-write
    STATUS current
    DESCRIPTION "End date and time."
    ::= { cwsPmExtendedHistory24hStateEntry 3 }

cwsPmExtendedHistory24hStateState OBJECT-TYPE
    SYNTAX PmBinState
    MAX-ACCESS read-write
    STATUS current
    DESCRIPTION "The PM bin state."
    ::= { cwsPmExtendedHistory24hStateEntry 4 }

cwsPmExtendedHistory24hStatisticsTable OBJECT-TYPE
    SYNTAX SEQUENCE OF CwsPmExtendedHistory24hStatisticsEntry
    MAX-ACCESS not-accessible
    STATUS current
    DESCRIPTION "Statistics data."
    ::= { cienaWsPmMIB 49 }

cwsPmExtendedHistory24hStatisticsEntry OBJECT-TYPE
    SYNTAX CwsPmExtendedHistory24hStatisticsEntry
    MAX-ACCESS not-accessible
    STATUS current
    DESCRIPTION "Entry for cwsPmExtendedHistory24hStatisticsTable."
    INDEX { cwsPmPortExtendedTxRxInstancesInstanceName, cwsPmExtendedHistory24hStatisticsTableSnmpKey }
    ::= { cwsPmExtendedHistory24hStatisticsTable 1 }

CwsPmExtendedHistory24hStatisticsEntry ::= SEQUENCE { 
    cwsPmExtendedHistory24hStatisticsTableSnmpKey Integer32,
    cwsPmExtendedHistory24hStatisticsFrameErrorRatio Counter64 
}

cwsPmExtendedHistory24hStatisticsTableSnmpKey OBJECT-TYPE
    SYNTAX Integer32(0..2147483647)
    MAX-ACCESS not-accessible
    STATUS current
    DESCRIPTION "Unique key for cwsPmExtendedHistory24hStatistics"
    ::= { cwsPmExtendedHistory24hStatisticsEntry 1 }

cwsPmExtendedHistory24hStatisticsFrameErrorRatio OBJECT-TYPE
    SYNTAX Counter64
    MAX-ACCESS read-only
    STATUS current
    DESCRIPTION "RMON frame error ratio."
    ::= { cwsPmExtendedHistory24hStatisticsEntry 2 }

cwsPmExtendedHistory24hRxIfCountsTable OBJECT-TYPE
    SYNTAX SEQUENCE OF CwsPmExtendedHistory24hRxIfCountsEntry
    MAX-ACCESS not-accessible
    STATUS current
    DESCRIPTION "Rx counts."
    ::= { cienaWsPmMIB 50 }

cwsPmExtendedHistory24hRxIfCountsEntry OBJECT-TYPE
    SYNTAX CwsPmExtendedHistory24hRxIfCountsEntry
    MAX-ACCESS not-accessible
    STATUS current
    DESCRIPTION "Entry for cwsPmExtendedHistory24hRxIfCountsTable."
    INDEX { cwsPmPortExtendedTxRxInstancesInstanceName, cwsPmExtendedHistory24hRxIfCountsTableSnmpKey }
    ::= { cwsPmExtendedHistory24hRxIfCountsTable 1 }

CwsPmExtendedHistory24hRxIfCountsEntry ::= SEQUENCE { 
    cwsPmExtendedHistory24hRxIfCountsTableSnmpKey Integer32,
    cwsPmExtendedHistory24hRxIfCountsBytes Counter64,
    cwsPmExtendedHistory24hRxIfCountsPackets Counter64,
    cwsPmExtendedHistory24hRxIfCountsAverageLinkUtilization Decimal1Dig,
    cwsPmExtendedHistory24hRxIfCountsCrcErroredPackets Counter64,
    cwsPmExtendedHistory24hRxIfCountsMulticastPackets Counter64,
    cwsPmExtendedHistory24hRxIfCountsBroadcastPackets Counter64,
    cwsPmExtendedHistory24hRxIfCountsPausePackets Counter64,
    cwsPmExtendedHistory24hRxIfCountsUndersizedPackets Counter64,
    cwsPmExtendedHistory24hRxIfCountsOversizedPackets Counter64,
    cwsPmExtendedHistory24hRxIfCountsFragmentPackets Counter64,
    cwsPmExtendedHistory24hRxIfCountsJabberPackets Counter64,
    cwsPmExtendedHistory24hRxIfCountsLengthOutRangePackets Counter64,
    cwsPmExtendedHistory24hRxIfCountsPackets64Octet Counter64,
    cwsPmExtendedHistory24hRxIfCountsPackets65127Octet Counter64,
    cwsPmExtendedHistory24hRxIfCountsPackets128255Octet Counter64,
    cwsPmExtendedHistory24hRxIfCountsPackets256511Octet Counter64,
    cwsPmExtendedHistory24hRxIfCountsPackets5121023Octet Counter64,
    cwsPmExtendedHistory24hRxIfCountsPackets10241518Octet Counter64 
}

cwsPmExtendedHistory24hRxIfCountsTableSnmpKey OBJECT-TYPE
    SYNTAX Integer32(0..2147483647)
    MAX-ACCESS not-accessible
    STATUS current
    DESCRIPTION "Unique key for cwsPmExtendedHistory24hRxIfCounts"
    ::= { cwsPmExtendedHistory24hRxIfCountsEntry 1 }

cwsPmExtendedHistory24hRxIfCountsBytes OBJECT-TYPE
    SYNTAX Counter64
    MAX-ACCESS read-write
    STATUS current
    DESCRIPTION "Number of bytes received including good and bad packets. This includes FCS bytes, but excludes framing bits."
    ::= { cwsPmExtendedHistory24hRxIfCountsEntry 2 }

cwsPmExtendedHistory24hRxIfCountsPackets OBJECT-TYPE
    SYNTAX Counter64
    MAX-ACCESS read-write
    STATUS current
    DESCRIPTION "Number of packets received, including all unicast, multicast, broadcast, MAC control, and bad packets"
    ::= { cwsPmExtendedHistory24hRxIfCountsEntry 3 }

cwsPmExtendedHistory24hRxIfCountsAverageLinkUtilization OBJECT-TYPE
    SYNTAX Decimal1Dig
    MAX-ACCESS read-write
    STATUS current
    DESCRIPTION "Average percent utilization derived from Rx bytes and port speed."
    ::= { cwsPmExtendedHistory24hRxIfCountsEntry 19 }

cwsPmExtendedHistory24hRxIfCountsCrcErroredPackets OBJECT-TYPE
    SYNTAX Counter64
    MAX-ACCESS read-write
    STATUS current
    DESCRIPTION "Number of packets received which contained an FCS error and were between 64 and 1518 bytes in length."
    ::= { cwsPmExtendedHistory24hRxIfCountsEntry 4 }

cwsPmExtendedHistory24hRxIfCountsMulticastPackets OBJECT-TYPE
    SYNTAX Counter64
    MAX-ACCESS read-write
    STATUS current
    DESCRIPTION "Number of good multicast packets received that were between 64 and 1518 bytes in length. Excludes MAC control frames"
    ::= { cwsPmExtendedHistory24hRxIfCountsEntry 5 }

cwsPmExtendedHistory24hRxIfCountsBroadcastPackets OBJECT-TYPE
    SYNTAX Counter64
    MAX-ACCESS read-write
    STATUS current
    DESCRIPTION "Number of good broadcast packets received that were between 64 and 1518 bytes in length. Excludes MAC control frames"
    ::= { cwsPmExtendedHistory24hRxIfCountsEntry 6 }

cwsPmExtendedHistory24hRxIfCountsPausePackets OBJECT-TYPE
    SYNTAX Counter64
    MAX-ACCESS read-write
    STATUS current
    DESCRIPTION "Number of received valid pause packets that were between 64 and 1518 bytes in length"
    ::= { cwsPmExtendedHistory24hRxIfCountsEntry 7 }

cwsPmExtendedHistory24hRxIfCountsUndersizedPackets OBJECT-TYPE
    SYNTAX Counter64
    MAX-ACCESS read-write
    STATUS current
    DESCRIPTION "Number of packets received that were less than 64 bytes (excluding framing bits but including FCS bytes) and were otherwise well formed. This counter also includes the number of packets discarded because of Ethernet length check errors. Undersize packets are discarded."
    ::= { cwsPmExtendedHistory24hRxIfCountsEntry 8 }

cwsPmExtendedHistory24hRxIfCountsOversizedPackets OBJECT-TYPE
    SYNTAX Counter64
    MAX-ACCESS read-write
    STATUS current
    DESCRIPTION "Number of packets received (including unicast, multicast, and broadcast packets) that were longer than 1518 bytes up to the configured maximum frame size, that contained a valid FCS (excluding framing bits but including FCS bytes), and that were otherwise well formed"
    ::= { cwsPmExtendedHistory24hRxIfCountsEntry 9 }

cwsPmExtendedHistory24hRxIfCountsFragmentPackets OBJECT-TYPE
    SYNTAX Counter64
    MAX-ACCESS read-write
    STATUS current
    DESCRIPTION "Number of packets received between 10 and 63 bytes in length (excluding framing bits but including FCS bytes) that had either a bad FCS with an integral number of bytes (FCS Error) or a bad FCS with a non-integral number of bytes (Alignment Error). Fragment packets are discarded."
    ::= { cwsPmExtendedHistory24hRxIfCountsEntry 10 }

cwsPmExtendedHistory24hRxIfCountsJabberPackets OBJECT-TYPE
    SYNTAX Counter64
    MAX-ACCESS read-write
    STATUS current
    DESCRIPTION "Number of packets received that were longer than 1518 bytes up to the configured maximum frame size (excluding framing bits, but including FCS bytes), and had either a bad FCS with an integral number of bytes (FCS Error) or a bad FCS with a non-integral number of bytes (Alignment Error). Jabber packets are discarded"
    ::= { cwsPmExtendedHistory24hRxIfCountsEntry 11 }

cwsPmExtendedHistory24hRxIfCountsLengthOutRangePackets OBJECT-TYPE
    SYNTAX Counter64
    MAX-ACCESS read-write
    STATUS current
    DESCRIPTION "Number of packets received that exceeded the maximum frame size and contained a valid or invalid FCS"
    ::= { cwsPmExtendedHistory24hRxIfCountsEntry 12 }

cwsPmExtendedHistory24hRxIfCountsPackets64Octet OBJECT-TYPE
    SYNTAX Counter64
    MAX-ACCESS read-write
    STATUS current
    DESCRIPTION "Number of packets (including bad packets) received that were 64 bytes in length (excluding framing bits but including FCS bytes)."
    ::= { cwsPmExtendedHistory24hRxIfCountsEntry 13 }

cwsPmExtendedHistory24hRxIfCountsPackets65127Octet OBJECT-TYPE
    SYNTAX Counter64
    MAX-ACCESS read-write
    STATUS current
    DESCRIPTION "Number of good and bad packets received that were between 65 and 127 bytes in length (excluding framing bits but including FCS bytes)."
    ::= { cwsPmExtendedHistory24hRxIfCountsEntry 14 }

cwsPmExtendedHistory24hRxIfCountsPackets128255Octet OBJECT-TYPE
    SYNTAX Counter64
    MAX-ACCESS read-write
    STATUS current
    DESCRIPTION "Number of good and bad packets received that were between 128 and 255 bytes in length inclusive (excluding framing bits but including FCS bytes)."
    ::= { cwsPmExtendedHistory24hRxIfCountsEntry 15 }

cwsPmExtendedHistory24hRxIfCountsPackets256511Octet OBJECT-TYPE
    SYNTAX Counter64
    MAX-ACCESS read-write
    STATUS current
    DESCRIPTION "Number of good and bad packets received that were between 256 and 511 bytes in length inclusive (excluding framing bits but including FCS bytes)."
    ::= { cwsPmExtendedHistory24hRxIfCountsEntry 16 }

cwsPmExtendedHistory24hRxIfCountsPackets5121023Octet OBJECT-TYPE
    SYNTAX Counter64
    MAX-ACCESS read-write
    STATUS current
    DESCRIPTION "Number of good and bad packets received that were between 512 and 1023 bytes in length inclusive (excluding framing bits but including FCS bytes)."
    ::= { cwsPmExtendedHistory24hRxIfCountsEntry 17 }

cwsPmExtendedHistory24hRxIfCountsPackets10241518Octet OBJECT-TYPE
    SYNTAX Counter64
    MAX-ACCESS read-write
    STATUS current
    DESCRIPTION "Number of good and bad packets received that were between 1024 and 1518 bytes in length inclusive (excluding framing bits but including FCS bytes)."
    ::= { cwsPmExtendedHistory24hRxIfCountsEntry 18 }

cwsPmExtendedHistory24hTxIfCountsTable OBJECT-TYPE
    SYNTAX SEQUENCE OF CwsPmExtendedHistory24hTxIfCountsEntry
    MAX-ACCESS not-accessible
    STATUS current
    DESCRIPTION "Tx counts."
    ::= { cienaWsPmMIB 51 }

cwsPmExtendedHistory24hTxIfCountsEntry OBJECT-TYPE
    SYNTAX CwsPmExtendedHistory24hTxIfCountsEntry
    MAX-ACCESS not-accessible
    STATUS current
    DESCRIPTION "Entry for cwsPmExtendedHistory24hTxIfCountsTable."
    INDEX { cwsPmPortExtendedTxRxInstancesInstanceName, cwsPmExtendedHistory24hTxIfCountsTableSnmpKey }
    ::= { cwsPmExtendedHistory24hTxIfCountsTable 1 }

CwsPmExtendedHistory24hTxIfCountsEntry ::= SEQUENCE { 
    cwsPmExtendedHistory24hTxIfCountsTableSnmpKey Integer32,
    cwsPmExtendedHistory24hTxIfCountsBytes Counter64,
    cwsPmExtendedHistory24hTxIfCountsPackets Counter64,
    cwsPmExtendedHistory24hTxIfCountsAverageLinkUtilization Decimal1Dig,
    cwsPmExtendedHistory24hTxIfCountsCrcErroredPackets Counter64,
    cwsPmExtendedHistory24hTxIfCountsMulticastPackets Counter64,
    cwsPmExtendedHistory24hTxIfCountsBroadcastPackets Counter64,
    cwsPmExtendedHistory24hTxIfCountsPausePackets Counter64,
    cwsPmExtendedHistory24hTxIfCountsExcessiveDeferredPackets Counter64,
    cwsPmExtendedHistory24hTxIfCountsGiantPackets Counter64,
    cwsPmExtendedHistory24hTxIfCountsUnderrunPackets Counter64,
    cwsPmExtendedHistory24hTxIfCountsLengthCheckErrorPackets Counter64,
    cwsPmExtendedHistory24hTxIfCountsLengthOutRangePackets Counter64 
}

cwsPmExtendedHistory24hTxIfCountsTableSnmpKey OBJECT-TYPE
    SYNTAX Integer32(0..2147483647)
    MAX-ACCESS not-accessible
    STATUS current
    DESCRIPTION "Unique key for cwsPmExtendedHistory24hTxIfCounts"
    ::= { cwsPmExtendedHistory24hTxIfCountsEntry 1 }

cwsPmExtendedHistory24hTxIfCountsBytes OBJECT-TYPE
    SYNTAX Counter64
    MAX-ACCESS read-write
    STATUS current
    DESCRIPTION "Number of transmitted bytes in good and bad packets including FCS bytes and excluding frame bits."
    ::= { cwsPmExtendedHistory24hTxIfCountsEntry 2 }

cwsPmExtendedHistory24hTxIfCountsPackets OBJECT-TYPE
    SYNTAX Counter64
    MAX-ACCESS read-write
    STATUS current
    DESCRIPTION "Number of transmitted packets, including all unicast, multicast, broadcast, MAC control, and bad packets"
    ::= { cwsPmExtendedHistory24hTxIfCountsEntry 3 }

cwsPmExtendedHistory24hTxIfCountsAverageLinkUtilization OBJECT-TYPE
    SYNTAX Decimal1Dig
    MAX-ACCESS read-write
    STATUS current
    DESCRIPTION "Average percent utilization derived from Tx bytes and port speed."
    ::= { cwsPmExtendedHistory24hTxIfCountsEntry 13 }

cwsPmExtendedHistory24hTxIfCountsCrcErroredPackets OBJECT-TYPE
    SYNTAX Counter64
    MAX-ACCESS read-write
    STATUS current
    DESCRIPTION "Number of transmitted packets with an FCS error"
    ::= { cwsPmExtendedHistory24hTxIfCountsEntry 4 }

cwsPmExtendedHistory24hTxIfCountsMulticastPackets OBJECT-TYPE
    SYNTAX Counter64
    MAX-ACCESS read-write
    STATUS current
    DESCRIPTION "Number of good multicast packets transmitted"
    ::= { cwsPmExtendedHistory24hTxIfCountsEntry 5 }

cwsPmExtendedHistory24hTxIfCountsBroadcastPackets OBJECT-TYPE
    SYNTAX Counter64
    MAX-ACCESS read-write
    STATUS current
    DESCRIPTION "Number of good broadcast packets transmitted"
    ::= { cwsPmExtendedHistory24hTxIfCountsEntry 6 }

cwsPmExtendedHistory24hTxIfCountsPausePackets OBJECT-TYPE
    SYNTAX Counter64
    MAX-ACCESS read-write
    STATUS current
    DESCRIPTION "Number of pause packets transmitted"
    ::= { cwsPmExtendedHistory24hTxIfCountsEntry 7 }

cwsPmExtendedHistory24hTxIfCountsExcessiveDeferredPackets OBJECT-TYPE
    SYNTAX Counter64
    MAX-ACCESS read-write
    STATUS current
    DESCRIPTION "Number of transmitted packets experiencing two or more deferrals. Applicable to copper ports only"
    ::= { cwsPmExtendedHistory24hTxIfCountsEntry 8 }

cwsPmExtendedHistory24hTxIfCountsGiantPackets OBJECT-TYPE
    SYNTAX Counter64
    MAX-ACCESS read-write
    STATUS current
    DESCRIPTION "Number of well-formed packets larger than 1518 bytes, including FCS bytes but excluding framing bits."
    ::= { cwsPmExtendedHistory24hTxIfCountsEntry 9 }

cwsPmExtendedHistory24hTxIfCountsUnderrunPackets OBJECT-TYPE
    SYNTAX Counter64
    MAX-ACCESS read-write
    STATUS current
    DESCRIPTION "Number of underrun packets transmitted"
    ::= { cwsPmExtendedHistory24hTxIfCountsEntry 10 }

cwsPmExtendedHistory24hTxIfCountsLengthCheckErrorPackets OBJECT-TYPE
    SYNTAX Counter64
    MAX-ACCESS read-write
    STATUS current
    DESCRIPTION "Number of length check packets transmitted"
    ::= { cwsPmExtendedHistory24hTxIfCountsEntry 11 }

cwsPmExtendedHistory24hTxIfCountsLengthOutRangePackets OBJECT-TYPE
    SYNTAX Counter64
    MAX-ACCESS read-write
    STATUS current
    DESCRIPTION "Number of length out-of-range packets transmitted"
    ::= { cwsPmExtendedHistory24hTxIfCountsEntry 12 }

cwsPmExtendedHistory24hTxQueueTable OBJECT-TYPE
    SYNTAX SEQUENCE OF CwsPmExtendedHistory24hTxQueueEntry
    MAX-ACCESS not-accessible
    STATUS current
    DESCRIPTION "Tx queue."
    ::= { cienaWsPmMIB 52 }

cwsPmExtendedHistory24hTxQueueEntry OBJECT-TYPE
    SYNTAX CwsPmExtendedHistory24hTxQueueEntry
    MAX-ACCESS not-accessible
    STATUS current
    DESCRIPTION "Entry for cwsPmExtendedHistory24hTxQueueTable."
    INDEX { cwsPmPortExtendedTxRxInstancesInstanceName, cwsPmExtendedHistory24hTxQueueTableSnmpKey }
    ::= { cwsPmExtendedHistory24hTxQueueTable 1 }

CwsPmExtendedHistory24hTxQueueEntry ::= SEQUENCE { 
    cwsPmExtendedHistory24hTxQueueTableSnmpKey Integer32,
    cwsPmExtendedHistory24hTxQueuePacketDropCountSummary Counter64,
    cwsPmExtendedHistory24hTxQueueQ0PacketDropCount Counter64,
    cwsPmExtendedHistory24hTxQueueQ1PacketDropCount Counter64,
    cwsPmExtendedHistory24hTxQueueQ2PacketDropCount Counter64,
    cwsPmExtendedHistory24hTxQueueQ3PacketDropCount Counter64,
    cwsPmExtendedHistory24hTxQueueQ4PacketDropCount Counter64,
    cwsPmExtendedHistory24hTxQueueQ5PacketDropCount Counter64,
    cwsPmExtendedHistory24hTxQueueQ6PacketDropCount Counter64,
    cwsPmExtendedHistory24hTxQueueQ7PacketDropCount Counter64 
}

cwsPmExtendedHistory24hTxQueueTableSnmpKey OBJECT-TYPE
    SYNTAX Integer32(0..2147483647)
    MAX-ACCESS not-accessible
    STATUS current
    DESCRIPTION "Unique key for cwsPmExtendedHistory24hTxQueue"
    ::= { cwsPmExtendedHistory24hTxQueueEntry 1 }

cwsPmExtendedHistory24hTxQueuePacketDropCountSummary OBJECT-TYPE
    SYNTAX Counter64
    MAX-ACCESS read-write
    STATUS current
    DESCRIPTION "Summary of the number of bytes dropped from queues 0 to 3 (Q0, Q1, Q2, and Q3)"
    ::= { cwsPmExtendedHistory24hTxQueueEntry 2 }

cwsPmExtendedHistory24hTxQueueQ0PacketDropCount OBJECT-TYPE
    SYNTAX Counter64
    MAX-ACCESS read-write
    STATUS current
    DESCRIPTION "The number of bytes dropped from queue 0 (Q0)"
    ::= { cwsPmExtendedHistory24hTxQueueEntry 3 }

cwsPmExtendedHistory24hTxQueueQ1PacketDropCount OBJECT-TYPE
    SYNTAX Counter64
    MAX-ACCESS read-write
    STATUS current
    DESCRIPTION "The number of bytes dropped from queue 1 (Q1)"
    ::= { cwsPmExtendedHistory24hTxQueueEntry 4 }

cwsPmExtendedHistory24hTxQueueQ2PacketDropCount OBJECT-TYPE
    SYNTAX Counter64
    MAX-ACCESS read-write
    STATUS current
    DESCRIPTION "The number of bytes dropped from queue 2 (Q2)"
    ::= { cwsPmExtendedHistory24hTxQueueEntry 5 }

cwsPmExtendedHistory24hTxQueueQ3PacketDropCount OBJECT-TYPE
    SYNTAX Counter64
    MAX-ACCESS read-write
    STATUS current
    DESCRIPTION "The number of bytes dropped from queue 3 (Q3)"
    ::= { cwsPmExtendedHistory24hTxQueueEntry 6 }

cwsPmExtendedHistory24hTxQueueQ4PacketDropCount OBJECT-TYPE
    SYNTAX Counter64
    MAX-ACCESS read-write
    STATUS current
    DESCRIPTION "The number of bytes dropped from queue 4 (Q4)"
    ::= { cwsPmExtendedHistory24hTxQueueEntry 7 }

cwsPmExtendedHistory24hTxQueueQ5PacketDropCount OBJECT-TYPE
    SYNTAX Counter64
    MAX-ACCESS read-write
    STATUS current
    DESCRIPTION "The number of bytes dropped from queue 5 (Q5)"
    ::= { cwsPmExtendedHistory24hTxQueueEntry 8 }

cwsPmExtendedHistory24hTxQueueQ6PacketDropCount OBJECT-TYPE
    SYNTAX Counter64
    MAX-ACCESS read-write
    STATUS current
    DESCRIPTION "The number of bytes dropped from queue 6 (Q6)"
    ::= { cwsPmExtendedHistory24hTxQueueEntry 9 }

cwsPmExtendedHistory24hTxQueueQ7PacketDropCount OBJECT-TYPE
    SYNTAX Counter64
    MAX-ACCESS read-write
    STATUS current
    DESCRIPTION "The number of bytes dropped from queue 7 (Q7)"
    ::= { cwsPmExtendedHistory24hTxQueueEntry 10 }

cwsPmExtendedHistory24hMacLayerTable OBJECT-TYPE
    SYNTAX SEQUENCE OF CwsPmExtendedHistory24hMacLayerEntry
    MAX-ACCESS not-accessible
    STATUS obsolete
    DESCRIPTION "None"
    ::= { cienaWsPmMIB 53 }

cwsPmExtendedHistory24hMacLayerEntry OBJECT-TYPE
    SYNTAX CwsPmExtendedHistory24hMacLayerEntry
    MAX-ACCESS not-accessible
    STATUS obsolete
    DESCRIPTION "Entry for cwsPmExtendedHistory24hMacLayerTable."
    INDEX { cwsPmPortExtendedTxRxInstancesInstanceName, cwsPmExtendedHistory24hMacLayerTableSnmpKey }
    ::= { cwsPmExtendedHistory24hMacLayerTable 1 }

CwsPmExtendedHistory24hMacLayerEntry ::= SEQUENCE { 
    cwsPmExtendedHistory24hMacLayerTableSnmpKey Integer32,
    cwsPmExtendedHistory24hMacLayerUnavailableSeconds Counter64 
}

cwsPmExtendedHistory24hMacLayerTableSnmpKey OBJECT-TYPE
    SYNTAX Integer32(0..2147483647)
    MAX-ACCESS not-accessible
    STATUS current
    DESCRIPTION "Unique key for cwsPmExtendedHistory24hMacLayer"
    ::= { cwsPmExtendedHistory24hMacLayerEntry 1 }

cwsPmExtendedHistory24hMacLayerUnavailableSeconds OBJECT-TYPE
    SYNTAX Counter64
    MAX-ACCESS read-only
    STATUS obsolete
    DESCRIPTION "The number of seconds that the interface was unavailable."
    ::= { cwsPmExtendedHistory24hMacLayerEntry 2 }

cwsPmExtendedHistory24hPcsLayerTable OBJECT-TYPE
    SYNTAX SEQUENCE OF CwsPmExtendedHistory24hPcsLayerEntry
    MAX-ACCESS not-accessible
    STATUS current
    DESCRIPTION "None"
    ::= { cienaWsPmMIB 54 }

cwsPmExtendedHistory24hPcsLayerEntry OBJECT-TYPE
    SYNTAX CwsPmExtendedHistory24hPcsLayerEntry
    MAX-ACCESS not-accessible
    STATUS current
    DESCRIPTION "Entry for cwsPmExtendedHistory24hPcsLayerTable."
    INDEX { cwsPmPortExtendedTxRxInstancesInstanceName, cwsPmExtendedHistory24hPcsLayerTableSnmpKey }
    ::= { cwsPmExtendedHistory24hPcsLayerTable 1 }

CwsPmExtendedHistory24hPcsLayerEntry ::= SEQUENCE { 
    cwsPmExtendedHistory24hPcsLayerTableSnmpKey Integer32,
    cwsPmExtendedHistory24hPcsLayerErroredSeconds Counter64,
    cwsPmExtendedHistory24hPcsLayerSeverelyErroredSeconds Counter64,
    cwsPmExtendedHistory24hPcsLayerUnavailableSeconds Counter64 
}

cwsPmExtendedHistory24hPcsLayerTableSnmpKey OBJECT-TYPE
    SYNTAX Integer32(0..2147483647)
    MAX-ACCESS not-accessible
    STATUS current
    DESCRIPTION "Unique key for cwsPmExtendedHistory24hPcsLayer"
    ::= { cwsPmExtendedHistory24hPcsLayerEntry 1 }

cwsPmExtendedHistory24hPcsLayerErroredSeconds OBJECT-TYPE
    SYNTAX Counter64
    MAX-ACCESS read-write
    STATUS current
    DESCRIPTION "Number of seconds that error happened."
    ::= { cwsPmExtendedHistory24hPcsLayerEntry 2 }

cwsPmExtendedHistory24hPcsLayerSeverelyErroredSeconds OBJECT-TYPE
    SYNTAX Counter64
    MAX-ACCESS read-write
    STATUS current
    DESCRIPTION "Number of seconds that severe error happened."
    ::= { cwsPmExtendedHistory24hPcsLayerEntry 3 }

cwsPmExtendedHistory24hPcsLayerUnavailableSeconds OBJECT-TYPE
    SYNTAX Counter64
    MAX-ACCESS read-write
    STATUS current
    DESCRIPTION "Number of seconds that the interface was unavailable."
    ::= { cwsPmExtendedHistory24hPcsLayerEntry 4 }

cwsPmExtendedHistory24hPcsSyncHeaderErrorsTable OBJECT-TYPE
    SYNTAX SEQUENCE OF CwsPmExtendedHistory24hPcsSyncHeaderErrorsEntry
    MAX-ACCESS not-accessible
    STATUS current
    DESCRIPTION "None"
    ::= { cienaWsPmMIB 55 }

cwsPmExtendedHistory24hPcsSyncHeaderErrorsEntry OBJECT-TYPE
    SYNTAX CwsPmExtendedHistory24hPcsSyncHeaderErrorsEntry
    MAX-ACCESS not-accessible
    STATUS current
    DESCRIPTION "Entry for cwsPmExtendedHistory24hPcsSyncHeaderErrorsTable."
    INDEX { cwsPmPortExtendedTxRxInstancesInstanceName, cwsPmExtendedHistory24hPcsSyncHeaderErrorsTableSnmpKey }
    ::= { cwsPmExtendedHistory24hPcsSyncHeaderErrorsTable 1 }

CwsPmExtendedHistory24hPcsSyncHeaderErrorsEntry ::= SEQUENCE { 
    cwsPmExtendedHistory24hPcsSyncHeaderErrorsTableSnmpKey Integer32,
    cwsPmExtendedHistory24hPcsSyncHeaderErrorsCount Counter64 
}

cwsPmExtendedHistory24hPcsSyncHeaderErrorsTableSnmpKey OBJECT-TYPE
    SYNTAX Integer32(0..2147483647)
    MAX-ACCESS not-accessible
    STATUS current
    DESCRIPTION "Unique key for cwsPmExtendedHistory24hPcsSyncHeaderErrors"
    ::= { cwsPmExtendedHistory24hPcsSyncHeaderErrorsEntry 1 }

cwsPmExtendedHistory24hPcsSyncHeaderErrorsCount OBJECT-TYPE
    SYNTAX Counter64
    MAX-ACCESS read-only
    STATUS current
    DESCRIPTION "Sync header errors count value."
    ::= { cwsPmExtendedHistory24hPcsSyncHeaderErrorsEntry 2 }

cwsPmExtendedHistory24hPcsBlockErrorsTable OBJECT-TYPE
    SYNTAX SEQUENCE OF CwsPmExtendedHistory24hPcsBlockErrorsEntry
    MAX-ACCESS not-accessible
    STATUS current
    DESCRIPTION "None"
    ::= { cienaWsPmMIB 56 }

cwsPmExtendedHistory24hPcsBlockErrorsEntry OBJECT-TYPE
    SYNTAX CwsPmExtendedHistory24hPcsBlockErrorsEntry
    MAX-ACCESS not-accessible
    STATUS current
    DESCRIPTION "Entry for cwsPmExtendedHistory24hPcsBlockErrorsTable."
    INDEX { cwsPmPortExtendedTxRxInstancesInstanceName, cwsPmExtendedHistory24hPcsBlockErrorsTableSnmpKey }
    ::= { cwsPmExtendedHistory24hPcsBlockErrorsTable 1 }

CwsPmExtendedHistory24hPcsBlockErrorsEntry ::= SEQUENCE { 
    cwsPmExtendedHistory24hPcsBlockErrorsTableSnmpKey Integer32,
    cwsPmExtendedHistory24hPcsBlockErrorsCount Counter64 
}

cwsPmExtendedHistory24hPcsBlockErrorsTableSnmpKey OBJECT-TYPE
    SYNTAX Integer32(0..2147483647)
    MAX-ACCESS not-accessible
    STATUS current
    DESCRIPTION "Unique key for cwsPmExtendedHistory24hPcsBlockErrors"
    ::= { cwsPmExtendedHistory24hPcsBlockErrorsEntry 1 }

cwsPmExtendedHistory24hPcsBlockErrorsCount OBJECT-TYPE
    SYNTAX Counter64
    MAX-ACCESS read-only
    STATUS current
    DESCRIPTION "Block errors count value."
    ::= { cwsPmExtendedHistory24hPcsBlockErrorsEntry 2 }

cwsPmExtendedHistory24hPcsMultilaneBipErrorsTable OBJECT-TYPE
    SYNTAX SEQUENCE OF CwsPmExtendedHistory24hPcsMultilaneBipErrorsEntry
    MAX-ACCESS not-accessible
    STATUS current
    DESCRIPTION "None"
    ::= { cienaWsPmMIB 57 }

cwsPmExtendedHistory24hPcsMultilaneBipErrorsEntry OBJECT-TYPE
    SYNTAX CwsPmExtendedHistory24hPcsMultilaneBipErrorsEntry
    MAX-ACCESS not-accessible
    STATUS current
    DESCRIPTION "Entry for cwsPmExtendedHistory24hPcsMultilaneBipErrorsTable."
    INDEX { cwsPmPortExtendedTxRxInstancesInstanceName, cwsPmExtendedHistory24hPcsMultilaneBipErrorsTableSnmpKey }
    ::= { cwsPmExtendedHistory24hPcsMultilaneBipErrorsTable 1 }

CwsPmExtendedHistory24hPcsMultilaneBipErrorsEntry ::= SEQUENCE { 
    cwsPmExtendedHistory24hPcsMultilaneBipErrorsTableSnmpKey Integer32,
    cwsPmExtendedHistory24hPcsMultilaneBipErrorsCount Counter64 
}

cwsPmExtendedHistory24hPcsMultilaneBipErrorsTableSnmpKey OBJECT-TYPE
    SYNTAX Integer32(0..2147483647)
    MAX-ACCESS not-accessible
    STATUS current
    DESCRIPTION "Unique key for cwsPmExtendedHistory24hPcsMultilaneBipErrors"
    ::= { cwsPmExtendedHistory24hPcsMultilaneBipErrorsEntry 1 }

cwsPmExtendedHistory24hPcsMultilaneBipErrorsCount OBJECT-TYPE
    SYNTAX Counter64
    MAX-ACCESS read-only
    STATUS current
    DESCRIPTION "Multilane bip errors count value."
    ::= { cwsPmExtendedHistory24hPcsMultilaneBipErrorsEntry 2 }

cwsPmExtendedHistory24hOduLayerTable OBJECT-TYPE
    SYNTAX SEQUENCE OF CwsPmExtendedHistory24hOduLayerEntry
    MAX-ACCESS not-accessible
    STATUS current
    DESCRIPTION "None"
    ::= { cienaWsPmMIB 124 }

cwsPmExtendedHistory24hOduLayerEntry OBJECT-TYPE
    SYNTAX CwsPmExtendedHistory24hOduLayerEntry
    MAX-ACCESS not-accessible
    STATUS current
    DESCRIPTION "Entry for cwsPmExtendedHistory24hOduLayerTable."
    INDEX { cwsPmPortExtendedTxRxInstancesInstanceName, cwsPmExtendedHistory24hOduLayerTableSnmpKey }
    ::= { cwsPmExtendedHistory24hOduLayerTable 1 }

CwsPmExtendedHistory24hOduLayerEntry ::= SEQUENCE { 
    cwsPmExtendedHistory24hOduLayerTableSnmpKey Integer32,
    cwsPmExtendedHistory24hOduLayerErroredSeconds Counter64,
    cwsPmExtendedHistory24hOduLayerSeverelyErroredSeconds Counter64,
    cwsPmExtendedHistory24hOduLayerUnavailableSeconds Counter64 
}

cwsPmExtendedHistory24hOduLayerTableSnmpKey OBJECT-TYPE
    SYNTAX Integer32(0..2147483647)
    MAX-ACCESS not-accessible
    STATUS current
    DESCRIPTION "Unique key for cwsPmExtendedHistory24hOduLayer"
    ::= { cwsPmExtendedHistory24hOduLayerEntry 1 }

cwsPmExtendedHistory24hOduLayerErroredSeconds OBJECT-TYPE
    SYNTAX Counter64
    MAX-ACCESS read-write
    STATUS current
    DESCRIPTION "Number of seconds that error happened."
    ::= { cwsPmExtendedHistory24hOduLayerEntry 2 }

cwsPmExtendedHistory24hOduLayerSeverelyErroredSeconds OBJECT-TYPE
    SYNTAX Counter64
    MAX-ACCESS read-write
    STATUS current
    DESCRIPTION "Number of seconds that severe error happened."
    ::= { cwsPmExtendedHistory24hOduLayerEntry 3 }

cwsPmExtendedHistory24hOduLayerUnavailableSeconds OBJECT-TYPE
    SYNTAX Counter64
    MAX-ACCESS read-write
    STATUS current
    DESCRIPTION "Number of seconds that the interface was unavailable."
    ::= { cwsPmExtendedHistory24hOduLayerEntry 4 }

cwsPmExtendedHistory24hFecLayerTable OBJECT-TYPE
    SYNTAX SEQUENCE OF CwsPmExtendedHistory24hFecLayerEntry
    MAX-ACCESS not-accessible
    STATUS current
    DESCRIPTION "None"
    ::= { cienaWsPmMIB 58 }

cwsPmExtendedHistory24hFecLayerEntry OBJECT-TYPE
    SYNTAX CwsPmExtendedHistory24hFecLayerEntry
    MAX-ACCESS not-accessible
    STATUS current
    DESCRIPTION "Entry for cwsPmExtendedHistory24hFecLayerTable."
    INDEX { cwsPmPortExtendedTxRxInstancesInstanceName, cwsPmExtendedHistory24hFecLayerTableSnmpKey }
    ::= { cwsPmExtendedHistory24hFecLayerTable 1 }

CwsPmExtendedHistory24hFecLayerEntry ::= SEQUENCE { 
    cwsPmExtendedHistory24hFecLayerTableSnmpKey Integer32,
    cwsPmExtendedHistory24hFecLayerCorrectedBlockCount Counter64,
    cwsPmExtendedHistory24hFecLayerUncorrectedBlockCount Counter64,
    cwsPmExtendedHistory24hFecLayerSymbolErrorCount Counter64 
}

cwsPmExtendedHistory24hFecLayerTableSnmpKey OBJECT-TYPE
    SYNTAX Integer32(0..2147483647)
    MAX-ACCESS not-accessible
    STATUS current
    DESCRIPTION "Unique key for cwsPmExtendedHistory24hFecLayer"
    ::= { cwsPmExtendedHistory24hFecLayerEntry 1 }

cwsPmExtendedHistory24hFecLayerCorrectedBlockCount OBJECT-TYPE
    SYNTAX Counter64
    MAX-ACCESS read-write
    STATUS current
    DESCRIPTION "Fec layer corrected block count"
    ::= { cwsPmExtendedHistory24hFecLayerEntry 2 }

cwsPmExtendedHistory24hFecLayerUncorrectedBlockCount OBJECT-TYPE
    SYNTAX Counter64
    MAX-ACCESS read-write
    STATUS current
    DESCRIPTION "Fec layer uncorrected block count"
    ::= { cwsPmExtendedHistory24hFecLayerEntry 3 }

cwsPmExtendedHistory24hFecLayerSymbolErrorCount OBJECT-TYPE
    SYNTAX Counter64
    MAX-ACCESS read-write
    STATUS current
    DESCRIPTION "Fec layer symbol error count"
    ::= { cwsPmExtendedHistory24hFecLayerEntry 4 }

cwsPmPtpBasicInstancesTable OBJECT-TYPE
    SYNTAX SEQUENCE OF CwsPmPtpBasicInstancesEntry
    MAX-ACCESS not-accessible
    STATUS current
    DESCRIPTION "PTP PM basic instance."
    ::= { cienaWsPmMIB 59 }

cwsPmPtpBasicInstancesEntry OBJECT-TYPE
    SYNTAX CwsPmPtpBasicInstancesEntry
    MAX-ACCESS not-accessible
    STATUS current
    DESCRIPTION "Entry for cwsPmPtpBasicInstancesTable."
    INDEX { cwsPmPtpBasicInstancesInstanceName }
    ::= { cwsPmPtpBasicInstancesTable 1 }

CwsPmPtpBasicInstancesEntry ::= SEQUENCE { 
    cwsPmPtpBasicInstancesInstanceName Integer32 
}

cwsPmPtpBasicInstancesInstanceName OBJECT-TYPE
    SYNTAX Integer32(0..2147483647)
    MAX-ACCESS read-only
    STATUS current
    DESCRIPTION "Unique name for PM instance."
    ::= { cwsPmPtpBasicInstancesEntry 1 }

cwsPmBasicIdTable OBJECT-TYPE
    SYNTAX SEQUENCE OF CwsPmBasicIdEntry
    MAX-ACCESS not-accessible
    STATUS current
    DESCRIPTION "PM PTP basic instance identification."
    ::= { cienaWsPmMIB 60 }

cwsPmBasicIdEntry OBJECT-TYPE
    SYNTAX CwsPmBasicIdEntry
    MAX-ACCESS not-accessible
    STATUS current
    DESCRIPTION "Entry for cwsPmBasicIdTable."
    INDEX { cwsPmPtpBasicInstancesInstanceName, cwsPmBasicIdTableSnmpKey }
    ::= { cwsPmBasicIdTable 1 }

CwsPmBasicIdEntry ::= SEQUENCE { 
    cwsPmBasicIdTableSnmpKey Integer32,
    cwsPmBasicIdInstanceId Unsigned32,
    cwsPmBasicIdInstanceType PmInstanceType,
    cwsPmBasicIdProfileType PmProfileType 
}

cwsPmBasicIdTableSnmpKey OBJECT-TYPE
    SYNTAX Integer32(0..2147483647)
    MAX-ACCESS not-accessible
    STATUS current
    DESCRIPTION "Unique key for cwsPmBasicId"
    ::= { cwsPmBasicIdEntry 1 }

cwsPmBasicIdInstanceId OBJECT-TYPE
    SYNTAX Unsigned32
    MAX-ACCESS read-write
    STATUS current
    DESCRIPTION "ID of the PM instance."
    ::= { cwsPmBasicIdEntry 2 }

cwsPmBasicIdInstanceType OBJECT-TYPE
    SYNTAX PmInstanceType
    MAX-ACCESS read-write
    STATUS current
    DESCRIPTION "The PM instance type."
    ::= { cwsPmBasicIdEntry 3 }

cwsPmBasicIdProfileType OBJECT-TYPE
    SYNTAX PmProfileType
    MAX-ACCESS read-write
    STATUS current
    DESCRIPTION "The PM profile type."
    ::= { cwsPmBasicIdEntry 4 }

cwsPmBasicStateTable OBJECT-TYPE
    SYNTAX SEQUENCE OF CwsPmBasicStateEntry
    MAX-ACCESS not-accessible
    STATUS current
    DESCRIPTION "Performance Monitoring Instance State."
    ::= { cienaWsPmMIB 61 }

cwsPmBasicStateEntry OBJECT-TYPE
    SYNTAX CwsPmBasicStateEntry
    MAX-ACCESS not-accessible
    STATUS current
    DESCRIPTION "Entry for cwsPmBasicStateTable."
    INDEX { cwsPmPtpBasicInstancesInstanceName, cwsPmBasicStateTableSnmpKey }
    ::= { cwsPmBasicStateTable 1 }

CwsPmBasicStateEntry ::= SEQUENCE { 
    cwsPmBasicStateTableSnmpKey Integer32,
    cwsPmBasicStateAdminState EnabledDisabledEnum,
    cwsPmBasicStateOperationalState EnabledDisabledEnum,
    cwsPmBasicStateCurrentBinId Unsigned32,
    cwsPmBasicStateCollectionStartDateTime StringMaxl64,
    cwsPmBasicStateCollectionEndDateTime StringMaxl64 
}

cwsPmBasicStateTableSnmpKey OBJECT-TYPE
    SYNTAX Integer32(0..2147483647)
    MAX-ACCESS not-accessible
    STATUS current
    DESCRIPTION "Unique key for cwsPmBasicState"
    ::= { cwsPmBasicStateEntry 1 }

cwsPmBasicStateAdminState OBJECT-TYPE
    SYNTAX EnabledDisabledEnum
    MAX-ACCESS read-write
    STATUS current
    DESCRIPTION "The configured administrative state of the port."
    ::= { cwsPmBasicStateEntry 2 }

cwsPmBasicStateOperationalState OBJECT-TYPE
    SYNTAX EnabledDisabledEnum
    MAX-ACCESS read-only
    STATUS current
    DESCRIPTION "The operational state of the PM instance."
    ::= { cwsPmBasicStateEntry 3 }

cwsPmBasicStateCurrentBinId OBJECT-TYPE
    SYNTAX Unsigned32
    MAX-ACCESS read-only
    STATUS current
    DESCRIPTION "The operational state of the PM instance."
    ::= { cwsPmBasicStateEntry 4 }

cwsPmBasicStateCollectionStartDateTime OBJECT-TYPE
    SYNTAX StringMaxl64
    MAX-ACCESS read-only
    STATUS current
    DESCRIPTION "The PM stats collection starting date and time."
    ::= { cwsPmBasicStateEntry 5 }

cwsPmBasicStateCollectionEndDateTime OBJECT-TYPE
    SYNTAX StringMaxl64
    MAX-ACCESS read-only
    STATUS current
    DESCRIPTION "The PM stats collection ending date and time."
    ::= { cwsPmBasicStateEntry 6 }

cwsPmBasicPropertiesTable OBJECT-TYPE
    SYNTAX SEQUENCE OF CwsPmBasicPropertiesEntry
    MAX-ACCESS not-accessible
    STATUS current
    DESCRIPTION "PM instance properties."
    ::= { cienaWsPmMIB 62 }

cwsPmBasicPropertiesEntry OBJECT-TYPE
    SYNTAX CwsPmBasicPropertiesEntry
    MAX-ACCESS not-accessible
    STATUS current
    DESCRIPTION "Entry for cwsPmBasicPropertiesTable."
    INDEX { cwsPmPtpBasicInstancesInstanceName, cwsPmBasicPropertiesTableSnmpKey }
    ::= { cwsPmBasicPropertiesTable 1 }

CwsPmBasicPropertiesEntry ::= SEQUENCE { 
    cwsPmBasicPropertiesTableSnmpKey Integer32,
    cwsPmBasicPropertiesConfigurationMode PmConfigurationMode,
    cwsPmBasicPropertiesAlignment PmAlignment,
    cwsPmBasicPropertiesConfiguredBinCount Unsigned32,
    cwsPmBasicPropertiesConfiguredBinDuration Unsigned32 
}

cwsPmBasicPropertiesTableSnmpKey OBJECT-TYPE
    SYNTAX Integer32(0..2147483647)
    MAX-ACCESS not-accessible
    STATUS current
    DESCRIPTION "Unique key for cwsPmBasicProperties"
    ::= { cwsPmBasicPropertiesEntry 1 }

cwsPmBasicPropertiesConfigurationMode OBJECT-TYPE
    SYNTAX PmConfigurationMode
    MAX-ACCESS read-write
    STATUS current
    DESCRIPTION "The PM instance configuration mode"
    ::= { cwsPmBasicPropertiesEntry 2 }

cwsPmBasicPropertiesAlignment OBJECT-TYPE
    SYNTAX PmAlignment
    MAX-ACCESS read-write
    STATUS current
    DESCRIPTION "The PM alignment."
    ::= { cwsPmBasicPropertiesEntry 3 }

cwsPmBasicPropertiesConfiguredBinCount OBJECT-TYPE
    SYNTAX Unsigned32
    MAX-ACCESS read-write
    STATUS current
    DESCRIPTION "The configured number of history bins."
    ::= { cwsPmBasicPropertiesEntry 4 }

cwsPmBasicPropertiesConfiguredBinDuration OBJECT-TYPE
    SYNTAX Unsigned32
    MAX-ACCESS read-write
    STATUS current
    DESCRIPTION "The configured PM bin duration in minutes."
    ::= { cwsPmBasicPropertiesEntry 5 }

cwsPmBasicAttachedInterfaceTable OBJECT-TYPE
    SYNTAX SEQUENCE OF CwsPmBasicAttachedInterfaceEntry
    MAX-ACCESS not-accessible
    STATUS current
    DESCRIPTION "Attached interface."
    ::= { cienaWsPmMIB 63 }

cwsPmBasicAttachedInterfaceEntry OBJECT-TYPE
    SYNTAX CwsPmBasicAttachedInterfaceEntry
    MAX-ACCESS not-accessible
    STATUS current
    DESCRIPTION "Entry for cwsPmBasicAttachedInterfaceTable."
    INDEX { cwsPmPtpBasicInstancesInstanceName, cwsPmBasicAttachedInterfaceTableSnmpKey }
    ::= { cwsPmBasicAttachedInterfaceTable 1 }

CwsPmBasicAttachedInterfaceEntry ::= SEQUENCE { 
    cwsPmBasicAttachedInterfaceTableSnmpKey Integer32,
    cwsPmBasicAttachedInterfaceType PmInterfaceType,
    cwsPmBasicAttachedInterfaceName StringMaxl32,
    cwsPmBasicAttachedInterfaceOperationalState EnabledDisabledEnum 
}

cwsPmBasicAttachedInterfaceTableSnmpKey OBJECT-TYPE
    SYNTAX Integer32(0..2147483647)
    MAX-ACCESS not-accessible
    STATUS current
    DESCRIPTION "Unique key for cwsPmBasicAttachedInterface"
    ::= { cwsPmBasicAttachedInterfaceEntry 1 }

cwsPmBasicAttachedInterfaceType OBJECT-TYPE
    SYNTAX PmInterfaceType
    MAX-ACCESS read-write
    STATUS current
    DESCRIPTION "Attached interface type."
    ::= { cwsPmBasicAttachedInterfaceEntry 2 }

cwsPmBasicAttachedInterfaceName OBJECT-TYPE
    SYNTAX StringMaxl32
    MAX-ACCESS read-write
    STATUS current
    DESCRIPTION "Attached interface name."
    ::= { cwsPmBasicAttachedInterfaceEntry 3 }

cwsPmBasicAttachedInterfaceOperationalState OBJECT-TYPE
    SYNTAX EnabledDisabledEnum
    MAX-ACCESS read-write
    STATUS current
    DESCRIPTION "Attached interface operational state."
    ::= { cwsPmBasicAttachedInterfaceEntry 4 }

cwsPmBasicCurrentIdTable OBJECT-TYPE
    SYNTAX SEQUENCE OF CwsPmBasicCurrentIdEntry
    MAX-ACCESS not-accessible
    STATUS current
    DESCRIPTION "PM Bin identification."
    ::= { cienaWsPmMIB 64 }

cwsPmBasicCurrentIdEntry OBJECT-TYPE
    SYNTAX CwsPmBasicCurrentIdEntry
    MAX-ACCESS not-accessible
    STATUS current
    DESCRIPTION "Entry for cwsPmBasicCurrentIdTable."
    INDEX { cwsPmPtpBasicInstancesInstanceName, cwsPmBasicCurrentIdTableSnmpKey }
    ::= { cwsPmBasicCurrentIdTable 1 }

CwsPmBasicCurrentIdEntry ::= SEQUENCE { 
    cwsPmBasicCurrentIdTableSnmpKey Integer32,
    cwsPmBasicCurrentIdBinNumber Unsigned32,
    cwsPmBasicCurrentIdBinName StringMaxl32 
}

cwsPmBasicCurrentIdTableSnmpKey OBJECT-TYPE
    SYNTAX Integer32(0..2147483647)
    MAX-ACCESS not-accessible
    STATUS current
    DESCRIPTION "Unique key for cwsPmBasicCurrentId"
    ::= { cwsPmBasicCurrentIdEntry 1 }

cwsPmBasicCurrentIdBinNumber OBJECT-TYPE
    SYNTAX Unsigned32
    MAX-ACCESS read-write
    STATUS current
    DESCRIPTION "The PM bin number."
    ::= { cwsPmBasicCurrentIdEntry 2 }

cwsPmBasicCurrentIdBinName OBJECT-TYPE
    SYNTAX StringMaxl32
    MAX-ACCESS read-write
    STATUS current
    DESCRIPTION "The PM bin name."
    ::= { cwsPmBasicCurrentIdEntry 3 }

cwsPmBasicCurrentStateTable OBJECT-TYPE
    SYNTAX SEQUENCE OF CwsPmBasicCurrentStateEntry
    MAX-ACCESS not-accessible
    STATUS current
    DESCRIPTION "PM bin state."
    ::= { cienaWsPmMIB 65 }

cwsPmBasicCurrentStateEntry OBJECT-TYPE
    SYNTAX CwsPmBasicCurrentStateEntry
    MAX-ACCESS not-accessible
    STATUS current
    DESCRIPTION "Entry for cwsPmBasicCurrentStateTable."
    INDEX { cwsPmPtpBasicInstancesInstanceName, cwsPmBasicCurrentStateTableSnmpKey }
    ::= { cwsPmBasicCurrentStateTable 1 }

CwsPmBasicCurrentStateEntry ::= SEQUENCE { 
    cwsPmBasicCurrentStateTableSnmpKey Integer32,
    cwsPmBasicCurrentStateStartDateTime StringMaxl32,
    cwsPmBasicCurrentStateClearedDateTime StringMaxl32,
    cwsPmBasicCurrentStateState PmBinState 
}

cwsPmBasicCurrentStateTableSnmpKey OBJECT-TYPE
    SYNTAX Integer32(0..2147483647)
    MAX-ACCESS not-accessible
    STATUS current
    DESCRIPTION "Unique key for cwsPmBasicCurrentState"
    ::= { cwsPmBasicCurrentStateEntry 1 }

cwsPmBasicCurrentStateStartDateTime OBJECT-TYPE
    SYNTAX StringMaxl32
    MAX-ACCESS read-write
    STATUS current
    DESCRIPTION "Start date and time."
    ::= { cwsPmBasicCurrentStateEntry 2 }

cwsPmBasicCurrentStateClearedDateTime OBJECT-TYPE
    SYNTAX StringMaxl32
    MAX-ACCESS read-write
    STATUS current
    DESCRIPTION "Cleared date and time."
    ::= { cwsPmBasicCurrentStateEntry 3 }

cwsPmBasicCurrentStateState OBJECT-TYPE
    SYNTAX PmBinState
    MAX-ACCESS read-write
    STATUS current
    DESCRIPTION "The PM bin state."
    ::= { cwsPmBasicCurrentStateEntry 4 }

cwsPmBasicCurrentStatisticsTable OBJECT-TYPE
    SYNTAX SEQUENCE OF CwsPmBasicCurrentStatisticsEntry
    MAX-ACCESS not-accessible
    STATUS current
    DESCRIPTION "Statistics data."
    ::= { cienaWsPmMIB 66 }

cwsPmBasicCurrentStatisticsEntry OBJECT-TYPE
    SYNTAX CwsPmBasicCurrentStatisticsEntry
    MAX-ACCESS not-accessible
    STATUS current
    DESCRIPTION "Entry for cwsPmBasicCurrentStatisticsTable."
    INDEX { cwsPmPtpBasicInstancesInstanceName, cwsPmBasicCurrentStatisticsTableSnmpKey }
    ::= { cwsPmBasicCurrentStatisticsTable 1 }

CwsPmBasicCurrentStatisticsEntry ::= SEQUENCE { 
    cwsPmBasicCurrentStatisticsTableSnmpKey Integer32,
    cwsPmBasicCurrentStatisticsNumberOfChannels Unsigned32 
}

cwsPmBasicCurrentStatisticsTableSnmpKey OBJECT-TYPE
    SYNTAX Integer32(0..2147483647)
    MAX-ACCESS not-accessible
    STATUS current
    DESCRIPTION "Unique key for cwsPmBasicCurrentStatistics"
    ::= { cwsPmBasicCurrentStatisticsEntry 1 }

cwsPmBasicCurrentStatisticsNumberOfChannels OBJECT-TYPE
    SYNTAX Unsigned32
    MAX-ACCESS read-only
    STATUS current
    DESCRIPTION "Number of channels."
    ::= { cwsPmBasicCurrentStatisticsEntry 2 }

cwsPmBasicCurrentOpticalPowerTable OBJECT-TYPE
    SYNTAX SEQUENCE OF CwsPmBasicCurrentOpticalPowerEntry
    MAX-ACCESS not-accessible
    STATUS current
    DESCRIPTION "statistics for a PTP channel."
    ::= { cienaWsPmMIB 67 }

cwsPmBasicCurrentOpticalPowerEntry OBJECT-TYPE
    SYNTAX CwsPmBasicCurrentOpticalPowerEntry
    MAX-ACCESS not-accessible
    STATUS current
    DESCRIPTION "Entry for cwsPmBasicCurrentOpticalPowerTable."
    INDEX { cwsPmPtpBasicInstancesInstanceName, cwsPmBasicCurrentOpticalPowerChannelNumber }
    ::= { cwsPmBasicCurrentOpticalPowerTable 1 }

CwsPmBasicCurrentOpticalPowerEntry ::= SEQUENCE { 
    cwsPmBasicCurrentOpticalPowerChannelNumber Integer32 
}

cwsPmBasicCurrentOpticalPowerChannelNumber OBJECT-TYPE
    SYNTAX Integer32(0..2147483647)
    MAX-ACCESS read-only
    STATUS current
    DESCRIPTION "Channel number."
    ::= { cwsPmBasicCurrentOpticalPowerEntry 1 }

cwsPmBasicCurrentOpticalRxPowerTable OBJECT-TYPE
    SYNTAX SEQUENCE OF CwsPmBasicCurrentOpticalRxPowerEntry
    MAX-ACCESS not-accessible
    STATUS current
    DESCRIPTION "Rx power reading."
    ::= { cienaWsPmMIB 68 }

cwsPmBasicCurrentOpticalRxPowerEntry OBJECT-TYPE
    SYNTAX CwsPmBasicCurrentOpticalRxPowerEntry
    MAX-ACCESS not-accessible
    STATUS current
    DESCRIPTION "Entry for cwsPmBasicCurrentOpticalRxPowerTable."
    INDEX { cwsPmPtpBasicInstancesInstanceName, cwsPmBasicCurrentOpticalPowerChannelNumber, cwsPmBasicCurrentOpticalRxPowerTableSnmpKey }
    ::= { cwsPmBasicCurrentOpticalRxPowerTable 1 }

CwsPmBasicCurrentOpticalRxPowerEntry ::= SEQUENCE { 
    cwsPmBasicCurrentOpticalRxPowerTableSnmpKey Integer32,
    cwsPmBasicCurrentOpticalRxPowerActual Decimal3Dig,
    cwsPmBasicCurrentOpticalRxPowerMinimum Decimal3Dig,
    cwsPmBasicCurrentOpticalRxPowerMaximum Decimal3Dig,
    cwsPmBasicCurrentOpticalRxPowerAverage Decimal3Dig 
}

cwsPmBasicCurrentOpticalRxPowerTableSnmpKey OBJECT-TYPE
    SYNTAX Integer32(0..2147483647)
    MAX-ACCESS not-accessible
    STATUS current
    DESCRIPTION "Unique key for cwsPmBasicCurrentOpticalRxPower"
    ::= { cwsPmBasicCurrentOpticalRxPowerEntry 1 }

cwsPmBasicCurrentOpticalRxPowerActual OBJECT-TYPE
    SYNTAX Decimal3Dig
    MAX-ACCESS read-write
    STATUS current
    DESCRIPTION "Actual power reading."
    ::= { cwsPmBasicCurrentOpticalRxPowerEntry 2 }

cwsPmBasicCurrentOpticalRxPowerMinimum OBJECT-TYPE
    SYNTAX Decimal3Dig
    MAX-ACCESS read-write
    STATUS current
    DESCRIPTION "Minimum power reading."
    ::= { cwsPmBasicCurrentOpticalRxPowerEntry 3 }

cwsPmBasicCurrentOpticalRxPowerMaximum OBJECT-TYPE
    SYNTAX Decimal3Dig
    MAX-ACCESS read-write
    STATUS current
    DESCRIPTION "Maximum power reading."
    ::= { cwsPmBasicCurrentOpticalRxPowerEntry 4 }

cwsPmBasicCurrentOpticalRxPowerAverage OBJECT-TYPE
    SYNTAX Decimal3Dig
    MAX-ACCESS read-write
    STATUS current
    DESCRIPTION "Average power reading."
    ::= { cwsPmBasicCurrentOpticalRxPowerEntry 5 }

cwsPmBasicCurrentOpticalTxPowerTable OBJECT-TYPE
    SYNTAX SEQUENCE OF CwsPmBasicCurrentOpticalTxPowerEntry
    MAX-ACCESS not-accessible
    STATUS current
    DESCRIPTION "Tx power reading."
    ::= { cienaWsPmMIB 69 }

cwsPmBasicCurrentOpticalTxPowerEntry OBJECT-TYPE
    SYNTAX CwsPmBasicCurrentOpticalTxPowerEntry
    MAX-ACCESS not-accessible
    STATUS current
    DESCRIPTION "Entry for cwsPmBasicCurrentOpticalTxPowerTable."
    INDEX { cwsPmPtpBasicInstancesInstanceName, cwsPmBasicCurrentOpticalPowerChannelNumber, cwsPmBasicCurrentOpticalTxPowerTableSnmpKey }
    ::= { cwsPmBasicCurrentOpticalTxPowerTable 1 }

CwsPmBasicCurrentOpticalTxPowerEntry ::= SEQUENCE { 
    cwsPmBasicCurrentOpticalTxPowerTableSnmpKey Integer32,
    cwsPmBasicCurrentOpticalTxPowerActual Decimal3Dig,
    cwsPmBasicCurrentOpticalTxPowerMinimum Decimal3Dig,
    cwsPmBasicCurrentOpticalTxPowerMaximum Decimal3Dig,
    cwsPmBasicCurrentOpticalTxPowerAverage Decimal3Dig 
}

cwsPmBasicCurrentOpticalTxPowerTableSnmpKey OBJECT-TYPE
    SYNTAX Integer32(0..2147483647)
    MAX-ACCESS not-accessible
    STATUS current
    DESCRIPTION "Unique key for cwsPmBasicCurrentOpticalTxPower"
    ::= { cwsPmBasicCurrentOpticalTxPowerEntry 1 }

cwsPmBasicCurrentOpticalTxPowerActual OBJECT-TYPE
    SYNTAX Decimal3Dig
    MAX-ACCESS read-write
    STATUS current
    DESCRIPTION "Actual power reading."
    ::= { cwsPmBasicCurrentOpticalTxPowerEntry 2 }

cwsPmBasicCurrentOpticalTxPowerMinimum OBJECT-TYPE
    SYNTAX Decimal3Dig
    MAX-ACCESS read-write
    STATUS current
    DESCRIPTION "Minimum power reading."
    ::= { cwsPmBasicCurrentOpticalTxPowerEntry 3 }

cwsPmBasicCurrentOpticalTxPowerMaximum OBJECT-TYPE
    SYNTAX Decimal3Dig
    MAX-ACCESS read-write
    STATUS current
    DESCRIPTION "Maximum power reading."
    ::= { cwsPmBasicCurrentOpticalTxPowerEntry 4 }

cwsPmBasicCurrentOpticalTxPowerAverage OBJECT-TYPE
    SYNTAX Decimal3Dig
    MAX-ACCESS read-write
    STATUS current
    DESCRIPTION "Average power reading."
    ::= { cwsPmBasicCurrentOpticalTxPowerEntry 5 }

cwsPmBasicCurrentChannelRxPowerTable OBJECT-TYPE
    SYNTAX SEQUENCE OF CwsPmBasicCurrentChannelRxPowerEntry
    MAX-ACCESS not-accessible
    STATUS current
    DESCRIPTION "Rx power reading."
    ::= { cienaWsPmMIB 70 }

cwsPmBasicCurrentChannelRxPowerEntry OBJECT-TYPE
    SYNTAX CwsPmBasicCurrentChannelRxPowerEntry
    MAX-ACCESS not-accessible
    STATUS current
    DESCRIPTION "Entry for cwsPmBasicCurrentChannelRxPowerTable."
    INDEX { cwsPmPtpBasicInstancesInstanceName, cwsPmBasicCurrentChannelRxPowerTableSnmpKey }
    ::= { cwsPmBasicCurrentChannelRxPowerTable 1 }

CwsPmBasicCurrentChannelRxPowerEntry ::= SEQUENCE { 
    cwsPmBasicCurrentChannelRxPowerTableSnmpKey Integer32,
    cwsPmBasicCurrentChannelRxPowerActual Decimal3Dig,
    cwsPmBasicCurrentChannelRxPowerMinimum Decimal3Dig,
    cwsPmBasicCurrentChannelRxPowerMaximum Decimal3Dig,
    cwsPmBasicCurrentChannelRxPowerAverage Decimal3Dig 
}

cwsPmBasicCurrentChannelRxPowerTableSnmpKey OBJECT-TYPE
    SYNTAX Integer32(0..2147483647)
    MAX-ACCESS not-accessible
    STATUS current
    DESCRIPTION "Unique key for cwsPmBasicCurrentChannelRxPower"
    ::= { cwsPmBasicCurrentChannelRxPowerEntry 1 }

cwsPmBasicCurrentChannelRxPowerActual OBJECT-TYPE
    SYNTAX Decimal3Dig
    MAX-ACCESS read-write
    STATUS current
    DESCRIPTION "Actual power reading."
    ::= { cwsPmBasicCurrentChannelRxPowerEntry 2 }

cwsPmBasicCurrentChannelRxPowerMinimum OBJECT-TYPE
    SYNTAX Decimal3Dig
    MAX-ACCESS read-write
    STATUS current
    DESCRIPTION "Minimum power reading."
    ::= { cwsPmBasicCurrentChannelRxPowerEntry 3 }

cwsPmBasicCurrentChannelRxPowerMaximum OBJECT-TYPE
    SYNTAX Decimal3Dig
    MAX-ACCESS read-write
    STATUS current
    DESCRIPTION "Maximum power reading."
    ::= { cwsPmBasicCurrentChannelRxPowerEntry 4 }

cwsPmBasicCurrentChannelRxPowerAverage OBJECT-TYPE
    SYNTAX Decimal3Dig
    MAX-ACCESS read-write
    STATUS current
    DESCRIPTION "Average power reading."
    ::= { cwsPmBasicCurrentChannelRxPowerEntry 5 }

cwsPmBasicCurrent24hIdTable OBJECT-TYPE
    SYNTAX SEQUENCE OF CwsPmBasicCurrent24hIdEntry
    MAX-ACCESS not-accessible
    STATUS current
    DESCRIPTION "PM Bin identification."
    ::= { cienaWsPmMIB 71 }

cwsPmBasicCurrent24hIdEntry OBJECT-TYPE
    SYNTAX CwsPmBasicCurrent24hIdEntry
    MAX-ACCESS not-accessible
    STATUS current
    DESCRIPTION "Entry for cwsPmBasicCurrent24hIdTable."
    INDEX { cwsPmPtpBasicInstancesInstanceName, cwsPmBasicCurrent24hIdTableSnmpKey }
    ::= { cwsPmBasicCurrent24hIdTable 1 }

CwsPmBasicCurrent24hIdEntry ::= SEQUENCE { 
    cwsPmBasicCurrent24hIdTableSnmpKey Integer32,
    cwsPmBasicCurrent24hIdBinNumber Unsigned32,
    cwsPmBasicCurrent24hIdBinName StringMaxl32 
}

cwsPmBasicCurrent24hIdTableSnmpKey OBJECT-TYPE
    SYNTAX Integer32(0..2147483647)
    MAX-ACCESS not-accessible
    STATUS current
    DESCRIPTION "Unique key for cwsPmBasicCurrent24hId"
    ::= { cwsPmBasicCurrent24hIdEntry 1 }

cwsPmBasicCurrent24hIdBinNumber OBJECT-TYPE
    SYNTAX Unsigned32
    MAX-ACCESS read-write
    STATUS current
    DESCRIPTION "The PM bin number."
    ::= { cwsPmBasicCurrent24hIdEntry 2 }

cwsPmBasicCurrent24hIdBinName OBJECT-TYPE
    SYNTAX StringMaxl32
    MAX-ACCESS read-write
    STATUS current
    DESCRIPTION "The PM bin name."
    ::= { cwsPmBasicCurrent24hIdEntry 3 }

cwsPmBasicCurrent24hStateTable OBJECT-TYPE
    SYNTAX SEQUENCE OF CwsPmBasicCurrent24hStateEntry
    MAX-ACCESS not-accessible
    STATUS current
    DESCRIPTION "PM bin state."
    ::= { cienaWsPmMIB 72 }

cwsPmBasicCurrent24hStateEntry OBJECT-TYPE
    SYNTAX CwsPmBasicCurrent24hStateEntry
    MAX-ACCESS not-accessible
    STATUS current
    DESCRIPTION "Entry for cwsPmBasicCurrent24hStateTable."
    INDEX { cwsPmPtpBasicInstancesInstanceName, cwsPmBasicCurrent24hStateTableSnmpKey }
    ::= { cwsPmBasicCurrent24hStateTable 1 }

CwsPmBasicCurrent24hStateEntry ::= SEQUENCE { 
    cwsPmBasicCurrent24hStateTableSnmpKey Integer32,
    cwsPmBasicCurrent24hStateStartDateTime StringMaxl32,
    cwsPmBasicCurrent24hStateClearedDateTime StringMaxl32,
    cwsPmBasicCurrent24hStateState PmBinState 
}

cwsPmBasicCurrent24hStateTableSnmpKey OBJECT-TYPE
    SYNTAX Integer32(0..2147483647)
    MAX-ACCESS not-accessible
    STATUS current
    DESCRIPTION "Unique key for cwsPmBasicCurrent24hState"
    ::= { cwsPmBasicCurrent24hStateEntry 1 }

cwsPmBasicCurrent24hStateStartDateTime OBJECT-TYPE
    SYNTAX StringMaxl32
    MAX-ACCESS read-write
    STATUS current
    DESCRIPTION "Start date and time."
    ::= { cwsPmBasicCurrent24hStateEntry 2 }

cwsPmBasicCurrent24hStateClearedDateTime OBJECT-TYPE
    SYNTAX StringMaxl32
    MAX-ACCESS read-write
    STATUS current
    DESCRIPTION "Cleared date and time."
    ::= { cwsPmBasicCurrent24hStateEntry 3 }

cwsPmBasicCurrent24hStateState OBJECT-TYPE
    SYNTAX PmBinState
    MAX-ACCESS read-write
    STATUS current
    DESCRIPTION "The PM bin state."
    ::= { cwsPmBasicCurrent24hStateEntry 4 }

cwsPmBasicCurrent24hBinStatisticsTable OBJECT-TYPE
    SYNTAX SEQUENCE OF CwsPmBasicCurrent24hBinStatisticsEntry
    MAX-ACCESS not-accessible
    STATUS current
    DESCRIPTION "Statistics data."
    ::= { cienaWsPmMIB 73 }

cwsPmBasicCurrent24hBinStatisticsEntry OBJECT-TYPE
    SYNTAX CwsPmBasicCurrent24hBinStatisticsEntry
    MAX-ACCESS not-accessible
    STATUS current
    DESCRIPTION "Entry for cwsPmBasicCurrent24hBinStatisticsTable."
    INDEX { cwsPmPtpBasicInstancesInstanceName, cwsPmBasicCurrent24hBinStatisticsTableSnmpKey }
    ::= { cwsPmBasicCurrent24hBinStatisticsTable 1 }

CwsPmBasicCurrent24hBinStatisticsEntry ::= SEQUENCE { 
    cwsPmBasicCurrent24hBinStatisticsTableSnmpKey Integer32,
    cwsPmBasicCurrent24hBinStatisticsNumberOfChannels Unsigned32 
}

cwsPmBasicCurrent24hBinStatisticsTableSnmpKey OBJECT-TYPE
    SYNTAX Integer32(0..2147483647)
    MAX-ACCESS not-accessible
    STATUS current
    DESCRIPTION "Unique key for cwsPmBasicCurrent24hBinStatistics"
    ::= { cwsPmBasicCurrent24hBinStatisticsEntry 1 }

cwsPmBasicCurrent24hBinStatisticsNumberOfChannels OBJECT-TYPE
    SYNTAX Unsigned32
    MAX-ACCESS read-only
    STATUS current
    DESCRIPTION "Number of channels."
    ::= { cwsPmBasicCurrent24hBinStatisticsEntry 2 }

cwsPmBasicCurrent24hOpticalPowerTable OBJECT-TYPE
    SYNTAX SEQUENCE OF CwsPmBasicCurrent24hOpticalPowerEntry
    MAX-ACCESS not-accessible
    STATUS current
    DESCRIPTION "statistics for a PTP channel."
    ::= { cienaWsPmMIB 74 }

cwsPmBasicCurrent24hOpticalPowerEntry OBJECT-TYPE
    SYNTAX CwsPmBasicCurrent24hOpticalPowerEntry
    MAX-ACCESS not-accessible
    STATUS current
    DESCRIPTION "Entry for cwsPmBasicCurrent24hOpticalPowerTable."
    INDEX { cwsPmPtpBasicInstancesInstanceName, cwsPmBasicCurrent24hOpticalPowerChannelNumber }
    ::= { cwsPmBasicCurrent24hOpticalPowerTable 1 }

CwsPmBasicCurrent24hOpticalPowerEntry ::= SEQUENCE { 
    cwsPmBasicCurrent24hOpticalPowerChannelNumber Integer32 
}

cwsPmBasicCurrent24hOpticalPowerChannelNumber OBJECT-TYPE
    SYNTAX Integer32(0..2147483647)
    MAX-ACCESS read-only
    STATUS current
    DESCRIPTION "Channel number."
    ::= { cwsPmBasicCurrent24hOpticalPowerEntry 1 }

cwsPmBasicCurrent24hRxOpticalPowerTable OBJECT-TYPE
    SYNTAX SEQUENCE OF CwsPmBasicCurrent24hRxOpticalPowerEntry
    MAX-ACCESS not-accessible
    STATUS current
    DESCRIPTION "Rx power reading."
    ::= { cienaWsPmMIB 75 }

cwsPmBasicCurrent24hRxOpticalPowerEntry OBJECT-TYPE
    SYNTAX CwsPmBasicCurrent24hRxOpticalPowerEntry
    MAX-ACCESS not-accessible
    STATUS current
    DESCRIPTION "Entry for cwsPmBasicCurrent24hRxOpticalPowerTable."
    INDEX { cwsPmPtpBasicInstancesInstanceName, cwsPmBasicCurrent24hOpticalPowerChannelNumber, cwsPmBasicCurrent24hRxOpticalPowerTableSnmpKey }
    ::= { cwsPmBasicCurrent24hRxOpticalPowerTable 1 }

CwsPmBasicCurrent24hRxOpticalPowerEntry ::= SEQUENCE { 
    cwsPmBasicCurrent24hRxOpticalPowerTableSnmpKey Integer32,
    cwsPmBasicCurrent24hRxOpticalPowerActual Decimal3Dig,
    cwsPmBasicCurrent24hRxOpticalPowerMinimum Decimal3Dig,
    cwsPmBasicCurrent24hRxOpticalPowerMaximum Decimal3Dig,
    cwsPmBasicCurrent24hRxOpticalPowerAverage Decimal3Dig 
}

cwsPmBasicCurrent24hRxOpticalPowerTableSnmpKey OBJECT-TYPE
    SYNTAX Integer32(0..2147483647)
    MAX-ACCESS not-accessible
    STATUS current
    DESCRIPTION "Unique key for cwsPmBasicCurrent24hRxOpticalPower"
    ::= { cwsPmBasicCurrent24hRxOpticalPowerEntry 1 }

cwsPmBasicCurrent24hRxOpticalPowerActual OBJECT-TYPE
    SYNTAX Decimal3Dig
    MAX-ACCESS read-write
    STATUS current
    DESCRIPTION "Actual power reading."
    ::= { cwsPmBasicCurrent24hRxOpticalPowerEntry 2 }

cwsPmBasicCurrent24hRxOpticalPowerMinimum OBJECT-TYPE
    SYNTAX Decimal3Dig
    MAX-ACCESS read-write
    STATUS current
    DESCRIPTION "Minimum power reading."
    ::= { cwsPmBasicCurrent24hRxOpticalPowerEntry 3 }

cwsPmBasicCurrent24hRxOpticalPowerMaximum OBJECT-TYPE
    SYNTAX Decimal3Dig
    MAX-ACCESS read-write
    STATUS current
    DESCRIPTION "Maximum power reading."
    ::= { cwsPmBasicCurrent24hRxOpticalPowerEntry 4 }

cwsPmBasicCurrent24hRxOpticalPowerAverage OBJECT-TYPE
    SYNTAX Decimal3Dig
    MAX-ACCESS read-write
    STATUS current
    DESCRIPTION "Average power reading."
    ::= { cwsPmBasicCurrent24hRxOpticalPowerEntry 5 }

cwsPmBasicCurrent24hTxOpticalPowerTable OBJECT-TYPE
    SYNTAX SEQUENCE OF CwsPmBasicCurrent24hTxOpticalPowerEntry
    MAX-ACCESS not-accessible
    STATUS current
    DESCRIPTION "Tx power reading."
    ::= { cienaWsPmMIB 76 }

cwsPmBasicCurrent24hTxOpticalPowerEntry OBJECT-TYPE
    SYNTAX CwsPmBasicCurrent24hTxOpticalPowerEntry
    MAX-ACCESS not-accessible
    STATUS current
    DESCRIPTION "Entry for cwsPmBasicCurrent24hTxOpticalPowerTable."
    INDEX { cwsPmPtpBasicInstancesInstanceName, cwsPmBasicCurrent24hOpticalPowerChannelNumber, cwsPmBasicCurrent24hTxOpticalPowerTableSnmpKey }
    ::= { cwsPmBasicCurrent24hTxOpticalPowerTable 1 }

CwsPmBasicCurrent24hTxOpticalPowerEntry ::= SEQUENCE { 
    cwsPmBasicCurrent24hTxOpticalPowerTableSnmpKey Integer32,
    cwsPmBasicCurrent24hTxOpticalPowerActual Decimal3Dig,
    cwsPmBasicCurrent24hTxOpticalPowerMinimum Decimal3Dig,
    cwsPmBasicCurrent24hTxOpticalPowerMaximum Decimal3Dig,
    cwsPmBasicCurrent24hTxOpticalPowerAverage Decimal3Dig 
}

cwsPmBasicCurrent24hTxOpticalPowerTableSnmpKey OBJECT-TYPE
    SYNTAX Integer32(0..2147483647)
    MAX-ACCESS not-accessible
    STATUS current
    DESCRIPTION "Unique key for cwsPmBasicCurrent24hTxOpticalPower"
    ::= { cwsPmBasicCurrent24hTxOpticalPowerEntry 1 }

cwsPmBasicCurrent24hTxOpticalPowerActual OBJECT-TYPE
    SYNTAX Decimal3Dig
    MAX-ACCESS read-write
    STATUS current
    DESCRIPTION "Actual power reading."
    ::= { cwsPmBasicCurrent24hTxOpticalPowerEntry 2 }

cwsPmBasicCurrent24hTxOpticalPowerMinimum OBJECT-TYPE
    SYNTAX Decimal3Dig
    MAX-ACCESS read-write
    STATUS current
    DESCRIPTION "Minimum power reading."
    ::= { cwsPmBasicCurrent24hTxOpticalPowerEntry 3 }

cwsPmBasicCurrent24hTxOpticalPowerMaximum OBJECT-TYPE
    SYNTAX Decimal3Dig
    MAX-ACCESS read-write
    STATUS current
    DESCRIPTION "Maximum power reading."
    ::= { cwsPmBasicCurrent24hTxOpticalPowerEntry 4 }

cwsPmBasicCurrent24hTxOpticalPowerAverage OBJECT-TYPE
    SYNTAX Decimal3Dig
    MAX-ACCESS read-write
    STATUS current
    DESCRIPTION "Average power reading."
    ::= { cwsPmBasicCurrent24hTxOpticalPowerEntry 5 }

cwsPmBasicCurrent24hRxChannelPowerTable OBJECT-TYPE
    SYNTAX SEQUENCE OF CwsPmBasicCurrent24hRxChannelPowerEntry
    MAX-ACCESS not-accessible
    STATUS current
    DESCRIPTION "Rx power reading."
    ::= { cienaWsPmMIB 77 }

cwsPmBasicCurrent24hRxChannelPowerEntry OBJECT-TYPE
    SYNTAX CwsPmBasicCurrent24hRxChannelPowerEntry
    MAX-ACCESS not-accessible
    STATUS current
    DESCRIPTION "Entry for cwsPmBasicCurrent24hRxChannelPowerTable."
    INDEX { cwsPmPtpBasicInstancesInstanceName, cwsPmBasicCurrent24hRxChannelPowerTableSnmpKey }
    ::= { cwsPmBasicCurrent24hRxChannelPowerTable 1 }

CwsPmBasicCurrent24hRxChannelPowerEntry ::= SEQUENCE { 
    cwsPmBasicCurrent24hRxChannelPowerTableSnmpKey Integer32,
    cwsPmBasicCurrent24hRxChannelPowerActual Decimal3Dig,
    cwsPmBasicCurrent24hRxChannelPowerMinimum Decimal3Dig,
    cwsPmBasicCurrent24hRxChannelPowerMaximum Decimal3Dig,
    cwsPmBasicCurrent24hRxChannelPowerAverage Decimal3Dig 
}

cwsPmBasicCurrent24hRxChannelPowerTableSnmpKey OBJECT-TYPE
    SYNTAX Integer32(0..2147483647)
    MAX-ACCESS not-accessible
    STATUS current
    DESCRIPTION "Unique key for cwsPmBasicCurrent24hRxChannelPower"
    ::= { cwsPmBasicCurrent24hRxChannelPowerEntry 1 }

cwsPmBasicCurrent24hRxChannelPowerActual OBJECT-TYPE
    SYNTAX Decimal3Dig
    MAX-ACCESS read-write
    STATUS current
    DESCRIPTION "Actual power reading."
    ::= { cwsPmBasicCurrent24hRxChannelPowerEntry 2 }

cwsPmBasicCurrent24hRxChannelPowerMinimum OBJECT-TYPE
    SYNTAX Decimal3Dig
    MAX-ACCESS read-write
    STATUS current
    DESCRIPTION "Minimum power reading."
    ::= { cwsPmBasicCurrent24hRxChannelPowerEntry 3 }

cwsPmBasicCurrent24hRxChannelPowerMaximum OBJECT-TYPE
    SYNTAX Decimal3Dig
    MAX-ACCESS read-write
    STATUS current
    DESCRIPTION "Maximum power reading."
    ::= { cwsPmBasicCurrent24hRxChannelPowerEntry 4 }

cwsPmBasicCurrent24hRxChannelPowerAverage OBJECT-TYPE
    SYNTAX Decimal3Dig
    MAX-ACCESS read-write
    STATUS current
    DESCRIPTION "Average power reading."
    ::= { cwsPmBasicCurrent24hRxChannelPowerEntry 5 }

cwsPmBasicHistoryBinsTable OBJECT-TYPE
    SYNTAX SEQUENCE OF CwsPmBasicHistoryBinsEntry
    MAX-ACCESS not-accessible
    STATUS current
    DESCRIPTION "Performance Monitoring instance for port."
    ::= { cienaWsPmMIB 78 }

cwsPmBasicHistoryBinsEntry OBJECT-TYPE
    SYNTAX CwsPmBasicHistoryBinsEntry
    MAX-ACCESS not-accessible
    STATUS current
    DESCRIPTION "Entry for cwsPmBasicHistoryBinsTable."
    INDEX { cwsPmPtpBasicInstancesInstanceName, cwsPmBasicHistoryBinsBinNumber }
    ::= { cwsPmBasicHistoryBinsTable 1 }

CwsPmBasicHistoryBinsEntry ::= SEQUENCE { 
    cwsPmBasicHistoryBinsBinNumber Integer32 
}

cwsPmBasicHistoryBinsBinNumber OBJECT-TYPE
    SYNTAX Integer32(0..2147483647)
    MAX-ACCESS read-only
    STATUS current
    DESCRIPTION "Unique, logical ID of the port."
    ::= { cwsPmBasicHistoryBinsEntry 1 }

cwsPmBasicHistoryStateTable OBJECT-TYPE
    SYNTAX SEQUENCE OF CwsPmBasicHistoryStateEntry
    MAX-ACCESS not-accessible
    STATUS current
    DESCRIPTION "PM bin state."
    ::= { cienaWsPmMIB 79 }

cwsPmBasicHistoryStateEntry OBJECT-TYPE
    SYNTAX CwsPmBasicHistoryStateEntry
    MAX-ACCESS not-accessible
    STATUS current
    DESCRIPTION "Entry for cwsPmBasicHistoryStateTable."
    INDEX { cwsPmPtpBasicInstancesInstanceName, cwsPmBasicHistoryBinsBinNumber, cwsPmBasicHistoryStateTableSnmpKey }
    ::= { cwsPmBasicHistoryStateTable 1 }

CwsPmBasicHistoryStateEntry ::= SEQUENCE { 
    cwsPmBasicHistoryStateTableSnmpKey Integer32,
    cwsPmBasicHistoryStateStartDateTime StringMaxl32,
    cwsPmBasicHistoryStateEndDateTime StringMaxl32,
    cwsPmBasicHistoryStateState PmBinState 
}

cwsPmBasicHistoryStateTableSnmpKey OBJECT-TYPE
    SYNTAX Integer32(0..2147483647)
    MAX-ACCESS not-accessible
    STATUS current
    DESCRIPTION "Unique key for cwsPmBasicHistoryState"
    ::= { cwsPmBasicHistoryStateEntry 1 }

cwsPmBasicHistoryStateStartDateTime OBJECT-TYPE
    SYNTAX StringMaxl32
    MAX-ACCESS read-write
    STATUS current
    DESCRIPTION "Start date and time."
    ::= { cwsPmBasicHistoryStateEntry 2 }

cwsPmBasicHistoryStateEndDateTime OBJECT-TYPE
    SYNTAX StringMaxl32
    MAX-ACCESS read-write
    STATUS current
    DESCRIPTION "End date and time."
    ::= { cwsPmBasicHistoryStateEntry 3 }

cwsPmBasicHistoryStateState OBJECT-TYPE
    SYNTAX PmBinState
    MAX-ACCESS read-write
    STATUS current
    DESCRIPTION "The PM bin state."
    ::= { cwsPmBasicHistoryStateEntry 4 }

cwsPmBasicHistoryStatisticsTable OBJECT-TYPE
    SYNTAX SEQUENCE OF CwsPmBasicHistoryStatisticsEntry
    MAX-ACCESS not-accessible
    STATUS current
    DESCRIPTION "Statistics data."
    ::= { cienaWsPmMIB 80 }

cwsPmBasicHistoryStatisticsEntry OBJECT-TYPE
    SYNTAX CwsPmBasicHistoryStatisticsEntry
    MAX-ACCESS not-accessible
    STATUS current
    DESCRIPTION "Entry for cwsPmBasicHistoryStatisticsTable."
    INDEX { cwsPmPtpBasicInstancesInstanceName, cwsPmBasicHistoryBinsBinNumber, cwsPmBasicHistoryStatisticsTableSnmpKey }
    ::= { cwsPmBasicHistoryStatisticsTable 1 }

CwsPmBasicHistoryStatisticsEntry ::= SEQUENCE { 
    cwsPmBasicHistoryStatisticsTableSnmpKey Integer32,
    cwsPmBasicHistoryStatisticsNumberOfChannels Unsigned32 
}

cwsPmBasicHistoryStatisticsTableSnmpKey OBJECT-TYPE
    SYNTAX Integer32(0..2147483647)
    MAX-ACCESS not-accessible
    STATUS current
    DESCRIPTION "Unique key for cwsPmBasicHistoryStatistics"
    ::= { cwsPmBasicHistoryStatisticsEntry 1 }

cwsPmBasicHistoryStatisticsNumberOfChannels OBJECT-TYPE
    SYNTAX Unsigned32
    MAX-ACCESS read-only
    STATUS current
    DESCRIPTION "Number of channels."
    ::= { cwsPmBasicHistoryStatisticsEntry 2 }

cwsPmBasicHistoryOpticalPowerTable OBJECT-TYPE
    SYNTAX SEQUENCE OF CwsPmBasicHistoryOpticalPowerEntry
    MAX-ACCESS not-accessible
    STATUS current
    DESCRIPTION "statistics for a PTP channel."
    ::= { cienaWsPmMIB 81 }

cwsPmBasicHistoryOpticalPowerEntry OBJECT-TYPE
    SYNTAX CwsPmBasicHistoryOpticalPowerEntry
    MAX-ACCESS not-accessible
    STATUS current
    DESCRIPTION "Entry for cwsPmBasicHistoryOpticalPowerTable."
    INDEX { cwsPmPtpBasicInstancesInstanceName, cwsPmBasicHistoryBinsBinNumber, cwsPmBasicHistoryOpticalPowerChannelNumber }
    ::= { cwsPmBasicHistoryOpticalPowerTable 1 }

CwsPmBasicHistoryOpticalPowerEntry ::= SEQUENCE { 
    cwsPmBasicHistoryOpticalPowerChannelNumber Integer32 
}

cwsPmBasicHistoryOpticalPowerChannelNumber OBJECT-TYPE
    SYNTAX Integer32(0..2147483647)
    MAX-ACCESS read-only
    STATUS current
    DESCRIPTION "Channel number."
    ::= { cwsPmBasicHistoryOpticalPowerEntry 1 }

cwsPmBasicHistoryRxOpticalPowerTable OBJECT-TYPE
    SYNTAX SEQUENCE OF CwsPmBasicHistoryRxOpticalPowerEntry
    MAX-ACCESS not-accessible
    STATUS current
    DESCRIPTION "Rx power reading."
    ::= { cienaWsPmMIB 82 }

cwsPmBasicHistoryRxOpticalPowerEntry OBJECT-TYPE
    SYNTAX CwsPmBasicHistoryRxOpticalPowerEntry
    MAX-ACCESS not-accessible
    STATUS current
    DESCRIPTION "Entry for cwsPmBasicHistoryRxOpticalPowerTable."
    INDEX { cwsPmPtpBasicInstancesInstanceName, cwsPmBasicHistoryBinsBinNumber, cwsPmBasicHistoryOpticalPowerChannelNumber, cwsPmBasicHistoryRxOpticalPowerTableSnmpKey }
    ::= { cwsPmBasicHistoryRxOpticalPowerTable 1 }

CwsPmBasicHistoryRxOpticalPowerEntry ::= SEQUENCE { 
    cwsPmBasicHistoryRxOpticalPowerTableSnmpKey Integer32,
    cwsPmBasicHistoryRxOpticalPowerActual Decimal3Dig,
    cwsPmBasicHistoryRxOpticalPowerMinimum Decimal3Dig,
    cwsPmBasicHistoryRxOpticalPowerMaximum Decimal3Dig,
    cwsPmBasicHistoryRxOpticalPowerAverage Decimal3Dig 
}

cwsPmBasicHistoryRxOpticalPowerTableSnmpKey OBJECT-TYPE
    SYNTAX Integer32(0..2147483647)
    MAX-ACCESS not-accessible
    STATUS current
    DESCRIPTION "Unique key for cwsPmBasicHistoryRxOpticalPower"
    ::= { cwsPmBasicHistoryRxOpticalPowerEntry 1 }

cwsPmBasicHistoryRxOpticalPowerActual OBJECT-TYPE
    SYNTAX Decimal3Dig
    MAX-ACCESS read-write
    STATUS current
    DESCRIPTION "Actual power reading."
    ::= { cwsPmBasicHistoryRxOpticalPowerEntry 2 }

cwsPmBasicHistoryRxOpticalPowerMinimum OBJECT-TYPE
    SYNTAX Decimal3Dig
    MAX-ACCESS read-write
    STATUS current
    DESCRIPTION "Minimum power reading."
    ::= { cwsPmBasicHistoryRxOpticalPowerEntry 3 }

cwsPmBasicHistoryRxOpticalPowerMaximum OBJECT-TYPE
    SYNTAX Decimal3Dig
    MAX-ACCESS read-write
    STATUS current
    DESCRIPTION "Maximum power reading."
    ::= { cwsPmBasicHistoryRxOpticalPowerEntry 4 }

cwsPmBasicHistoryRxOpticalPowerAverage OBJECT-TYPE
    SYNTAX Decimal3Dig
    MAX-ACCESS read-write
    STATUS current
    DESCRIPTION "Average power reading."
    ::= { cwsPmBasicHistoryRxOpticalPowerEntry 5 }

cwsPmBasicHistoryTxOpticalPowerTable OBJECT-TYPE
    SYNTAX SEQUENCE OF CwsPmBasicHistoryTxOpticalPowerEntry
    MAX-ACCESS not-accessible
    STATUS current
    DESCRIPTION "Tx power reading."
    ::= { cienaWsPmMIB 83 }

cwsPmBasicHistoryTxOpticalPowerEntry OBJECT-TYPE
    SYNTAX CwsPmBasicHistoryTxOpticalPowerEntry
    MAX-ACCESS not-accessible
    STATUS current
    DESCRIPTION "Entry for cwsPmBasicHistoryTxOpticalPowerTable."
    INDEX { cwsPmPtpBasicInstancesInstanceName, cwsPmBasicHistoryBinsBinNumber, cwsPmBasicHistoryOpticalPowerChannelNumber, cwsPmBasicHistoryTxOpticalPowerTableSnmpKey }
    ::= { cwsPmBasicHistoryTxOpticalPowerTable 1 }

CwsPmBasicHistoryTxOpticalPowerEntry ::= SEQUENCE { 
    cwsPmBasicHistoryTxOpticalPowerTableSnmpKey Integer32,
    cwsPmBasicHistoryTxOpticalPowerActual Decimal3Dig,
    cwsPmBasicHistoryTxOpticalPowerMinimum Decimal3Dig,
    cwsPmBasicHistoryTxOpticalPowerMaximum Decimal3Dig,
    cwsPmBasicHistoryTxOpticalPowerAverage Decimal3Dig 
}

cwsPmBasicHistoryTxOpticalPowerTableSnmpKey OBJECT-TYPE
    SYNTAX Integer32(0..2147483647)
    MAX-ACCESS not-accessible
    STATUS current
    DESCRIPTION "Unique key for cwsPmBasicHistoryTxOpticalPower"
    ::= { cwsPmBasicHistoryTxOpticalPowerEntry 1 }

cwsPmBasicHistoryTxOpticalPowerActual OBJECT-TYPE
    SYNTAX Decimal3Dig
    MAX-ACCESS read-write
    STATUS current
    DESCRIPTION "Actual power reading."
    ::= { cwsPmBasicHistoryTxOpticalPowerEntry 2 }

cwsPmBasicHistoryTxOpticalPowerMinimum OBJECT-TYPE
    SYNTAX Decimal3Dig
    MAX-ACCESS read-write
    STATUS current
    DESCRIPTION "Minimum power reading."
    ::= { cwsPmBasicHistoryTxOpticalPowerEntry 3 }

cwsPmBasicHistoryTxOpticalPowerMaximum OBJECT-TYPE
    SYNTAX Decimal3Dig
    MAX-ACCESS read-write
    STATUS current
    DESCRIPTION "Maximum power reading."
    ::= { cwsPmBasicHistoryTxOpticalPowerEntry 4 }

cwsPmBasicHistoryTxOpticalPowerAverage OBJECT-TYPE
    SYNTAX Decimal3Dig
    MAX-ACCESS read-write
    STATUS current
    DESCRIPTION "Average power reading."
    ::= { cwsPmBasicHistoryTxOpticalPowerEntry 5 }

cwsPmBasicHistoryTxChannelPowerTable OBJECT-TYPE
    SYNTAX SEQUENCE OF CwsPmBasicHistoryTxChannelPowerEntry
    MAX-ACCESS not-accessible
    STATUS current
    DESCRIPTION "Rx power reading."
    ::= { cienaWsPmMIB 84 }

cwsPmBasicHistoryTxChannelPowerEntry OBJECT-TYPE
    SYNTAX CwsPmBasicHistoryTxChannelPowerEntry
    MAX-ACCESS not-accessible
    STATUS current
    DESCRIPTION "Entry for cwsPmBasicHistoryTxChannelPowerTable."
    INDEX { cwsPmPtpBasicInstancesInstanceName, cwsPmBasicHistoryBinsBinNumber, cwsPmBasicHistoryTxChannelPowerTableSnmpKey }
    ::= { cwsPmBasicHistoryTxChannelPowerTable 1 }

CwsPmBasicHistoryTxChannelPowerEntry ::= SEQUENCE { 
    cwsPmBasicHistoryTxChannelPowerTableSnmpKey Integer32,
    cwsPmBasicHistoryTxChannelPowerActual Decimal3Dig,
    cwsPmBasicHistoryTxChannelPowerMinimum Decimal3Dig,
    cwsPmBasicHistoryTxChannelPowerMaximum Decimal3Dig,
    cwsPmBasicHistoryTxChannelPowerAverage Decimal3Dig 
}

cwsPmBasicHistoryTxChannelPowerTableSnmpKey OBJECT-TYPE
    SYNTAX Integer32(0..2147483647)
    MAX-ACCESS not-accessible
    STATUS current
    DESCRIPTION "Unique key for cwsPmBasicHistoryTxChannelPower"
    ::= { cwsPmBasicHistoryTxChannelPowerEntry 1 }

cwsPmBasicHistoryTxChannelPowerActual OBJECT-TYPE
    SYNTAX Decimal3Dig
    MAX-ACCESS read-write
    STATUS current
    DESCRIPTION "Actual power reading."
    ::= { cwsPmBasicHistoryTxChannelPowerEntry 2 }

cwsPmBasicHistoryTxChannelPowerMinimum OBJECT-TYPE
    SYNTAX Decimal3Dig
    MAX-ACCESS read-write
    STATUS current
    DESCRIPTION "Minimum power reading."
    ::= { cwsPmBasicHistoryTxChannelPowerEntry 3 }

cwsPmBasicHistoryTxChannelPowerMaximum OBJECT-TYPE
    SYNTAX Decimal3Dig
    MAX-ACCESS read-write
    STATUS current
    DESCRIPTION "Maximum power reading."
    ::= { cwsPmBasicHistoryTxChannelPowerEntry 4 }

cwsPmBasicHistoryTxChannelPowerAverage OBJECT-TYPE
    SYNTAX Decimal3Dig
    MAX-ACCESS read-write
    STATUS current
    DESCRIPTION "Average power reading."
    ::= { cwsPmBasicHistoryTxChannelPowerEntry 5 }

cwsPmBasicHistory24hIdTable OBJECT-TYPE
    SYNTAX SEQUENCE OF CwsPmBasicHistory24hIdEntry
    MAX-ACCESS not-accessible
    STATUS current
    DESCRIPTION "PM Bin identification."
    ::= { cienaWsPmMIB 85 }

cwsPmBasicHistory24hIdEntry OBJECT-TYPE
    SYNTAX CwsPmBasicHistory24hIdEntry
    MAX-ACCESS not-accessible
    STATUS current
    DESCRIPTION "Entry for cwsPmBasicHistory24hIdTable."
    INDEX { cwsPmPtpBasicInstancesInstanceName, cwsPmBasicHistory24hIdTableSnmpKey }
    ::= { cwsPmBasicHistory24hIdTable 1 }

CwsPmBasicHistory24hIdEntry ::= SEQUENCE { 
    cwsPmBasicHistory24hIdTableSnmpKey Integer32,
    cwsPmBasicHistory24hIdBinNumber Unsigned32,
    cwsPmBasicHistory24hIdBinName StringMaxl32 
}

cwsPmBasicHistory24hIdTableSnmpKey OBJECT-TYPE
    SYNTAX Integer32(0..2147483647)
    MAX-ACCESS not-accessible
    STATUS current
    DESCRIPTION "Unique key for cwsPmBasicHistory24hId"
    ::= { cwsPmBasicHistory24hIdEntry 1 }

cwsPmBasicHistory24hIdBinNumber OBJECT-TYPE
    SYNTAX Unsigned32
    MAX-ACCESS read-write
    STATUS current
    DESCRIPTION "The PM bin number."
    ::= { cwsPmBasicHistory24hIdEntry 2 }

cwsPmBasicHistory24hIdBinName OBJECT-TYPE
    SYNTAX StringMaxl32
    MAX-ACCESS read-write
    STATUS current
    DESCRIPTION "The PM bin name."
    ::= { cwsPmBasicHistory24hIdEntry 3 }

cwsPmBasicHistory24hStateTable OBJECT-TYPE
    SYNTAX SEQUENCE OF CwsPmBasicHistory24hStateEntry
    MAX-ACCESS not-accessible
    STATUS current
    DESCRIPTION "PM bin state."
    ::= { cienaWsPmMIB 86 }

cwsPmBasicHistory24hStateEntry OBJECT-TYPE
    SYNTAX CwsPmBasicHistory24hStateEntry
    MAX-ACCESS not-accessible
    STATUS current
    DESCRIPTION "Entry for cwsPmBasicHistory24hStateTable."
    INDEX { cwsPmPtpBasicInstancesInstanceName, cwsPmBasicHistory24hStateTableSnmpKey }
    ::= { cwsPmBasicHistory24hStateTable 1 }

CwsPmBasicHistory24hStateEntry ::= SEQUENCE { 
    cwsPmBasicHistory24hStateTableSnmpKey Integer32,
    cwsPmBasicHistory24hStateStartDateTime StringMaxl32,
    cwsPmBasicHistory24hStateEndDateTime StringMaxl32,
    cwsPmBasicHistory24hStateState PmBinState 
}

cwsPmBasicHistory24hStateTableSnmpKey OBJECT-TYPE
    SYNTAX Integer32(0..2147483647)
    MAX-ACCESS not-accessible
    STATUS current
    DESCRIPTION "Unique key for cwsPmBasicHistory24hState"
    ::= { cwsPmBasicHistory24hStateEntry 1 }

cwsPmBasicHistory24hStateStartDateTime OBJECT-TYPE
    SYNTAX StringMaxl32
    MAX-ACCESS read-write
    STATUS current
    DESCRIPTION "Start date and time."
    ::= { cwsPmBasicHistory24hStateEntry 2 }

cwsPmBasicHistory24hStateEndDateTime OBJECT-TYPE
    SYNTAX StringMaxl32
    MAX-ACCESS read-write
    STATUS current
    DESCRIPTION "End date and time."
    ::= { cwsPmBasicHistory24hStateEntry 3 }

cwsPmBasicHistory24hStateState OBJECT-TYPE
    SYNTAX PmBinState
    MAX-ACCESS read-write
    STATUS current
    DESCRIPTION "The PM bin state."
    ::= { cwsPmBasicHistory24hStateEntry 4 }

cwsPmBasicHistory24hStatisticsTable OBJECT-TYPE
    SYNTAX SEQUENCE OF CwsPmBasicHistory24hStatisticsEntry
    MAX-ACCESS not-accessible
    STATUS current
    DESCRIPTION "Statistics data."
    ::= { cienaWsPmMIB 87 }

cwsPmBasicHistory24hStatisticsEntry OBJECT-TYPE
    SYNTAX CwsPmBasicHistory24hStatisticsEntry
    MAX-ACCESS not-accessible
    STATUS current
    DESCRIPTION "Entry for cwsPmBasicHistory24hStatisticsTable."
    INDEX { cwsPmPtpBasicInstancesInstanceName, cwsPmBasicHistory24hStatisticsTableSnmpKey }
    ::= { cwsPmBasicHistory24hStatisticsTable 1 }

CwsPmBasicHistory24hStatisticsEntry ::= SEQUENCE { 
    cwsPmBasicHistory24hStatisticsTableSnmpKey Integer32,
    cwsPmBasicHistory24hStatisticsNumberOfChannels Unsigned32 
}

cwsPmBasicHistory24hStatisticsTableSnmpKey OBJECT-TYPE
    SYNTAX Integer32(0..2147483647)
    MAX-ACCESS not-accessible
    STATUS current
    DESCRIPTION "Unique key for cwsPmBasicHistory24hStatistics"
    ::= { cwsPmBasicHistory24hStatisticsEntry 1 }

cwsPmBasicHistory24hStatisticsNumberOfChannels OBJECT-TYPE
    SYNTAX Unsigned32
    MAX-ACCESS read-only
    STATUS current
    DESCRIPTION "Number of channels."
    ::= { cwsPmBasicHistory24hStatisticsEntry 2 }

cwsPmBasicHistory24hOpticalPowerTable OBJECT-TYPE
    SYNTAX SEQUENCE OF CwsPmBasicHistory24hOpticalPowerEntry
    MAX-ACCESS not-accessible
    STATUS current
    DESCRIPTION "statistics for a PTP channel."
    ::= { cienaWsPmMIB 88 }

cwsPmBasicHistory24hOpticalPowerEntry OBJECT-TYPE
    SYNTAX CwsPmBasicHistory24hOpticalPowerEntry
    MAX-ACCESS not-accessible
    STATUS current
    DESCRIPTION "Entry for cwsPmBasicHistory24hOpticalPowerTable."
    INDEX { cwsPmPtpBasicInstancesInstanceName, cwsPmBasicHistory24hOpticalPowerChannelNumber }
    ::= { cwsPmBasicHistory24hOpticalPowerTable 1 }

CwsPmBasicHistory24hOpticalPowerEntry ::= SEQUENCE { 
    cwsPmBasicHistory24hOpticalPowerChannelNumber Integer32 
}

cwsPmBasicHistory24hOpticalPowerChannelNumber OBJECT-TYPE
    SYNTAX Integer32(0..2147483647)
    MAX-ACCESS read-only
    STATUS current
    DESCRIPTION "Channel number."
    ::= { cwsPmBasicHistory24hOpticalPowerEntry 1 }

cwsPmBasicHistory24hRxOpticalPowerTable OBJECT-TYPE
    SYNTAX SEQUENCE OF CwsPmBasicHistory24hRxOpticalPowerEntry
    MAX-ACCESS not-accessible
    STATUS current
    DESCRIPTION "Rx power reading."
    ::= { cienaWsPmMIB 89 }

cwsPmBasicHistory24hRxOpticalPowerEntry OBJECT-TYPE
    SYNTAX CwsPmBasicHistory24hRxOpticalPowerEntry
    MAX-ACCESS not-accessible
    STATUS current
    DESCRIPTION "Entry for cwsPmBasicHistory24hRxOpticalPowerTable."
    INDEX { cwsPmPtpBasicInstancesInstanceName, cwsPmBasicHistory24hOpticalPowerChannelNumber, cwsPmBasicHistory24hRxOpticalPowerTableSnmpKey }
    ::= { cwsPmBasicHistory24hRxOpticalPowerTable 1 }

CwsPmBasicHistory24hRxOpticalPowerEntry ::= SEQUENCE { 
    cwsPmBasicHistory24hRxOpticalPowerTableSnmpKey Integer32,
    cwsPmBasicHistory24hRxOpticalPowerActual Decimal3Dig,
    cwsPmBasicHistory24hRxOpticalPowerMinimum Decimal3Dig,
    cwsPmBasicHistory24hRxOpticalPowerMaximum Decimal3Dig,
    cwsPmBasicHistory24hRxOpticalPowerAverage Decimal3Dig 
}

cwsPmBasicHistory24hRxOpticalPowerTableSnmpKey OBJECT-TYPE
    SYNTAX Integer32(0..2147483647)
    MAX-ACCESS not-accessible
    STATUS current
    DESCRIPTION "Unique key for cwsPmBasicHistory24hRxOpticalPower"
    ::= { cwsPmBasicHistory24hRxOpticalPowerEntry 1 }

cwsPmBasicHistory24hRxOpticalPowerActual OBJECT-TYPE
    SYNTAX Decimal3Dig
    MAX-ACCESS read-write
    STATUS current
    DESCRIPTION "Actual power reading."
    ::= { cwsPmBasicHistory24hRxOpticalPowerEntry 2 }

cwsPmBasicHistory24hRxOpticalPowerMinimum OBJECT-TYPE
    SYNTAX Decimal3Dig
    MAX-ACCESS read-write
    STATUS current
    DESCRIPTION "Minimum power reading."
    ::= { cwsPmBasicHistory24hRxOpticalPowerEntry 3 }

cwsPmBasicHistory24hRxOpticalPowerMaximum OBJECT-TYPE
    SYNTAX Decimal3Dig
    MAX-ACCESS read-write
    STATUS current
    DESCRIPTION "Maximum power reading."
    ::= { cwsPmBasicHistory24hRxOpticalPowerEntry 4 }

cwsPmBasicHistory24hRxOpticalPowerAverage OBJECT-TYPE
    SYNTAX Decimal3Dig
    MAX-ACCESS read-write
    STATUS current
    DESCRIPTION "Average power reading."
    ::= { cwsPmBasicHistory24hRxOpticalPowerEntry 5 }

cwsPmBasicHistory24hTxOpticalPowerTable OBJECT-TYPE
    SYNTAX SEQUENCE OF CwsPmBasicHistory24hTxOpticalPowerEntry
    MAX-ACCESS not-accessible
    STATUS current
    DESCRIPTION "Tx power reading."
    ::= { cienaWsPmMIB 90 }

cwsPmBasicHistory24hTxOpticalPowerEntry OBJECT-TYPE
    SYNTAX CwsPmBasicHistory24hTxOpticalPowerEntry
    MAX-ACCESS not-accessible
    STATUS current
    DESCRIPTION "Entry for cwsPmBasicHistory24hTxOpticalPowerTable."
    INDEX { cwsPmPtpBasicInstancesInstanceName, cwsPmBasicHistory24hOpticalPowerChannelNumber, cwsPmBasicHistory24hTxOpticalPowerTableSnmpKey }
    ::= { cwsPmBasicHistory24hTxOpticalPowerTable 1 }

CwsPmBasicHistory24hTxOpticalPowerEntry ::= SEQUENCE { 
    cwsPmBasicHistory24hTxOpticalPowerTableSnmpKey Integer32,
    cwsPmBasicHistory24hTxOpticalPowerActual Decimal3Dig,
    cwsPmBasicHistory24hTxOpticalPowerMinimum Decimal3Dig,
    cwsPmBasicHistory24hTxOpticalPowerMaximum Decimal3Dig,
    cwsPmBasicHistory24hTxOpticalPowerAverage Decimal3Dig 
}

cwsPmBasicHistory24hTxOpticalPowerTableSnmpKey OBJECT-TYPE
    SYNTAX Integer32(0..2147483647)
    MAX-ACCESS not-accessible
    STATUS current
    DESCRIPTION "Unique key for cwsPmBasicHistory24hTxOpticalPower"
    ::= { cwsPmBasicHistory24hTxOpticalPowerEntry 1 }

cwsPmBasicHistory24hTxOpticalPowerActual OBJECT-TYPE
    SYNTAX Decimal3Dig
    MAX-ACCESS read-write
    STATUS current
    DESCRIPTION "Actual power reading."
    ::= { cwsPmBasicHistory24hTxOpticalPowerEntry 2 }

cwsPmBasicHistory24hTxOpticalPowerMinimum OBJECT-TYPE
    SYNTAX Decimal3Dig
    MAX-ACCESS read-write
    STATUS current
    DESCRIPTION "Minimum power reading."
    ::= { cwsPmBasicHistory24hTxOpticalPowerEntry 3 }

cwsPmBasicHistory24hTxOpticalPowerMaximum OBJECT-TYPE
    SYNTAX Decimal3Dig
    MAX-ACCESS read-write
    STATUS current
    DESCRIPTION "Maximum power reading."
    ::= { cwsPmBasicHistory24hTxOpticalPowerEntry 4 }

cwsPmBasicHistory24hTxOpticalPowerAverage OBJECT-TYPE
    SYNTAX Decimal3Dig
    MAX-ACCESS read-write
    STATUS current
    DESCRIPTION "Average power reading."
    ::= { cwsPmBasicHistory24hTxOpticalPowerEntry 5 }

cwsPmBasicHistory24hRxChannelPowerTable OBJECT-TYPE
    SYNTAX SEQUENCE OF CwsPmBasicHistory24hRxChannelPowerEntry
    MAX-ACCESS not-accessible
    STATUS current
    DESCRIPTION "Rx power reading."
    ::= { cienaWsPmMIB 91 }

cwsPmBasicHistory24hRxChannelPowerEntry OBJECT-TYPE
    SYNTAX CwsPmBasicHistory24hRxChannelPowerEntry
    MAX-ACCESS not-accessible
    STATUS current
    DESCRIPTION "Entry for cwsPmBasicHistory24hRxChannelPowerTable."
    INDEX { cwsPmPtpBasicInstancesInstanceName, cwsPmBasicHistory24hRxChannelPowerTableSnmpKey }
    ::= { cwsPmBasicHistory24hRxChannelPowerTable 1 }

CwsPmBasicHistory24hRxChannelPowerEntry ::= SEQUENCE { 
    cwsPmBasicHistory24hRxChannelPowerTableSnmpKey Integer32,
    cwsPmBasicHistory24hRxChannelPowerActual Decimal3Dig,
    cwsPmBasicHistory24hRxChannelPowerMinimum Decimal3Dig,
    cwsPmBasicHistory24hRxChannelPowerMaximum Decimal3Dig,
    cwsPmBasicHistory24hRxChannelPowerAverage Decimal3Dig 
}

cwsPmBasicHistory24hRxChannelPowerTableSnmpKey OBJECT-TYPE
    SYNTAX Integer32(0..2147483647)
    MAX-ACCESS not-accessible
    STATUS current
    DESCRIPTION "Unique key for cwsPmBasicHistory24hRxChannelPower"
    ::= { cwsPmBasicHistory24hRxChannelPowerEntry 1 }

cwsPmBasicHistory24hRxChannelPowerActual OBJECT-TYPE
    SYNTAX Decimal3Dig
    MAX-ACCESS read-write
    STATUS current
    DESCRIPTION "Actual power reading."
    ::= { cwsPmBasicHistory24hRxChannelPowerEntry 2 }

cwsPmBasicHistory24hRxChannelPowerMinimum OBJECT-TYPE
    SYNTAX Decimal3Dig
    MAX-ACCESS read-write
    STATUS current
    DESCRIPTION "Minimum power reading."
    ::= { cwsPmBasicHistory24hRxChannelPowerEntry 3 }

cwsPmBasicHistory24hRxChannelPowerMaximum OBJECT-TYPE
    SYNTAX Decimal3Dig
    MAX-ACCESS read-write
    STATUS current
    DESCRIPTION "Maximum power reading."
    ::= { cwsPmBasicHistory24hRxChannelPowerEntry 4 }

cwsPmBasicHistory24hRxChannelPowerAverage OBJECT-TYPE
    SYNTAX Decimal3Dig
    MAX-ACCESS read-write
    STATUS current
    DESCRIPTION "Average power reading."
    ::= { cwsPmBasicHistory24hRxChannelPowerEntry 5 }

cwsPmPtpAdvancedInstancesTable OBJECT-TYPE
    SYNTAX SEQUENCE OF CwsPmPtpAdvancedInstancesEntry
    MAX-ACCESS not-accessible
    STATUS current
    DESCRIPTION "Performance Monitoring instance."
    ::= { cienaWsPmMIB 92 }

cwsPmPtpAdvancedInstancesEntry OBJECT-TYPE
    SYNTAX CwsPmPtpAdvancedInstancesEntry
    MAX-ACCESS not-accessible
    STATUS current
    DESCRIPTION "Entry for cwsPmPtpAdvancedInstancesTable."
    INDEX { cwsPmPtpAdvancedInstancesInstanceName }
    ::= { cwsPmPtpAdvancedInstancesTable 1 }

CwsPmPtpAdvancedInstancesEntry ::= SEQUENCE { 
    cwsPmPtpAdvancedInstancesInstanceName Integer32 
}

cwsPmPtpAdvancedInstancesInstanceName OBJECT-TYPE
    SYNTAX Integer32(0..2147483647)
    MAX-ACCESS read-only
    STATUS current
    DESCRIPTION "Unique name for PM instance."
    ::= { cwsPmPtpAdvancedInstancesEntry 1 }

cwsPmAdvancedIdTable OBJECT-TYPE
    SYNTAX SEQUENCE OF CwsPmAdvancedIdEntry
    MAX-ACCESS not-accessible
    STATUS current
    DESCRIPTION "PM PTP advance instance identification."
    ::= { cienaWsPmMIB 93 }

cwsPmAdvancedIdEntry OBJECT-TYPE
    SYNTAX CwsPmAdvancedIdEntry
    MAX-ACCESS not-accessible
    STATUS current
    DESCRIPTION "Entry for cwsPmAdvancedIdTable."
    INDEX { cwsPmPtpAdvancedInstancesInstanceName, cwsPmAdvancedIdTableSnmpKey }
    ::= { cwsPmAdvancedIdTable 1 }

CwsPmAdvancedIdEntry ::= SEQUENCE { 
    cwsPmAdvancedIdTableSnmpKey Integer32,
    cwsPmAdvancedIdInstanceId Unsigned32,
    cwsPmAdvancedIdInstanceType PmInstanceType,
    cwsPmAdvancedIdProfileType PmProfileType 
}

cwsPmAdvancedIdTableSnmpKey OBJECT-TYPE
    SYNTAX Integer32(0..2147483647)
    MAX-ACCESS not-accessible
    STATUS current
    DESCRIPTION "Unique key for cwsPmAdvancedId"
    ::= { cwsPmAdvancedIdEntry 1 }

cwsPmAdvancedIdInstanceId OBJECT-TYPE
    SYNTAX Unsigned32
    MAX-ACCESS read-write
    STATUS current
    DESCRIPTION "ID of the PM instance."
    ::= { cwsPmAdvancedIdEntry 2 }

cwsPmAdvancedIdInstanceType OBJECT-TYPE
    SYNTAX PmInstanceType
    MAX-ACCESS read-write
    STATUS current
    DESCRIPTION "The PM instance type."
    ::= { cwsPmAdvancedIdEntry 3 }

cwsPmAdvancedIdProfileType OBJECT-TYPE
    SYNTAX PmProfileType
    MAX-ACCESS read-write
    STATUS current
    DESCRIPTION "The PM profile type."
    ::= { cwsPmAdvancedIdEntry 4 }

cwsPmAdvancedStateTable OBJECT-TYPE
    SYNTAX SEQUENCE OF CwsPmAdvancedStateEntry
    MAX-ACCESS not-accessible
    STATUS current
    DESCRIPTION "Performance Monitoring Instance State."
    ::= { cienaWsPmMIB 94 }

cwsPmAdvancedStateEntry OBJECT-TYPE
    SYNTAX CwsPmAdvancedStateEntry
    MAX-ACCESS not-accessible
    STATUS current
    DESCRIPTION "Entry for cwsPmAdvancedStateTable."
    INDEX { cwsPmPtpAdvancedInstancesInstanceName, cwsPmAdvancedStateTableSnmpKey }
    ::= { cwsPmAdvancedStateTable 1 }

CwsPmAdvancedStateEntry ::= SEQUENCE { 
    cwsPmAdvancedStateTableSnmpKey Integer32,
    cwsPmAdvancedStateAdminState EnabledDisabledEnum,
    cwsPmAdvancedStateOperationalState EnabledDisabledEnum,
    cwsPmAdvancedStateCurrentBinId Unsigned32,
    cwsPmAdvancedStateCollectionStartDateTime StringMaxl64,
    cwsPmAdvancedStateCollectionEndDateTime StringMaxl64 
}

cwsPmAdvancedStateTableSnmpKey OBJECT-TYPE
    SYNTAX Integer32(0..2147483647)
    MAX-ACCESS not-accessible
    STATUS current
    DESCRIPTION "Unique key for cwsPmAdvancedState"
    ::= { cwsPmAdvancedStateEntry 1 }

cwsPmAdvancedStateAdminState OBJECT-TYPE
    SYNTAX EnabledDisabledEnum
    MAX-ACCESS read-write
    STATUS current
    DESCRIPTION "The configured administrative state of the port."
    ::= { cwsPmAdvancedStateEntry 2 }

cwsPmAdvancedStateOperationalState OBJECT-TYPE
    SYNTAX EnabledDisabledEnum
    MAX-ACCESS read-only
    STATUS current
    DESCRIPTION "The operational state of the PM instance."
    ::= { cwsPmAdvancedStateEntry 3 }

cwsPmAdvancedStateCurrentBinId OBJECT-TYPE
    SYNTAX Unsigned32
    MAX-ACCESS read-only
    STATUS current
    DESCRIPTION "The operational state of the PM instance."
    ::= { cwsPmAdvancedStateEntry 4 }

cwsPmAdvancedStateCollectionStartDateTime OBJECT-TYPE
    SYNTAX StringMaxl64
    MAX-ACCESS read-only
    STATUS current
    DESCRIPTION "The PM stats collection starting date and time."
    ::= { cwsPmAdvancedStateEntry 5 }

cwsPmAdvancedStateCollectionEndDateTime OBJECT-TYPE
    SYNTAX StringMaxl64
    MAX-ACCESS read-only
    STATUS current
    DESCRIPTION "The PM stats collection ending date and time."
    ::= { cwsPmAdvancedStateEntry 6 }

cwsPmAdvancedPropertiesTable OBJECT-TYPE
    SYNTAX SEQUENCE OF CwsPmAdvancedPropertiesEntry
    MAX-ACCESS not-accessible
    STATUS current
    DESCRIPTION "PM instance properties."
    ::= { cienaWsPmMIB 95 }

cwsPmAdvancedPropertiesEntry OBJECT-TYPE
    SYNTAX CwsPmAdvancedPropertiesEntry
    MAX-ACCESS not-accessible
    STATUS current
    DESCRIPTION "Entry for cwsPmAdvancedPropertiesTable."
    INDEX { cwsPmPtpAdvancedInstancesInstanceName, cwsPmAdvancedPropertiesTableSnmpKey }
    ::= { cwsPmAdvancedPropertiesTable 1 }

CwsPmAdvancedPropertiesEntry ::= SEQUENCE { 
    cwsPmAdvancedPropertiesTableSnmpKey Integer32,
    cwsPmAdvancedPropertiesConfigurationMode PmConfigurationMode,
    cwsPmAdvancedPropertiesAlignment PmAlignment,
    cwsPmAdvancedPropertiesConfiguredBinCount Unsigned32,
    cwsPmAdvancedPropertiesConfiguredBinDuration Unsigned32 
}

cwsPmAdvancedPropertiesTableSnmpKey OBJECT-TYPE
    SYNTAX Integer32(0..2147483647)
    MAX-ACCESS not-accessible
    STATUS current
    DESCRIPTION "Unique key for cwsPmAdvancedProperties"
    ::= { cwsPmAdvancedPropertiesEntry 1 }

cwsPmAdvancedPropertiesConfigurationMode OBJECT-TYPE
    SYNTAX PmConfigurationMode
    MAX-ACCESS read-write
    STATUS current
    DESCRIPTION "The PM instance configuration mode"
    ::= { cwsPmAdvancedPropertiesEntry 2 }

cwsPmAdvancedPropertiesAlignment OBJECT-TYPE
    SYNTAX PmAlignment
    MAX-ACCESS read-write
    STATUS current
    DESCRIPTION "The PM alignment."
    ::= { cwsPmAdvancedPropertiesEntry 3 }

cwsPmAdvancedPropertiesConfiguredBinCount OBJECT-TYPE
    SYNTAX Unsigned32
    MAX-ACCESS read-write
    STATUS current
    DESCRIPTION "The configured number of history bins."
    ::= { cwsPmAdvancedPropertiesEntry 4 }

cwsPmAdvancedPropertiesConfiguredBinDuration OBJECT-TYPE
    SYNTAX Unsigned32
    MAX-ACCESS read-write
    STATUS current
    DESCRIPTION "The configured PM bin duration in minutes."
    ::= { cwsPmAdvancedPropertiesEntry 5 }

cwsPmAdvancedAttachedInterfaceTable OBJECT-TYPE
    SYNTAX SEQUENCE OF CwsPmAdvancedAttachedInterfaceEntry
    MAX-ACCESS not-accessible
    STATUS current
    DESCRIPTION "Attached interface."
    ::= { cienaWsPmMIB 96 }

cwsPmAdvancedAttachedInterfaceEntry OBJECT-TYPE
    SYNTAX CwsPmAdvancedAttachedInterfaceEntry
    MAX-ACCESS not-accessible
    STATUS current
    DESCRIPTION "Entry for cwsPmAdvancedAttachedInterfaceTable."
    INDEX { cwsPmPtpAdvancedInstancesInstanceName, cwsPmAdvancedAttachedInterfaceTableSnmpKey }
    ::= { cwsPmAdvancedAttachedInterfaceTable 1 }

CwsPmAdvancedAttachedInterfaceEntry ::= SEQUENCE { 
    cwsPmAdvancedAttachedInterfaceTableSnmpKey Integer32,
    cwsPmAdvancedAttachedInterfaceType PmInterfaceType,
    cwsPmAdvancedAttachedInterfaceName StringMaxl32,
    cwsPmAdvancedAttachedInterfaceOperationalState EnabledDisabledEnum 
}

cwsPmAdvancedAttachedInterfaceTableSnmpKey OBJECT-TYPE
    SYNTAX Integer32(0..2147483647)
    MAX-ACCESS not-accessible
    STATUS current
    DESCRIPTION "Unique key for cwsPmAdvancedAttachedInterface"
    ::= { cwsPmAdvancedAttachedInterfaceEntry 1 }

cwsPmAdvancedAttachedInterfaceType OBJECT-TYPE
    SYNTAX PmInterfaceType
    MAX-ACCESS read-write
    STATUS current
    DESCRIPTION "Attached interface type."
    ::= { cwsPmAdvancedAttachedInterfaceEntry 2 }

cwsPmAdvancedAttachedInterfaceName OBJECT-TYPE
    SYNTAX StringMaxl32
    MAX-ACCESS read-write
    STATUS current
    DESCRIPTION "Attached interface name."
    ::= { cwsPmAdvancedAttachedInterfaceEntry 3 }

cwsPmAdvancedAttachedInterfaceOperationalState OBJECT-TYPE
    SYNTAX EnabledDisabledEnum
    MAX-ACCESS read-write
    STATUS current
    DESCRIPTION "Attached interface operational state."
    ::= { cwsPmAdvancedAttachedInterfaceEntry 4 }

cwsPmAdvancedCurrentIdTable OBJECT-TYPE
    SYNTAX SEQUENCE OF CwsPmAdvancedCurrentIdEntry
    MAX-ACCESS not-accessible
    STATUS current
    DESCRIPTION "PM Bin identification."
    ::= { cienaWsPmMIB 97 }

cwsPmAdvancedCurrentIdEntry OBJECT-TYPE
    SYNTAX CwsPmAdvancedCurrentIdEntry
    MAX-ACCESS not-accessible
    STATUS current
    DESCRIPTION "Entry for cwsPmAdvancedCurrentIdTable."
    INDEX { cwsPmPtpAdvancedInstancesInstanceName, cwsPmAdvancedCurrentIdTableSnmpKey }
    ::= { cwsPmAdvancedCurrentIdTable 1 }

CwsPmAdvancedCurrentIdEntry ::= SEQUENCE { 
    cwsPmAdvancedCurrentIdTableSnmpKey Integer32,
    cwsPmAdvancedCurrentIdBinNumber Unsigned32,
    cwsPmAdvancedCurrentIdBinName StringMaxl32 
}

cwsPmAdvancedCurrentIdTableSnmpKey OBJECT-TYPE
    SYNTAX Integer32(0..2147483647)
    MAX-ACCESS not-accessible
    STATUS current
    DESCRIPTION "Unique key for cwsPmAdvancedCurrentId"
    ::= { cwsPmAdvancedCurrentIdEntry 1 }

cwsPmAdvancedCurrentIdBinNumber OBJECT-TYPE
    SYNTAX Unsigned32
    MAX-ACCESS read-write
    STATUS current
    DESCRIPTION "The PM bin number."
    ::= { cwsPmAdvancedCurrentIdEntry 2 }

cwsPmAdvancedCurrentIdBinName OBJECT-TYPE
    SYNTAX StringMaxl32
    MAX-ACCESS read-write
    STATUS current
    DESCRIPTION "The PM bin name."
    ::= { cwsPmAdvancedCurrentIdEntry 3 }

cwsPmAdvancedCurrentStateTable OBJECT-TYPE
    SYNTAX SEQUENCE OF CwsPmAdvancedCurrentStateEntry
    MAX-ACCESS not-accessible
    STATUS current
    DESCRIPTION "PM bin state."
    ::= { cienaWsPmMIB 98 }

cwsPmAdvancedCurrentStateEntry OBJECT-TYPE
    SYNTAX CwsPmAdvancedCurrentStateEntry
    MAX-ACCESS not-accessible
    STATUS current
    DESCRIPTION "Entry for cwsPmAdvancedCurrentStateTable."
    INDEX { cwsPmPtpAdvancedInstancesInstanceName, cwsPmAdvancedCurrentStateTableSnmpKey }
    ::= { cwsPmAdvancedCurrentStateTable 1 }

CwsPmAdvancedCurrentStateEntry ::= SEQUENCE { 
    cwsPmAdvancedCurrentStateTableSnmpKey Integer32,
    cwsPmAdvancedCurrentStateStartDateTime StringMaxl32,
    cwsPmAdvancedCurrentStateClearedDateTime StringMaxl32,
    cwsPmAdvancedCurrentStateState PmBinState 
}

cwsPmAdvancedCurrentStateTableSnmpKey OBJECT-TYPE
    SYNTAX Integer32(0..2147483647)
    MAX-ACCESS not-accessible
    STATUS current
    DESCRIPTION "Unique key for cwsPmAdvancedCurrentState"
    ::= { cwsPmAdvancedCurrentStateEntry 1 }

cwsPmAdvancedCurrentStateStartDateTime OBJECT-TYPE
    SYNTAX StringMaxl32
    MAX-ACCESS read-write
    STATUS current
    DESCRIPTION "Start date and time."
    ::= { cwsPmAdvancedCurrentStateEntry 2 }

cwsPmAdvancedCurrentStateClearedDateTime OBJECT-TYPE
    SYNTAX StringMaxl32
    MAX-ACCESS read-write
    STATUS current
    DESCRIPTION "Cleared date and time."
    ::= { cwsPmAdvancedCurrentStateEntry 3 }

cwsPmAdvancedCurrentStateState OBJECT-TYPE
    SYNTAX PmBinState
    MAX-ACCESS read-write
    STATUS current
    DESCRIPTION "The PM bin state."
    ::= { cwsPmAdvancedCurrentStateEntry 4 }

cwsPmAdvancedCurrentStatisticsTable OBJECT-TYPE
    SYNTAX SEQUENCE OF CwsPmAdvancedCurrentStatisticsEntry
    MAX-ACCESS not-accessible
    STATUS current
    DESCRIPTION "Statistics data."
    ::= { cienaWsPmMIB 99 }

cwsPmAdvancedCurrentStatisticsEntry OBJECT-TYPE
    SYNTAX CwsPmAdvancedCurrentStatisticsEntry
    MAX-ACCESS not-accessible
    STATUS current
    DESCRIPTION "Entry for cwsPmAdvancedCurrentStatisticsTable."
    INDEX { cwsPmPtpAdvancedInstancesInstanceName, cwsPmAdvancedCurrentStatisticsTableSnmpKey }
    ::= { cwsPmAdvancedCurrentStatisticsTable 1 }

CwsPmAdvancedCurrentStatisticsEntry ::= SEQUENCE { 
    cwsPmAdvancedCurrentStatisticsTableSnmpKey Integer32,
    cwsPmAdvancedCurrentStatisticsPostFecBitErrorRate StringSci 
}

cwsPmAdvancedCurrentStatisticsTableSnmpKey OBJECT-TYPE
    SYNTAX Integer32(0..2147483647)
    MAX-ACCESS not-accessible
    STATUS current
    DESCRIPTION "Unique key for cwsPmAdvancedCurrentStatistics"
    ::= { cwsPmAdvancedCurrentStatisticsEntry 1 }

cwsPmAdvancedCurrentStatisticsPostFecBitErrorRate OBJECT-TYPE
    SYNTAX StringSci
    MAX-ACCESS read-only
    STATUS current
    DESCRIPTION "Post-FEC Bit error rate reading."
    ::= { cwsPmAdvancedCurrentStatisticsEntry 2 }

cwsPmPreFecBitErrorRateTable OBJECT-TYPE
    SYNTAX SEQUENCE OF CwsPmPreFecBitErrorRateEntry
    MAX-ACCESS not-accessible
    STATUS current
    DESCRIPTION "Pre-FEC BER counts."
    ::= { cienaWsPmMIB 100 }

cwsPmPreFecBitErrorRateEntry OBJECT-TYPE
    SYNTAX CwsPmPreFecBitErrorRateEntry
    MAX-ACCESS not-accessible
    STATUS current
    DESCRIPTION "Entry for cwsPmPreFecBitErrorRateTable."
    INDEX { cwsPmPtpAdvancedInstancesInstanceName, cwsPmPreFecBitErrorRateTableSnmpKey }
    ::= { cwsPmPreFecBitErrorRateTable 1 }

CwsPmPreFecBitErrorRateEntry ::= SEQUENCE { 
    cwsPmPreFecBitErrorRateTableSnmpKey Integer32,
    cwsPmPreFecBitErrorRateBitErrorRate StringSci,
    cwsPmPreFecBitErrorRateMaximum StringSci 
}

cwsPmPreFecBitErrorRateTableSnmpKey OBJECT-TYPE
    SYNTAX Integer32(0..2147483647)
    MAX-ACCESS not-accessible
    STATUS current
    DESCRIPTION "Unique key for cwsPmPreFecBitErrorRate"
    ::= { cwsPmPreFecBitErrorRateEntry 1 }

cwsPmPreFecBitErrorRateBitErrorRate OBJECT-TYPE
    SYNTAX StringSci
    MAX-ACCESS read-write
    STATUS current
    DESCRIPTION "Bit error rate reading."
    ::= { cwsPmPreFecBitErrorRateEntry 2 }

cwsPmPreFecBitErrorRateMaximum OBJECT-TYPE
    SYNTAX StringSci
    MAX-ACCESS read-write
    STATUS current
    DESCRIPTION "Maximum BER reading."
    ::= { cwsPmPreFecBitErrorRateEntry 3 }

cwsPmAdvancedCurrentQFactorTable OBJECT-TYPE
    SYNTAX SEQUENCE OF CwsPmAdvancedCurrentQFactorEntry
    MAX-ACCESS not-accessible
    STATUS current
    DESCRIPTION "Q-Factor count."
    ::= { cienaWsPmMIB 101 }

cwsPmAdvancedCurrentQFactorEntry OBJECT-TYPE
    SYNTAX CwsPmAdvancedCurrentQFactorEntry
    MAX-ACCESS not-accessible
    STATUS current
    DESCRIPTION "Entry for cwsPmAdvancedCurrentQFactorTable."
    INDEX { cwsPmPtpAdvancedInstancesInstanceName, cwsPmAdvancedCurrentQFactorTableSnmpKey }
    ::= { cwsPmAdvancedCurrentQFactorTable 1 }

CwsPmAdvancedCurrentQFactorEntry ::= SEQUENCE { 
    cwsPmAdvancedCurrentQFactorTableSnmpKey Integer32,
    cwsPmAdvancedCurrentQFactorQFactor Decimal3Dig,
    cwsPmAdvancedCurrentQFactorMinimum Decimal3Dig,
    cwsPmAdvancedCurrentQFactorMaximum Decimal3Dig 
}

cwsPmAdvancedCurrentQFactorTableSnmpKey OBJECT-TYPE
    SYNTAX Integer32(0..2147483647)
    MAX-ACCESS not-accessible
    STATUS current
    DESCRIPTION "Unique key for cwsPmAdvancedCurrentQFactor"
    ::= { cwsPmAdvancedCurrentQFactorEntry 1 }

cwsPmAdvancedCurrentQFactorQFactor OBJECT-TYPE
    SYNTAX Decimal3Dig
    MAX-ACCESS read-write
    STATUS current
    DESCRIPTION "Minimum Q-Factor reading."
    ::= { cwsPmAdvancedCurrentQFactorEntry 2 }

cwsPmAdvancedCurrentQFactorMinimum OBJECT-TYPE
    SYNTAX Decimal3Dig
    MAX-ACCESS read-write
    STATUS current
    DESCRIPTION "Minimum Q-Factor reading."
    ::= { cwsPmAdvancedCurrentQFactorEntry 3 }

cwsPmAdvancedCurrentQFactorMaximum OBJECT-TYPE
    SYNTAX Decimal3Dig
    MAX-ACCESS read-write
    STATUS current
    DESCRIPTION "Maximum Q-Factor reading."
    ::= { cwsPmAdvancedCurrentQFactorEntry 4 }

cwsPmAdvancedCurrentFecErrorTable OBJECT-TYPE
    SYNTAX SEQUENCE OF CwsPmAdvancedCurrentFecErrorEntry
    MAX-ACCESS not-accessible
    STATUS current
    DESCRIPTION "FEC error counts."
    ::= { cienaWsPmMIB 102 }

cwsPmAdvancedCurrentFecErrorEntry OBJECT-TYPE
    SYNTAX CwsPmAdvancedCurrentFecErrorEntry
    MAX-ACCESS not-accessible
    STATUS current
    DESCRIPTION "Entry for cwsPmAdvancedCurrentFecErrorTable."
    INDEX { cwsPmPtpAdvancedInstancesInstanceName, cwsPmAdvancedCurrentFecErrorTableSnmpKey }
    ::= { cwsPmAdvancedCurrentFecErrorTable 1 }

CwsPmAdvancedCurrentFecErrorEntry ::= SEQUENCE { 
    cwsPmAdvancedCurrentFecErrorTableSnmpKey Integer32,
    cwsPmAdvancedCurrentFecErrorFrameErrorCount Counter64,
    cwsPmAdvancedCurrentFecErrorFrameErrorCountSecond Counter64,
    cwsPmAdvancedCurrentFecErrorUncorrectedBlockCount Counter64,
    cwsPmAdvancedCurrentFecErrorHighCorrectionCountSeconds Counter64 
}

cwsPmAdvancedCurrentFecErrorTableSnmpKey OBJECT-TYPE
    SYNTAX Integer32(0..2147483647)
    MAX-ACCESS not-accessible
    STATUS current
    DESCRIPTION "Unique key for cwsPmAdvancedCurrentFecError"
    ::= { cwsPmAdvancedCurrentFecErrorEntry 1 }

cwsPmAdvancedCurrentFecErrorFrameErrorCount OBJECT-TYPE
    SYNTAX Counter64
    MAX-ACCESS read-write
    STATUS current
    DESCRIPTION "FEC Frame error counts."
    ::= { cwsPmAdvancedCurrentFecErrorEntry 2 }

cwsPmAdvancedCurrentFecErrorFrameErrorCountSecond OBJECT-TYPE
    SYNTAX Counter64
    MAX-ACCESS read-write
    STATUS current
    DESCRIPTION "FEC Frame error count second."
    ::= { cwsPmAdvancedCurrentFecErrorEntry 3 }

cwsPmAdvancedCurrentFecErrorUncorrectedBlockCount OBJECT-TYPE
    SYNTAX Counter64
    MAX-ACCESS read-write
    STATUS current
    DESCRIPTION "FEC uncorrected block count."
    ::= { cwsPmAdvancedCurrentFecErrorEntry 4 }

cwsPmAdvancedCurrentFecErrorHighCorrectionCountSeconds OBJECT-TYPE
    SYNTAX Counter64
    MAX-ACCESS read-write
    STATUS current
    DESCRIPTION "FEC high correction count seconds."
    ::= { cwsPmAdvancedCurrentFecErrorEntry 5 }

cwsPmAdvancedCurrent24hIdTable OBJECT-TYPE
    SYNTAX SEQUENCE OF CwsPmAdvancedCurrent24hIdEntry
    MAX-ACCESS not-accessible
    STATUS current
    DESCRIPTION "PM Bin identification."
    ::= { cienaWsPmMIB 103 }

cwsPmAdvancedCurrent24hIdEntry OBJECT-TYPE
    SYNTAX CwsPmAdvancedCurrent24hIdEntry
    MAX-ACCESS not-accessible
    STATUS current
    DESCRIPTION "Entry for cwsPmAdvancedCurrent24hIdTable."
    INDEX { cwsPmPtpAdvancedInstancesInstanceName, cwsPmAdvancedCurrent24hIdTableSnmpKey }
    ::= { cwsPmAdvancedCurrent24hIdTable 1 }

CwsPmAdvancedCurrent24hIdEntry ::= SEQUENCE { 
    cwsPmAdvancedCurrent24hIdTableSnmpKey Integer32,
    cwsPmAdvancedCurrent24hIdBinNumber Unsigned32,
    cwsPmAdvancedCurrent24hIdBinName StringMaxl32 
}

cwsPmAdvancedCurrent24hIdTableSnmpKey OBJECT-TYPE
    SYNTAX Integer32(0..2147483647)
    MAX-ACCESS not-accessible
    STATUS current
    DESCRIPTION "Unique key for cwsPmAdvancedCurrent24hId"
    ::= { cwsPmAdvancedCurrent24hIdEntry 1 }

cwsPmAdvancedCurrent24hIdBinNumber OBJECT-TYPE
    SYNTAX Unsigned32
    MAX-ACCESS read-write
    STATUS current
    DESCRIPTION "The PM bin number."
    ::= { cwsPmAdvancedCurrent24hIdEntry 2 }

cwsPmAdvancedCurrent24hIdBinName OBJECT-TYPE
    SYNTAX StringMaxl32
    MAX-ACCESS read-write
    STATUS current
    DESCRIPTION "The PM bin name."
    ::= { cwsPmAdvancedCurrent24hIdEntry 3 }

cwsPmAdvancedCurrent24hStateTable OBJECT-TYPE
    SYNTAX SEQUENCE OF CwsPmAdvancedCurrent24hStateEntry
    MAX-ACCESS not-accessible
    STATUS current
    DESCRIPTION "PM bin state."
    ::= { cienaWsPmMIB 104 }

cwsPmAdvancedCurrent24hStateEntry OBJECT-TYPE
    SYNTAX CwsPmAdvancedCurrent24hStateEntry
    MAX-ACCESS not-accessible
    STATUS current
    DESCRIPTION "Entry for cwsPmAdvancedCurrent24hStateTable."
    INDEX { cwsPmPtpAdvancedInstancesInstanceName, cwsPmAdvancedCurrent24hStateTableSnmpKey }
    ::= { cwsPmAdvancedCurrent24hStateTable 1 }

CwsPmAdvancedCurrent24hStateEntry ::= SEQUENCE { 
    cwsPmAdvancedCurrent24hStateTableSnmpKey Integer32,
    cwsPmAdvancedCurrent24hStateStartDateTime StringMaxl32,
    cwsPmAdvancedCurrent24hStateClearedDateTime StringMaxl32,
    cwsPmAdvancedCurrent24hStateState PmBinState 
}

cwsPmAdvancedCurrent24hStateTableSnmpKey OBJECT-TYPE
    SYNTAX Integer32(0..2147483647)
    MAX-ACCESS not-accessible
    STATUS current
    DESCRIPTION "Unique key for cwsPmAdvancedCurrent24hState"
    ::= { cwsPmAdvancedCurrent24hStateEntry 1 }

cwsPmAdvancedCurrent24hStateStartDateTime OBJECT-TYPE
    SYNTAX StringMaxl32
    MAX-ACCESS read-write
    STATUS current
    DESCRIPTION "Start date and time."
    ::= { cwsPmAdvancedCurrent24hStateEntry 2 }

cwsPmAdvancedCurrent24hStateClearedDateTime OBJECT-TYPE
    SYNTAX StringMaxl32
    MAX-ACCESS read-write
    STATUS current
    DESCRIPTION "Cleared date and time."
    ::= { cwsPmAdvancedCurrent24hStateEntry 3 }

cwsPmAdvancedCurrent24hStateState OBJECT-TYPE
    SYNTAX PmBinState
    MAX-ACCESS read-write
    STATUS current
    DESCRIPTION "The PM bin state."
    ::= { cwsPmAdvancedCurrent24hStateEntry 4 }

cwsPmAdvancedCurrent24hStatisticsTable OBJECT-TYPE
    SYNTAX SEQUENCE OF CwsPmAdvancedCurrent24hStatisticsEntry
    MAX-ACCESS not-accessible
    STATUS current
    DESCRIPTION "Statistics data."
    ::= { cienaWsPmMIB 105 }

cwsPmAdvancedCurrent24hStatisticsEntry OBJECT-TYPE
    SYNTAX CwsPmAdvancedCurrent24hStatisticsEntry
    MAX-ACCESS not-accessible
    STATUS current
    DESCRIPTION "Entry for cwsPmAdvancedCurrent24hStatisticsTable."
    INDEX { cwsPmPtpAdvancedInstancesInstanceName, cwsPmAdvancedCurrent24hStatisticsTableSnmpKey }
    ::= { cwsPmAdvancedCurrent24hStatisticsTable 1 }

CwsPmAdvancedCurrent24hStatisticsEntry ::= SEQUENCE { 
    cwsPmAdvancedCurrent24hStatisticsTableSnmpKey Integer32,
    cwsPmAdvancedCurrent24hStatisticsPostFecBitErrorRate StringSci 
}

cwsPmAdvancedCurrent24hStatisticsTableSnmpKey OBJECT-TYPE
    SYNTAX Integer32(0..2147483647)
    MAX-ACCESS not-accessible
    STATUS current
    DESCRIPTION "Unique key for cwsPmAdvancedCurrent24hStatistics"
    ::= { cwsPmAdvancedCurrent24hStatisticsEntry 1 }

cwsPmAdvancedCurrent24hStatisticsPostFecBitErrorRate OBJECT-TYPE
    SYNTAX StringSci
    MAX-ACCESS read-only
    STATUS current
    DESCRIPTION "Post-FEC Bit error rate reading."
    ::= { cwsPmAdvancedCurrent24hStatisticsEntry 2 }

cwsPmAdvancedCurrent24hPreFecBerTable OBJECT-TYPE
    SYNTAX SEQUENCE OF CwsPmAdvancedCurrent24hPreFecBerEntry
    MAX-ACCESS not-accessible
    STATUS current
    DESCRIPTION "Pre-FEC BER counts."
    ::= { cienaWsPmMIB 106 }

cwsPmAdvancedCurrent24hPreFecBerEntry OBJECT-TYPE
    SYNTAX CwsPmAdvancedCurrent24hPreFecBerEntry
    MAX-ACCESS not-accessible
    STATUS current
    DESCRIPTION "Entry for cwsPmAdvancedCurrent24hPreFecBerTable."
    INDEX { cwsPmPtpAdvancedInstancesInstanceName, cwsPmAdvancedCurrent24hPreFecBerTableSnmpKey }
    ::= { cwsPmAdvancedCurrent24hPreFecBerTable 1 }

CwsPmAdvancedCurrent24hPreFecBerEntry ::= SEQUENCE { 
    cwsPmAdvancedCurrent24hPreFecBerTableSnmpKey Integer32,
    cwsPmAdvancedCurrent24hPreFecBerBitErrorRate StringSci,
    cwsPmAdvancedCurrent24hPreFecBerMaximum StringSci 
}

cwsPmAdvancedCurrent24hPreFecBerTableSnmpKey OBJECT-TYPE
    SYNTAX Integer32(0..2147483647)
    MAX-ACCESS not-accessible
    STATUS current
    DESCRIPTION "Unique key for cwsPmAdvancedCurrent24hPreFecBer"
    ::= { cwsPmAdvancedCurrent24hPreFecBerEntry 1 }

cwsPmAdvancedCurrent24hPreFecBerBitErrorRate OBJECT-TYPE
    SYNTAX StringSci
    MAX-ACCESS read-write
    STATUS current
    DESCRIPTION "Bit error rate reading."
    ::= { cwsPmAdvancedCurrent24hPreFecBerEntry 2 }

cwsPmAdvancedCurrent24hPreFecBerMaximum OBJECT-TYPE
    SYNTAX StringSci
    MAX-ACCESS read-write
    STATUS current
    DESCRIPTION "Maximum BER reading."
    ::= { cwsPmAdvancedCurrent24hPreFecBerEntry 3 }

cwsPmAdvancedCurrent24hQFactorTable OBJECT-TYPE
    SYNTAX SEQUENCE OF CwsPmAdvancedCurrent24hQFactorEntry
    MAX-ACCESS not-accessible
    STATUS current
    DESCRIPTION "Q-Factor count."
    ::= { cienaWsPmMIB 107 }

cwsPmAdvancedCurrent24hQFactorEntry OBJECT-TYPE
    SYNTAX CwsPmAdvancedCurrent24hQFactorEntry
    MAX-ACCESS not-accessible
    STATUS current
    DESCRIPTION "Entry for cwsPmAdvancedCurrent24hQFactorTable."
    INDEX { cwsPmPtpAdvancedInstancesInstanceName, cwsPmAdvancedCurrent24hQFactorTableSnmpKey }
    ::= { cwsPmAdvancedCurrent24hQFactorTable 1 }

CwsPmAdvancedCurrent24hQFactorEntry ::= SEQUENCE { 
    cwsPmAdvancedCurrent24hQFactorTableSnmpKey Integer32,
    cwsPmAdvancedCurrent24hQFactorQFactor Decimal3Dig,
    cwsPmAdvancedCurrent24hQFactorMinimum Decimal3Dig,
    cwsPmAdvancedCurrent24hQFactorMaximum Decimal3Dig 
}

cwsPmAdvancedCurrent24hQFactorTableSnmpKey OBJECT-TYPE
    SYNTAX Integer32(0..2147483647)
    MAX-ACCESS not-accessible
    STATUS current
    DESCRIPTION "Unique key for cwsPmAdvancedCurrent24hQFactor"
    ::= { cwsPmAdvancedCurrent24hQFactorEntry 1 }

cwsPmAdvancedCurrent24hQFactorQFactor OBJECT-TYPE
    SYNTAX Decimal3Dig
    MAX-ACCESS read-write
    STATUS current
    DESCRIPTION "Minimum Q-Factor reading."
    ::= { cwsPmAdvancedCurrent24hQFactorEntry 2 }

cwsPmAdvancedCurrent24hQFactorMinimum OBJECT-TYPE
    SYNTAX Decimal3Dig
    MAX-ACCESS read-write
    STATUS current
    DESCRIPTION "Minimum Q-Factor reading."
    ::= { cwsPmAdvancedCurrent24hQFactorEntry 3 }

cwsPmAdvancedCurrent24hQFactorMaximum OBJECT-TYPE
    SYNTAX Decimal3Dig
    MAX-ACCESS read-write
    STATUS current
    DESCRIPTION "Maximum Q-Factor reading."
    ::= { cwsPmAdvancedCurrent24hQFactorEntry 4 }

cwsPmAdvancedCurrent24hFecErrorTable OBJECT-TYPE
    SYNTAX SEQUENCE OF CwsPmAdvancedCurrent24hFecErrorEntry
    MAX-ACCESS not-accessible
    STATUS current
    DESCRIPTION "FEC error counts."
    ::= { cienaWsPmMIB 108 }

cwsPmAdvancedCurrent24hFecErrorEntry OBJECT-TYPE
    SYNTAX CwsPmAdvancedCurrent24hFecErrorEntry
    MAX-ACCESS not-accessible
    STATUS current
    DESCRIPTION "Entry for cwsPmAdvancedCurrent24hFecErrorTable."
    INDEX { cwsPmPtpAdvancedInstancesInstanceName, cwsPmAdvancedCurrent24hFecErrorTableSnmpKey }
    ::= { cwsPmAdvancedCurrent24hFecErrorTable 1 }

CwsPmAdvancedCurrent24hFecErrorEntry ::= SEQUENCE { 
    cwsPmAdvancedCurrent24hFecErrorTableSnmpKey Integer32,
    cwsPmAdvancedCurrent24hFecErrorFrameErrorCount Counter64,
    cwsPmAdvancedCurrent24hFecErrorFrameErrorCountSecond Counter64,
    cwsPmAdvancedCurrent24hFecErrorUncorrectedBlockCount Counter64,
    cwsPmAdvancedCurrent24hFecErrorHighCorrectionCountSeconds Counter64 
}

cwsPmAdvancedCurrent24hFecErrorTableSnmpKey OBJECT-TYPE
    SYNTAX Integer32(0..2147483647)
    MAX-ACCESS not-accessible
    STATUS current
    DESCRIPTION "Unique key for cwsPmAdvancedCurrent24hFecError"
    ::= { cwsPmAdvancedCurrent24hFecErrorEntry 1 }

cwsPmAdvancedCurrent24hFecErrorFrameErrorCount OBJECT-TYPE
    SYNTAX Counter64
    MAX-ACCESS read-write
    STATUS current
    DESCRIPTION "FEC Frame error counts."
    ::= { cwsPmAdvancedCurrent24hFecErrorEntry 2 }

cwsPmAdvancedCurrent24hFecErrorFrameErrorCountSecond OBJECT-TYPE
    SYNTAX Counter64
    MAX-ACCESS read-write
    STATUS current
    DESCRIPTION "FEC Frame error count second."
    ::= { cwsPmAdvancedCurrent24hFecErrorEntry 3 }

cwsPmAdvancedCurrent24hFecErrorUncorrectedBlockCount OBJECT-TYPE
    SYNTAX Counter64
    MAX-ACCESS read-write
    STATUS current
    DESCRIPTION "FEC uncorrected block count."
    ::= { cwsPmAdvancedCurrent24hFecErrorEntry 4 }

cwsPmAdvancedCurrent24hFecErrorHighCorrectionCountSeconds OBJECT-TYPE
    SYNTAX Counter64
    MAX-ACCESS read-write
    STATUS current
    DESCRIPTION "FEC high correction count seconds."
    ::= { cwsPmAdvancedCurrent24hFecErrorEntry 5 }

cwsPmAdvancedHistoryBinsTable OBJECT-TYPE
    SYNTAX SEQUENCE OF CwsPmAdvancedHistoryBinsEntry
    MAX-ACCESS not-accessible
    STATUS current
    DESCRIPTION "List of PM history bins."
    ::= { cienaWsPmMIB 109 }

cwsPmAdvancedHistoryBinsEntry OBJECT-TYPE
    SYNTAX CwsPmAdvancedHistoryBinsEntry
    MAX-ACCESS not-accessible
    STATUS current
    DESCRIPTION "Entry for cwsPmAdvancedHistoryBinsTable."
    INDEX { cwsPmPtpAdvancedInstancesInstanceName, cwsPmAdvancedHistoryBinsBinNumber }
    ::= { cwsPmAdvancedHistoryBinsTable 1 }

CwsPmAdvancedHistoryBinsEntry ::= SEQUENCE { 
    cwsPmAdvancedHistoryBinsBinNumber Integer32 
}

cwsPmAdvancedHistoryBinsBinNumber OBJECT-TYPE
    SYNTAX Integer32(0..2147483647)
    MAX-ACCESS read-only
    STATUS current
    DESCRIPTION "Bin number."
    ::= { cwsPmAdvancedHistoryBinsEntry 1 }

cwsPmAdvancedHistoryStateTable OBJECT-TYPE
    SYNTAX SEQUENCE OF CwsPmAdvancedHistoryStateEntry
    MAX-ACCESS not-accessible
    STATUS current
    DESCRIPTION "PM bin state."
    ::= { cienaWsPmMIB 110 }

cwsPmAdvancedHistoryStateEntry OBJECT-TYPE
    SYNTAX CwsPmAdvancedHistoryStateEntry
    MAX-ACCESS not-accessible
    STATUS current
    DESCRIPTION "Entry for cwsPmAdvancedHistoryStateTable."
    INDEX { cwsPmPtpAdvancedInstancesInstanceName, cwsPmAdvancedHistoryBinsBinNumber, cwsPmAdvancedHistoryStateTableSnmpKey }
    ::= { cwsPmAdvancedHistoryStateTable 1 }

CwsPmAdvancedHistoryStateEntry ::= SEQUENCE { 
    cwsPmAdvancedHistoryStateTableSnmpKey Integer32,
    cwsPmAdvancedHistoryStateStartDateTime StringMaxl32,
    cwsPmAdvancedHistoryStateEndDateTime StringMaxl32,
    cwsPmAdvancedHistoryStateState PmBinState 
}

cwsPmAdvancedHistoryStateTableSnmpKey OBJECT-TYPE
    SYNTAX Integer32(0..2147483647)
    MAX-ACCESS not-accessible
    STATUS current
    DESCRIPTION "Unique key for cwsPmAdvancedHistoryState"
    ::= { cwsPmAdvancedHistoryStateEntry 1 }

cwsPmAdvancedHistoryStateStartDateTime OBJECT-TYPE
    SYNTAX StringMaxl32
    MAX-ACCESS read-write
    STATUS current
    DESCRIPTION "Start date and time."
    ::= { cwsPmAdvancedHistoryStateEntry 2 }

cwsPmAdvancedHistoryStateEndDateTime OBJECT-TYPE
    SYNTAX StringMaxl32
    MAX-ACCESS read-write
    STATUS current
    DESCRIPTION "End date and time."
    ::= { cwsPmAdvancedHistoryStateEntry 3 }

cwsPmAdvancedHistoryStateState OBJECT-TYPE
    SYNTAX PmBinState
    MAX-ACCESS read-write
    STATUS current
    DESCRIPTION "The PM bin state."
    ::= { cwsPmAdvancedHistoryStateEntry 4 }

cwsPmAdvancedHistoryStatisticsTable OBJECT-TYPE
    SYNTAX SEQUENCE OF CwsPmAdvancedHistoryStatisticsEntry
    MAX-ACCESS not-accessible
    STATUS current
    DESCRIPTION "Statistics data."
    ::= { cienaWsPmMIB 111 }

cwsPmAdvancedHistoryStatisticsEntry OBJECT-TYPE
    SYNTAX CwsPmAdvancedHistoryStatisticsEntry
    MAX-ACCESS not-accessible
    STATUS current
    DESCRIPTION "Entry for cwsPmAdvancedHistoryStatisticsTable."
    INDEX { cwsPmPtpAdvancedInstancesInstanceName, cwsPmAdvancedHistoryBinsBinNumber, cwsPmAdvancedHistoryStatisticsTableSnmpKey }
    ::= { cwsPmAdvancedHistoryStatisticsTable 1 }

CwsPmAdvancedHistoryStatisticsEntry ::= SEQUENCE { 
    cwsPmAdvancedHistoryStatisticsTableSnmpKey Integer32,
    cwsPmAdvancedHistoryStatisticsPostFecBitErrorRate StringSci 
}

cwsPmAdvancedHistoryStatisticsTableSnmpKey OBJECT-TYPE
    SYNTAX Integer32(0..2147483647)
    MAX-ACCESS not-accessible
    STATUS current
    DESCRIPTION "Unique key for cwsPmAdvancedHistoryStatistics"
    ::= { cwsPmAdvancedHistoryStatisticsEntry 1 }

cwsPmAdvancedHistoryStatisticsPostFecBitErrorRate OBJECT-TYPE
    SYNTAX StringSci
    MAX-ACCESS read-only
    STATUS current
    DESCRIPTION "Post-FEC Bit error rate reading."
    ::= { cwsPmAdvancedHistoryStatisticsEntry 2 }

cwsPmAdvancedHistoryPreFecBerTable OBJECT-TYPE
    SYNTAX SEQUENCE OF CwsPmAdvancedHistoryPreFecBerEntry
    MAX-ACCESS not-accessible
    STATUS current
    DESCRIPTION "Pre-FEC BER counts."
    ::= { cienaWsPmMIB 112 }

cwsPmAdvancedHistoryPreFecBerEntry OBJECT-TYPE
    SYNTAX CwsPmAdvancedHistoryPreFecBerEntry
    MAX-ACCESS not-accessible
    STATUS current
    DESCRIPTION "Entry for cwsPmAdvancedHistoryPreFecBerTable."
    INDEX { cwsPmPtpAdvancedInstancesInstanceName, cwsPmAdvancedHistoryBinsBinNumber, cwsPmAdvancedHistoryPreFecBerTableSnmpKey }
    ::= { cwsPmAdvancedHistoryPreFecBerTable 1 }

CwsPmAdvancedHistoryPreFecBerEntry ::= SEQUENCE { 
    cwsPmAdvancedHistoryPreFecBerTableSnmpKey Integer32,
    cwsPmAdvancedHistoryPreFecBerBitErrorRate StringSci,
    cwsPmAdvancedHistoryPreFecBerMaximum StringSci 
}

cwsPmAdvancedHistoryPreFecBerTableSnmpKey OBJECT-TYPE
    SYNTAX Integer32(0..2147483647)
    MAX-ACCESS not-accessible
    STATUS current
    DESCRIPTION "Unique key for cwsPmAdvancedHistoryPreFecBer"
    ::= { cwsPmAdvancedHistoryPreFecBerEntry 1 }

cwsPmAdvancedHistoryPreFecBerBitErrorRate OBJECT-TYPE
    SYNTAX StringSci
    MAX-ACCESS read-write
    STATUS current
    DESCRIPTION "Bit error rate reading."
    ::= { cwsPmAdvancedHistoryPreFecBerEntry 2 }

cwsPmAdvancedHistoryPreFecBerMaximum OBJECT-TYPE
    SYNTAX StringSci
    MAX-ACCESS read-write
    STATUS current
    DESCRIPTION "Maximum BER reading."
    ::= { cwsPmAdvancedHistoryPreFecBerEntry 3 }

cwsPmAdvancedHistoryQFactorTable OBJECT-TYPE
    SYNTAX SEQUENCE OF CwsPmAdvancedHistoryQFactorEntry
    MAX-ACCESS not-accessible
    STATUS current
    DESCRIPTION "Q-Factor count."
    ::= { cienaWsPmMIB 113 }

cwsPmAdvancedHistoryQFactorEntry OBJECT-TYPE
    SYNTAX CwsPmAdvancedHistoryQFactorEntry
    MAX-ACCESS not-accessible
    STATUS current
    DESCRIPTION "Entry for cwsPmAdvancedHistoryQFactorTable."
    INDEX { cwsPmPtpAdvancedInstancesInstanceName, cwsPmAdvancedHistoryBinsBinNumber, cwsPmAdvancedHistoryQFactorTableSnmpKey }
    ::= { cwsPmAdvancedHistoryQFactorTable 1 }

CwsPmAdvancedHistoryQFactorEntry ::= SEQUENCE { 
    cwsPmAdvancedHistoryQFactorTableSnmpKey Integer32,
    cwsPmAdvancedHistoryQFactorQFactor Decimal3Dig,
    cwsPmAdvancedHistoryQFactorMinimum Decimal3Dig,
    cwsPmAdvancedHistoryQFactorMaximum Decimal3Dig 
}

cwsPmAdvancedHistoryQFactorTableSnmpKey OBJECT-TYPE
    SYNTAX Integer32(0..2147483647)
    MAX-ACCESS not-accessible
    STATUS current
    DESCRIPTION "Unique key for cwsPmAdvancedHistoryQFactor"
    ::= { cwsPmAdvancedHistoryQFactorEntry 1 }

cwsPmAdvancedHistoryQFactorQFactor OBJECT-TYPE
    SYNTAX Decimal3Dig
    MAX-ACCESS read-write
    STATUS current
    DESCRIPTION "Minimum Q-Factor reading."
    ::= { cwsPmAdvancedHistoryQFactorEntry 2 }

cwsPmAdvancedHistoryQFactorMinimum OBJECT-TYPE
    SYNTAX Decimal3Dig
    MAX-ACCESS read-write
    STATUS current
    DESCRIPTION "Minimum Q-Factor reading."
    ::= { cwsPmAdvancedHistoryQFactorEntry 3 }

cwsPmAdvancedHistoryQFactorMaximum OBJECT-TYPE
    SYNTAX Decimal3Dig
    MAX-ACCESS read-write
    STATUS current
    DESCRIPTION "Maximum Q-Factor reading."
    ::= { cwsPmAdvancedHistoryQFactorEntry 4 }

cwsPmAdvancedHistoryFecErrorTable OBJECT-TYPE
    SYNTAX SEQUENCE OF CwsPmAdvancedHistoryFecErrorEntry
    MAX-ACCESS not-accessible
    STATUS current
    DESCRIPTION "FEC error counts."
    ::= { cienaWsPmMIB 114 }

cwsPmAdvancedHistoryFecErrorEntry OBJECT-TYPE
    SYNTAX CwsPmAdvancedHistoryFecErrorEntry
    MAX-ACCESS not-accessible
    STATUS current
    DESCRIPTION "Entry for cwsPmAdvancedHistoryFecErrorTable."
    INDEX { cwsPmPtpAdvancedInstancesInstanceName, cwsPmAdvancedHistoryBinsBinNumber, cwsPmAdvancedHistoryFecErrorTableSnmpKey }
    ::= { cwsPmAdvancedHistoryFecErrorTable 1 }

CwsPmAdvancedHistoryFecErrorEntry ::= SEQUENCE { 
    cwsPmAdvancedHistoryFecErrorTableSnmpKey Integer32,
    cwsPmAdvancedHistoryFecErrorFrameErrorCount Counter64,
    cwsPmAdvancedHistoryFecErrorFrameErrorCountSecond Counter64,
    cwsPmAdvancedHistoryFecErrorUncorrectedBlockCount Counter64,
    cwsPmAdvancedHistoryFecErrorHighCorrectionCountSeconds Counter64 
}

cwsPmAdvancedHistoryFecErrorTableSnmpKey OBJECT-TYPE
    SYNTAX Integer32(0..2147483647)
    MAX-ACCESS not-accessible
    STATUS current
    DESCRIPTION "Unique key for cwsPmAdvancedHistoryFecError"
    ::= { cwsPmAdvancedHistoryFecErrorEntry 1 }

cwsPmAdvancedHistoryFecErrorFrameErrorCount OBJECT-TYPE
    SYNTAX Counter64
    MAX-ACCESS read-write
    STATUS current
    DESCRIPTION "FEC Frame error counts."
    ::= { cwsPmAdvancedHistoryFecErrorEntry 2 }

cwsPmAdvancedHistoryFecErrorFrameErrorCountSecond OBJECT-TYPE
    SYNTAX Counter64
    MAX-ACCESS read-write
    STATUS current
    DESCRIPTION "FEC Frame error count second."
    ::= { cwsPmAdvancedHistoryFecErrorEntry 3 }

cwsPmAdvancedHistoryFecErrorUncorrectedBlockCount OBJECT-TYPE
    SYNTAX Counter64
    MAX-ACCESS read-write
    STATUS current
    DESCRIPTION "FEC uncorrected block count."
    ::= { cwsPmAdvancedHistoryFecErrorEntry 4 }

cwsPmAdvancedHistoryFecErrorHighCorrectionCountSeconds OBJECT-TYPE
    SYNTAX Counter64
    MAX-ACCESS read-write
    STATUS current
    DESCRIPTION "FEC high correction count seconds."
    ::= { cwsPmAdvancedHistoryFecErrorEntry 5 }

cwsPmAdvancedHistory24hIdTable OBJECT-TYPE
    SYNTAX SEQUENCE OF CwsPmAdvancedHistory24hIdEntry
    MAX-ACCESS not-accessible
    STATUS current
    DESCRIPTION "PM Bin identification."
    ::= { cienaWsPmMIB 115 }

cwsPmAdvancedHistory24hIdEntry OBJECT-TYPE
    SYNTAX CwsPmAdvancedHistory24hIdEntry
    MAX-ACCESS not-accessible
    STATUS current
    DESCRIPTION "Entry for cwsPmAdvancedHistory24hIdTable."
    INDEX { cwsPmPtpAdvancedInstancesInstanceName, cwsPmAdvancedHistory24hIdTableSnmpKey }
    ::= { cwsPmAdvancedHistory24hIdTable 1 }

CwsPmAdvancedHistory24hIdEntry ::= SEQUENCE { 
    cwsPmAdvancedHistory24hIdTableSnmpKey Integer32,
    cwsPmAdvancedHistory24hIdBinNumber Unsigned32,
    cwsPmAdvancedHistory24hIdBinName StringMaxl32 
}

cwsPmAdvancedHistory24hIdTableSnmpKey OBJECT-TYPE
    SYNTAX Integer32(0..2147483647)
    MAX-ACCESS not-accessible
    STATUS current
    DESCRIPTION "Unique key for cwsPmAdvancedHistory24hId"
    ::= { cwsPmAdvancedHistory24hIdEntry 1 }

cwsPmAdvancedHistory24hIdBinNumber OBJECT-TYPE
    SYNTAX Unsigned32
    MAX-ACCESS read-write
    STATUS current
    DESCRIPTION "The PM bin number."
    ::= { cwsPmAdvancedHistory24hIdEntry 2 }

cwsPmAdvancedHistory24hIdBinName OBJECT-TYPE
    SYNTAX StringMaxl32
    MAX-ACCESS read-write
    STATUS current
    DESCRIPTION "The PM bin name."
    ::= { cwsPmAdvancedHistory24hIdEntry 3 }

cwsPmAdvancedHistory24hStateTable OBJECT-TYPE
    SYNTAX SEQUENCE OF CwsPmAdvancedHistory24hStateEntry
    MAX-ACCESS not-accessible
    STATUS current
    DESCRIPTION "PM bin state."
    ::= { cienaWsPmMIB 116 }

cwsPmAdvancedHistory24hStateEntry OBJECT-TYPE
    SYNTAX CwsPmAdvancedHistory24hStateEntry
    MAX-ACCESS not-accessible
    STATUS current
    DESCRIPTION "Entry for cwsPmAdvancedHistory24hStateTable."
    INDEX { cwsPmPtpAdvancedInstancesInstanceName, cwsPmAdvancedHistory24hStateTableSnmpKey }
    ::= { cwsPmAdvancedHistory24hStateTable 1 }

CwsPmAdvancedHistory24hStateEntry ::= SEQUENCE { 
    cwsPmAdvancedHistory24hStateTableSnmpKey Integer32,
    cwsPmAdvancedHistory24hStateStartDateTime StringMaxl32,
    cwsPmAdvancedHistory24hStateEndDateTime StringMaxl32,
    cwsPmAdvancedHistory24hStateState PmBinState 
}

cwsPmAdvancedHistory24hStateTableSnmpKey OBJECT-TYPE
    SYNTAX Integer32(0..2147483647)
    MAX-ACCESS not-accessible
    STATUS current
    DESCRIPTION "Unique key for cwsPmAdvancedHistory24hState"
    ::= { cwsPmAdvancedHistory24hStateEntry 1 }

cwsPmAdvancedHistory24hStateStartDateTime OBJECT-TYPE
    SYNTAX StringMaxl32
    MAX-ACCESS read-write
    STATUS current
    DESCRIPTION "Start date and time."
    ::= { cwsPmAdvancedHistory24hStateEntry 2 }

cwsPmAdvancedHistory24hStateEndDateTime OBJECT-TYPE
    SYNTAX StringMaxl32
    MAX-ACCESS read-write
    STATUS current
    DESCRIPTION "End date and time."
    ::= { cwsPmAdvancedHistory24hStateEntry 3 }

cwsPmAdvancedHistory24hStateState OBJECT-TYPE
    SYNTAX PmBinState
    MAX-ACCESS read-write
    STATUS current
    DESCRIPTION "The PM bin state."
    ::= { cwsPmAdvancedHistory24hStateEntry 4 }

cwsPmAdvancedHistory24hStatisticsTable OBJECT-TYPE
    SYNTAX SEQUENCE OF CwsPmAdvancedHistory24hStatisticsEntry
    MAX-ACCESS not-accessible
    STATUS current
    DESCRIPTION "Statistics data."
    ::= { cienaWsPmMIB 117 }

cwsPmAdvancedHistory24hStatisticsEntry OBJECT-TYPE
    SYNTAX CwsPmAdvancedHistory24hStatisticsEntry
    MAX-ACCESS not-accessible
    STATUS current
    DESCRIPTION "Entry for cwsPmAdvancedHistory24hStatisticsTable."
    INDEX { cwsPmPtpAdvancedInstancesInstanceName, cwsPmAdvancedHistory24hStatisticsTableSnmpKey }
    ::= { cwsPmAdvancedHistory24hStatisticsTable 1 }

CwsPmAdvancedHistory24hStatisticsEntry ::= SEQUENCE { 
    cwsPmAdvancedHistory24hStatisticsTableSnmpKey Integer32,
    cwsPmAdvancedHistory24hStatisticsPostFecBitErrorRate StringSci 
}

cwsPmAdvancedHistory24hStatisticsTableSnmpKey OBJECT-TYPE
    SYNTAX Integer32(0..2147483647)
    MAX-ACCESS not-accessible
    STATUS current
    DESCRIPTION "Unique key for cwsPmAdvancedHistory24hStatistics"
    ::= { cwsPmAdvancedHistory24hStatisticsEntry 1 }

cwsPmAdvancedHistory24hStatisticsPostFecBitErrorRate OBJECT-TYPE
    SYNTAX StringSci
    MAX-ACCESS read-only
    STATUS current
    DESCRIPTION "Post-FEC Bit error rate reading."
    ::= { cwsPmAdvancedHistory24hStatisticsEntry 2 }

cwsPmAdvancedHistory24hPreFecBerTable OBJECT-TYPE
    SYNTAX SEQUENCE OF CwsPmAdvancedHistory24hPreFecBerEntry
    MAX-ACCESS not-accessible
    STATUS current
    DESCRIPTION "Pre-FEC BER counts."
    ::= { cienaWsPmMIB 118 }

cwsPmAdvancedHistory24hPreFecBerEntry OBJECT-TYPE
    SYNTAX CwsPmAdvancedHistory24hPreFecBerEntry
    MAX-ACCESS not-accessible
    STATUS current
    DESCRIPTION "Entry for cwsPmAdvancedHistory24hPreFecBerTable."
    INDEX { cwsPmPtpAdvancedInstancesInstanceName, cwsPmAdvancedHistory24hPreFecBerTableSnmpKey }
    ::= { cwsPmAdvancedHistory24hPreFecBerTable 1 }

CwsPmAdvancedHistory24hPreFecBerEntry ::= SEQUENCE { 
    cwsPmAdvancedHistory24hPreFecBerTableSnmpKey Integer32,
    cwsPmAdvancedHistory24hPreFecBerBitErrorRate StringSci,
    cwsPmAdvancedHistory24hPreFecBerMaximum StringSci 
}

cwsPmAdvancedHistory24hPreFecBerTableSnmpKey OBJECT-TYPE
    SYNTAX Integer32(0..2147483647)
    MAX-ACCESS not-accessible
    STATUS current
    DESCRIPTION "Unique key for cwsPmAdvancedHistory24hPreFecBer"
    ::= { cwsPmAdvancedHistory24hPreFecBerEntry 1 }

cwsPmAdvancedHistory24hPreFecBerBitErrorRate OBJECT-TYPE
    SYNTAX StringSci
    MAX-ACCESS read-write
    STATUS current
    DESCRIPTION "Bit error rate reading."
    ::= { cwsPmAdvancedHistory24hPreFecBerEntry 2 }

cwsPmAdvancedHistory24hPreFecBerMaximum OBJECT-TYPE
    SYNTAX StringSci
    MAX-ACCESS read-write
    STATUS current
    DESCRIPTION "Maximum BER reading."
    ::= { cwsPmAdvancedHistory24hPreFecBerEntry 3 }

cwsPmAdvancedHistory24hQFactorTable OBJECT-TYPE
    SYNTAX SEQUENCE OF CwsPmAdvancedHistory24hQFactorEntry
    MAX-ACCESS not-accessible
    STATUS current
    DESCRIPTION "Q-Factor count."
    ::= { cienaWsPmMIB 119 }

cwsPmAdvancedHistory24hQFactorEntry OBJECT-TYPE
    SYNTAX CwsPmAdvancedHistory24hQFactorEntry
    MAX-ACCESS not-accessible
    STATUS current
    DESCRIPTION "Entry for cwsPmAdvancedHistory24hQFactorTable."
    INDEX { cwsPmPtpAdvancedInstancesInstanceName, cwsPmAdvancedHistory24hQFactorTableSnmpKey }
    ::= { cwsPmAdvancedHistory24hQFactorTable 1 }

CwsPmAdvancedHistory24hQFactorEntry ::= SEQUENCE { 
    cwsPmAdvancedHistory24hQFactorTableSnmpKey Integer32,
    cwsPmAdvancedHistory24hQFactorQFactor Decimal3Dig,
    cwsPmAdvancedHistory24hQFactorMinimum Decimal3Dig,
    cwsPmAdvancedHistory24hQFactorMaximum Decimal3Dig 
}

cwsPmAdvancedHistory24hQFactorTableSnmpKey OBJECT-TYPE
    SYNTAX Integer32(0..2147483647)
    MAX-ACCESS not-accessible
    STATUS current
    DESCRIPTION "Unique key for cwsPmAdvancedHistory24hQFactor"
    ::= { cwsPmAdvancedHistory24hQFactorEntry 1 }

cwsPmAdvancedHistory24hQFactorQFactor OBJECT-TYPE
    SYNTAX Decimal3Dig
    MAX-ACCESS read-write
    STATUS current
    DESCRIPTION "Minimum Q-Factor reading."
    ::= { cwsPmAdvancedHistory24hQFactorEntry 2 }

cwsPmAdvancedHistory24hQFactorMinimum OBJECT-TYPE
    SYNTAX Decimal3Dig
    MAX-ACCESS read-write
    STATUS current
    DESCRIPTION "Minimum Q-Factor reading."
    ::= { cwsPmAdvancedHistory24hQFactorEntry 3 }

cwsPmAdvancedHistory24hQFactorMaximum OBJECT-TYPE
    SYNTAX Decimal3Dig
    MAX-ACCESS read-write
    STATUS current
    DESCRIPTION "Maximum Q-Factor reading."
    ::= { cwsPmAdvancedHistory24hQFactorEntry 4 }

cwsPmAdvancedHistory24hFecErrorTable OBJECT-TYPE
    SYNTAX SEQUENCE OF CwsPmAdvancedHistory24hFecErrorEntry
    MAX-ACCESS not-accessible
    STATUS current
    DESCRIPTION "FEC error counts."
    ::= { cienaWsPmMIB 120 }

cwsPmAdvancedHistory24hFecErrorEntry OBJECT-TYPE
    SYNTAX CwsPmAdvancedHistory24hFecErrorEntry
    MAX-ACCESS not-accessible
    STATUS current
    DESCRIPTION "Entry for cwsPmAdvancedHistory24hFecErrorTable."
    INDEX { cwsPmPtpAdvancedInstancesInstanceName, cwsPmAdvancedHistory24hFecErrorTableSnmpKey }
    ::= { cwsPmAdvancedHistory24hFecErrorTable 1 }

CwsPmAdvancedHistory24hFecErrorEntry ::= SEQUENCE { 
    cwsPmAdvancedHistory24hFecErrorTableSnmpKey Integer32,
    cwsPmAdvancedHistory24hFecErrorFrameErrorCount Counter64,
    cwsPmAdvancedHistory24hFecErrorFrameErrorCountSecond Counter64,
    cwsPmAdvancedHistory24hFecErrorUncorrectedBlockCount Counter64,
    cwsPmAdvancedHistory24hFecErrorHighCorrectionCountSeconds Counter64 
}

cwsPmAdvancedHistory24hFecErrorTableSnmpKey OBJECT-TYPE
    SYNTAX Integer32(0..2147483647)
    MAX-ACCESS not-accessible
    STATUS current
    DESCRIPTION "Unique key for cwsPmAdvancedHistory24hFecError"
    ::= { cwsPmAdvancedHistory24hFecErrorEntry 1 }

cwsPmAdvancedHistory24hFecErrorFrameErrorCount OBJECT-TYPE
    SYNTAX Counter64
    MAX-ACCESS read-write
    STATUS current
    DESCRIPTION "FEC Frame error counts."
    ::= { cwsPmAdvancedHistory24hFecErrorEntry 2 }

cwsPmAdvancedHistory24hFecErrorFrameErrorCountSecond OBJECT-TYPE
    SYNTAX Counter64
    MAX-ACCESS read-write
    STATUS current
    DESCRIPTION "FEC Frame error count second."
    ::= { cwsPmAdvancedHistory24hFecErrorEntry 3 }

cwsPmAdvancedHistory24hFecErrorUncorrectedBlockCount OBJECT-TYPE
    SYNTAX Counter64
    MAX-ACCESS read-write
    STATUS current
    DESCRIPTION "FEC uncorrected block count."
    ::= { cwsPmAdvancedHistory24hFecErrorEntry 4 }

cwsPmAdvancedHistory24hFecErrorHighCorrectionCountSeconds OBJECT-TYPE
    SYNTAX Counter64
    MAX-ACCESS read-write
    STATUS current
    DESCRIPTION "FEC high correction count seconds."
    ::= { cwsPmAdvancedHistory24hFecErrorEntry 5 }



-- Conformance statements
cienaWsPmObjects OBJECT IDENTIFIER
    ::= { cienaWsPmMIB 1 }

cienaWsPmConformance OBJECT IDENTIFIER
    ::= { cienaWsPmMIB 2 }

cienaWsPmGroups OBJECT IDENTIFIER
    ::= { cienaWsPmConformance 1 }

cienaWsPmGroup OBJECT-GROUP
    OBJECTS { 
        cwsPmGlobalConfigAdminState,
        cwsPmGlobalConfigPersistenceInterval,
        cwsPmGlobalConfigPersistenceStorageLocation,
        cwsPmPersistenceStateState,
        cwsPmPersistenceStateNextHistoryBinSave,
        cwsPmPersistenceStateCurrentFileSize,
        cwsPmPersistenceStateSaveStatus,
        cwsPmPersistenceStateInstancesSaved,
        cwsPmPersistenceStateElapsedSaveTime,
        cwsPmPersistenceStateLoadStatus,
        cwsPmPersistenceStateInstancesInFile,
        cwsPmPersistenceStateInstancesLoaded,
        cwsPmPersistenceStateElapsedLoadTime,
        cwsPmInstancesInstanceName,
        cwsPmInstancesAdminState,
        cwsPmInstancesOperationalState,
        cwsPmInstancesInstanceType,
        cwsPmInstancesBinCount,
        cwsPmInstancesBinDuration,
        cwsPmInstancesAttachedInterfaceType,
        cwsPmInstancesAttachedInterfaceName,
        cwsPmPortExtendedTxRxInstancesInstanceName,
        cwsPmExtendedIdInstanceId,
        cwsPmExtendedIdInstanceType,
        cwsPmExtendedIdProfileType,
        cwsPmExtendedStateAdminState,
        cwsPmExtendedStateOperationalState,
        cwsPmExtendedStateCurrentBinId,
        cwsPmExtendedStateCollectionStartDateTime,
        cwsPmExtendedStateCollectionEndDateTime,
        cwsPmExtendedPropertiesConfigurationMode,
        cwsPmExtendedPropertiesAlignment,
        cwsPmExtendedPropertiesConfiguredBinCount,
        cwsPmExtendedPropertiesConfiguredBinDuration,
        cwsPmExtendedPropertiesAttachedInterfacesType,
        cwsPmExtendedPropertiesAttachedInterfacesName,
        cwsPmExtendedPropertiesAttachedInterfacesOperationalState,
        cwsPmExtendedCurrentIdBinNumber,
        cwsPmExtendedCurrentIdBinName,
        cwsPmExtendedCurrentStateStartDateTime,
        cwsPmExtendedCurrentStateClearedDateTime,
        cwsPmExtendedCurrentStateState,
        cwsPmExtendedCurrentStatisticsFrameErrorRatio,
        cwsPmExtendedCurrentRxIfCountsBytes,
        cwsPmExtendedCurrentRxIfCountsPackets,
        cwsPmExtendedCurrentRxIfCountsAverageLinkUtilization,
        cwsPmExtendedCurrentRxIfCountsCrcErroredPackets,
        cwsPmExtendedCurrentRxIfCountsMulticastPackets,
        cwsPmExtendedCurrentRxIfCountsBroadcastPackets,
        cwsPmExtendedCurrentRxIfCountsPausePackets,
        cwsPmExtendedCurrentRxIfCountsUndersizedPackets,
        cwsPmExtendedCurrentRxIfCountsOversizedPackets,
        cwsPmExtendedCurrentRxIfCountsFragmentPackets,
        cwsPmExtendedCurrentRxIfCountsJabberPackets,
        cwsPmExtendedCurrentRxIfCountsLengthOutRangePackets,
        cwsPmExtendedCurrentRxIfCountsPackets64Octet,
        cwsPmExtendedCurrentRxIfCountsPackets65127Octet,
        cwsPmExtendedCurrentRxIfCountsPackets128255Octet,
        cwsPmExtendedCurrentRxIfCountsPackets256511Octet,
        cwsPmExtendedCurrentRxIfCountsPackets5121023Octet,
        cwsPmExtendedCurrentRxIfCountsPackets10241518Octet,
        cwsPmExtendedCurrentTxIfCountsBytes,
        cwsPmExtendedCurrentTxIfCountsPackets,
        cwsPmExtendedCurrentTxIfCountsAverageLinkUtilization,
        cwsPmExtendedCurrentTxIfCountsCrcErroredPackets,
        cwsPmExtendedCurrentTxIfCountsMulticastPackets,
        cwsPmExtendedCurrentTxIfCountsBroadcastPackets,
        cwsPmExtendedCurrentTxIfCountsPausePackets,
        cwsPmExtendedCurrentTxIfCountsExcessiveDeferredPackets,
        cwsPmExtendedCurrentTxIfCountsGiantPackets,
        cwsPmExtendedCurrentTxIfCountsUnderrunPackets,
        cwsPmExtendedCurrentTxIfCountsLengthCheckErrorPackets,
        cwsPmExtendedCurrentTxIfCountsLengthOutRangePackets,
        cwsPmExtendedCurrentTxQueuePacketDropCountSummary,
        cwsPmExtendedCurrentTxQueueQ0PacketDropCount,
        cwsPmExtendedCurrentTxQueueQ1PacketDropCount,
        cwsPmExtendedCurrentTxQueueQ2PacketDropCount,
        cwsPmExtendedCurrentTxQueueQ3PacketDropCount,
        cwsPmExtendedCurrentTxQueueQ4PacketDropCount,
        cwsPmExtendedCurrentTxQueueQ5PacketDropCount,
        cwsPmExtendedCurrentTxQueueQ6PacketDropCount,
        cwsPmExtendedCurrentTxQueueQ7PacketDropCount,
        cwsPmExtendedCurrentMacLayerUnavailableSeconds,
        cwsPmExtendedCurrentPcsLayerErroredSeconds,
        cwsPmExtendedCurrentPcsLayerSeverelyErroredSeconds,
        cwsPmExtendedCurrentPcsLayerUnavailableSeconds,
        cwsPmExtendedCurrentPcsSyncHeaderErrorsCount,
        cwsPmExtendedCurrentPcsBlockErrorsCount,
        cwsPmExtendedCurrentPcsMultilaneBipErrorsCount,
        cwsPmExtendedCurrentOduLayerErroredSeconds,
        cwsPmExtendedCurrentOduLayerSeverelyErroredSeconds,
        cwsPmExtendedCurrentOduLayerUnavailableSeconds,
        cwsPmExtendedCurrentFecLayerCorrectedBlockCount,
        cwsPmExtendedCurrentFecLayerUncorrectedBlockCount,
        cwsPmExtendedCurrentFecLayerSymbolErrorCount,
        cwsPmExtendedCurrent24hIdBinNumber,
        cwsPmExtendedCurrent24hIdBinName,
        cwsPmExtendedCurrent24hStateStartDateTime,
        cwsPmExtendedCurrent24hStateClearedDateTime,
        cwsPmExtendedCurrent24hStateState,
        cwsPmExtendedCurrent24hStatisticsFrameErrorRatio,
        cwsPmExtendedCurrent24hRxIfCountsBytes,
        cwsPmExtendedCurrent24hRxIfCountsPackets,
        cwsPmExtendedCurrent24hRxIfCountsAverageLinkUtilization,
        cwsPmExtendedCurrent24hRxIfCountsCrcErroredPackets,
        cwsPmExtendedCurrent24hRxIfCountsMulticastPackets,
        cwsPmExtendedCurrent24hRxIfCountsBroadcastPackets,
        cwsPmExtendedCurrent24hRxIfCountsPausePackets,
        cwsPmExtendedCurrent24hRxIfCountsUndersizedPackets,
        cwsPmExtendedCurrent24hRxIfCountsOversizedPackets,
        cwsPmExtendedCurrent24hRxIfCountsFragmentPackets,
        cwsPmExtendedCurrent24hRxIfCountsJabberPackets,
        cwsPmExtendedCurrent24hRxIfCountsLengthOutRangePackets,
        cwsPmExtendedCurrent24hRxIfCountsPackets64Octet,
        cwsPmExtendedCurrent24hRxIfCountsPackets65127Octet,
        cwsPmExtendedCurrent24hRxIfCountsPackets128255Octet,
        cwsPmExtendedCurrent24hRxIfCountsPackets256511Octet,
        cwsPmExtendedCurrent24hRxIfCountsPackets5121023Octet,
        cwsPmExtendedCurrent24hRxIfCountsPackets10241518Octet,
        cwsPmExtendedCurrent24hTxIfCountsBytes,
        cwsPmExtendedCurrent24hTxIfCountsPackets,
        cwsPmExtendedCurrent24hTxIfCountsAverageLinkUtilization,
        cwsPmExtendedCurrent24hTxIfCountsCrcErroredPackets,
        cwsPmExtendedCurrent24hTxIfCountsMulticastPackets,
        cwsPmExtendedCurrent24hTxIfCountsBroadcastPackets,
        cwsPmExtendedCurrent24hTxIfCountsPausePackets,
        cwsPmExtendedCurrent24hTxIfCountsExcessiveDeferredPackets,
        cwsPmExtendedCurrent24hTxIfCountsGiantPackets,
        cwsPmExtendedCurrent24hTxIfCountsUnderrunPackets,
        cwsPmExtendedCurrent24hTxIfCountsLengthCheckErrorPackets,
        cwsPmExtendedCurrent24hTxIfCountsLengthOutRangePackets,
        cwsPmExtendedCurrent24hTxQueuePacketDropCountSummary,
        cwsPmExtendedCurrent24hTxQueueQ0PacketDropCount,
        cwsPmExtendedCurrent24hTxQueueQ1PacketDropCount,
        cwsPmExtendedCurrent24hTxQueueQ2PacketDropCount,
        cwsPmExtendedCurrent24hTxQueueQ3PacketDropCount,
        cwsPmExtendedCurrent24hTxQueueQ4PacketDropCount,
        cwsPmExtendedCurrent24hTxQueueQ5PacketDropCount,
        cwsPmExtendedCurrent24hTxQueueQ6PacketDropCount,
        cwsPmExtendedCurrent24hTxQueueQ7PacketDropCount,
        cwsPmExtendedCurrent24hMacLayerUnavailableSeconds,
        cwsPmExtendedCurrent24hPcsLayerErroredSeconds,
        cwsPmExtendedCurrent24hPcsLayerSeverelyErroredSeconds,
        cwsPmExtendedCurrent24hPcsLayerUnavailableSeconds,
        cwsPmExtendedCurrent24hPcsSyncHeaderErrorsCount,
        cwsPmExtendedCurrent24hPcsBlockErrorsCount,
        cwsPmExtendedCurrent24hPcsMultilaneBipErrorsCount,
        cwsPmExtendedCurrent24hOduLayerErroredSeconds,
        cwsPmExtendedCurrent24hOduLayerSeverelyErroredSeconds,
        cwsPmExtendedCurrent24hOduLayerUnavailableSeconds,
        cwsPmExtendedCurrent24hFecLayerCorrectedBlockCount,
        cwsPmExtendedCurrent24hFecLayerUncorrectedBlockCount,
        cwsPmExtendedCurrent24hFecLayerSymbolErrorCount,
        cwsPmBinsBinNumber,
        cwsPmExtendedHistoryStateStartDateTime,
        cwsPmExtendedHistoryStateEndDateTime,
        cwsPmExtendedHistoryStateState,
        cwsPmExtendedHistoryStatisticsFrameErrorRatio,
        cwsPmExtendedHistoryRxIfCountsBytes,
        cwsPmExtendedHistoryRxIfCountsPackets,
        cwsPmExtendedHistoryRxIfCountsAverageLinkUtilization,
        cwsPmExtendedHistoryRxIfCountsCrcErroredPackets,
        cwsPmExtendedHistoryRxIfCountsMulticastPackets,
        cwsPmExtendedHistoryRxIfCountsBroadcastPackets,
        cwsPmExtendedHistoryRxIfCountsPausePackets,
        cwsPmExtendedHistoryRxIfCountsUndersizedPackets,
        cwsPmExtendedHistoryRxIfCountsOversizedPackets,
        cwsPmExtendedHistoryRxIfCountsFragmentPackets,
        cwsPmExtendedHistoryRxIfCountsJabberPackets,
        cwsPmExtendedHistoryRxIfCountsLengthOutRangePackets,
        cwsPmExtendedHistoryRxIfCountsPackets64Octet,
        cwsPmExtendedHistoryRxIfCountsPackets65127Octet,
        cwsPmExtendedHistoryRxIfCountsPackets128255Octet,
        cwsPmExtendedHistoryRxIfCountsPackets256511Octet,
        cwsPmExtendedHistoryRxIfCountsPackets5121023Octet,
        cwsPmExtendedHistoryRxIfCountsPackets10241518Octet,
        cwsPmExtendedHistoryTxIfCountsBytes,
        cwsPmExtendedHistoryTxIfCountsPackets,
        cwsPmExtendedHistoryTxIfCountsAverageLinkUtilization,
        cwsPmExtendedHistoryTxIfCountsCrcErroredPackets,
        cwsPmExtendedHistoryTxIfCountsMulticastPackets,
        cwsPmExtendedHistoryTxIfCountsBroadcastPackets,
        cwsPmExtendedHistoryTxIfCountsPausePackets,
        cwsPmExtendedHistoryTxIfCountsExcessiveDeferredPackets,
        cwsPmExtendedHistoryTxIfCountsGiantPackets,
        cwsPmExtendedHistoryTxIfCountsUnderrunPackets,
        cwsPmExtendedHistoryTxIfCountsLengthCheckErrorPackets,
        cwsPmExtendedHistoryTxIfCountsLengthOutRangePackets,
        cwsPmCurrentBinTxQueuePacketDropCountSummary,
        cwsPmCurrentBinTxQueueQ0PacketDropCount,
        cwsPmCurrentBinTxQueueQ1PacketDropCount,
        cwsPmCurrentBinTxQueueQ2PacketDropCount,
        cwsPmCurrentBinTxQueueQ3PacketDropCount,
        cwsPmCurrentBinTxQueueQ4PacketDropCount,
        cwsPmCurrentBinTxQueueQ5PacketDropCount,
        cwsPmCurrentBinTxQueueQ6PacketDropCount,
        cwsPmCurrentBinTxQueueQ7PacketDropCount,
        cwsPmExtendedHistoryMacLayerUnavailableSeconds,
        cwsPmExtendedHistoryPcsLayerErroredSeconds,
        cwsPmExtendedHistoryPcsLayerSeverelyErroredSeconds,
        cwsPmExtendedHistoryPcsLayerUnavailableSeconds,
        cwsPmExtendedHistoryPcsSyncHeaderErrorsCount,
        cwsPmExtendedHistoryPcsBlockErrorsCount,
        cwsPmExtendedHistoryPcsMultilaneBipErrorsCount,
        cwsPmExtendedHistoryOduLayerErroredSeconds,
        cwsPmExtendedHistoryOduLayerSeverelyErroredSeconds,
        cwsPmExtendedHistoryOduLayerUnavailableSeconds,
        cwsPmExtendedHistoryFecLayerCorrectedBlockCount,
        cwsPmExtendedHistoryFecLayerUncorrectedBlockCount,
        cwsPmExtendedHistoryFecLayerSymbolErrorCount,
        cwsPmExtendedHistory24hIdBinNumber,
        cwsPmExtendedHistory24hIdBinName,
        cwsPmExtendedHistory24hStateStartDateTime,
        cwsPmExtendedHistory24hStateEndDateTime,
        cwsPmExtendedHistory24hStateState,
        cwsPmExtendedHistory24hStatisticsFrameErrorRatio,
        cwsPmExtendedHistory24hRxIfCountsBytes,
        cwsPmExtendedHistory24hRxIfCountsPackets,
        cwsPmExtendedHistory24hRxIfCountsAverageLinkUtilization,
        cwsPmExtendedHistory24hRxIfCountsCrcErroredPackets,
        cwsPmExtendedHistory24hRxIfCountsMulticastPackets,
        cwsPmExtendedHistory24hRxIfCountsBroadcastPackets,
        cwsPmExtendedHistory24hRxIfCountsPausePackets,
        cwsPmExtendedHistory24hRxIfCountsUndersizedPackets,
        cwsPmExtendedHistory24hRxIfCountsOversizedPackets,
        cwsPmExtendedHistory24hRxIfCountsFragmentPackets,
        cwsPmExtendedHistory24hRxIfCountsJabberPackets,
        cwsPmExtendedHistory24hRxIfCountsLengthOutRangePackets,
        cwsPmExtendedHistory24hRxIfCountsPackets64Octet,
        cwsPmExtendedHistory24hRxIfCountsPackets65127Octet,
        cwsPmExtendedHistory24hRxIfCountsPackets128255Octet,
        cwsPmExtendedHistory24hRxIfCountsPackets256511Octet,
        cwsPmExtendedHistory24hRxIfCountsPackets5121023Octet,
        cwsPmExtendedHistory24hRxIfCountsPackets10241518Octet,
        cwsPmExtendedHistory24hTxIfCountsBytes,
        cwsPmExtendedHistory24hTxIfCountsPackets,
        cwsPmExtendedHistory24hTxIfCountsAverageLinkUtilization,
        cwsPmExtendedHistory24hTxIfCountsCrcErroredPackets,
        cwsPmExtendedHistory24hTxIfCountsMulticastPackets,
        cwsPmExtendedHistory24hTxIfCountsBroadcastPackets,
        cwsPmExtendedHistory24hTxIfCountsPausePackets,
        cwsPmExtendedHistory24hTxIfCountsExcessiveDeferredPackets,
        cwsPmExtendedHistory24hTxIfCountsGiantPackets,
        cwsPmExtendedHistory24hTxIfCountsUnderrunPackets,
        cwsPmExtendedHistory24hTxIfCountsLengthCheckErrorPackets,
        cwsPmExtendedHistory24hTxIfCountsLengthOutRangePackets,
        cwsPmExtendedHistory24hTxQueuePacketDropCountSummary,
        cwsPmExtendedHistory24hTxQueueQ0PacketDropCount,
        cwsPmExtendedHistory24hTxQueueQ1PacketDropCount,
        cwsPmExtendedHistory24hTxQueueQ2PacketDropCount,
        cwsPmExtendedHistory24hTxQueueQ3PacketDropCount,
        cwsPmExtendedHistory24hTxQueueQ4PacketDropCount,
        cwsPmExtendedHistory24hTxQueueQ5PacketDropCount,
        cwsPmExtendedHistory24hTxQueueQ6PacketDropCount,
        cwsPmExtendedHistory24hTxQueueQ7PacketDropCount,
        cwsPmExtendedHistory24hMacLayerUnavailableSeconds,
        cwsPmExtendedHistory24hPcsLayerErroredSeconds,
        cwsPmExtendedHistory24hPcsLayerSeverelyErroredSeconds,
        cwsPmExtendedHistory24hPcsLayerUnavailableSeconds,
        cwsPmExtendedHistory24hPcsSyncHeaderErrorsCount,
        cwsPmExtendedHistory24hPcsBlockErrorsCount,
        cwsPmExtendedHistory24hPcsMultilaneBipErrorsCount,
        cwsPmExtendedHistory24hOduLayerErroredSeconds,
        cwsPmExtendedHistory24hOduLayerSeverelyErroredSeconds,
        cwsPmExtendedHistory24hOduLayerUnavailableSeconds,
        cwsPmExtendedHistory24hFecLayerCorrectedBlockCount,
        cwsPmExtendedHistory24hFecLayerUncorrectedBlockCount,
        cwsPmExtendedHistory24hFecLayerSymbolErrorCount,
        cwsPmPtpBasicInstancesInstanceName,
        cwsPmBasicIdInstanceId,
        cwsPmBasicIdInstanceType,
        cwsPmBasicIdProfileType,
        cwsPmBasicStateAdminState,
        cwsPmBasicStateOperationalState,
        cwsPmBasicStateCurrentBinId,
        cwsPmBasicStateCollectionStartDateTime,
        cwsPmBasicStateCollectionEndDateTime,
        cwsPmBasicPropertiesConfigurationMode,
        cwsPmBasicPropertiesAlignment,
        cwsPmBasicPropertiesConfiguredBinCount,
        cwsPmBasicPropertiesConfiguredBinDuration,
        cwsPmBasicAttachedInterfaceType,
        cwsPmBasicAttachedInterfaceName,
        cwsPmBasicAttachedInterfaceOperationalState,
        cwsPmBasicCurrentIdBinNumber,
        cwsPmBasicCurrentIdBinName,
        cwsPmBasicCurrentStateStartDateTime,
        cwsPmBasicCurrentStateClearedDateTime,
        cwsPmBasicCurrentStateState,
        cwsPmBasicCurrentStatisticsNumberOfChannels,
        cwsPmBasicCurrentOpticalPowerChannelNumber,
        cwsPmBasicCurrentOpticalRxPowerActual,
        cwsPmBasicCurrentOpticalRxPowerMinimum,
        cwsPmBasicCurrentOpticalRxPowerMaximum,
        cwsPmBasicCurrentOpticalRxPowerAverage,
        cwsPmBasicCurrentOpticalTxPowerActual,
        cwsPmBasicCurrentOpticalTxPowerMinimum,
        cwsPmBasicCurrentOpticalTxPowerMaximum,
        cwsPmBasicCurrentOpticalTxPowerAverage,
        cwsPmBasicCurrentChannelRxPowerActual,
        cwsPmBasicCurrentChannelRxPowerMinimum,
        cwsPmBasicCurrentChannelRxPowerMaximum,
        cwsPmBasicCurrentChannelRxPowerAverage,
        cwsPmBasicCurrent24hIdBinNumber,
        cwsPmBasicCurrent24hIdBinName,
        cwsPmBasicCurrent24hStateStartDateTime,
        cwsPmBasicCurrent24hStateClearedDateTime,
        cwsPmBasicCurrent24hStateState,
        cwsPmBasicCurrent24hBinStatisticsNumberOfChannels,
        cwsPmBasicCurrent24hOpticalPowerChannelNumber,
        cwsPmBasicCurrent24hRxOpticalPowerActual,
        cwsPmBasicCurrent24hRxOpticalPowerMinimum,
        cwsPmBasicCurrent24hRxOpticalPowerMaximum,
        cwsPmBasicCurrent24hRxOpticalPowerAverage,
        cwsPmBasicCurrent24hTxOpticalPowerActual,
        cwsPmBasicCurrent24hTxOpticalPowerMinimum,
        cwsPmBasicCurrent24hTxOpticalPowerMaximum,
        cwsPmBasicCurrent24hTxOpticalPowerAverage,
        cwsPmBasicCurrent24hRxChannelPowerActual,
        cwsPmBasicCurrent24hRxChannelPowerMinimum,
        cwsPmBasicCurrent24hRxChannelPowerMaximum,
        cwsPmBasicCurrent24hRxChannelPowerAverage,
        cwsPmBasicHistoryBinsBinNumber,
        cwsPmBasicHistoryStateStartDateTime,
        cwsPmBasicHistoryStateEndDateTime,
        cwsPmBasicHistoryStateState,
        cwsPmBasicHistoryStatisticsNumberOfChannels,
        cwsPmBasicHistoryOpticalPowerChannelNumber,
        cwsPmBasicHistoryRxOpticalPowerActual,
        cwsPmBasicHistoryRxOpticalPowerMinimum,
        cwsPmBasicHistoryRxOpticalPowerMaximum,
        cwsPmBasicHistoryRxOpticalPowerAverage,
        cwsPmBasicHistoryTxOpticalPowerActual,
        cwsPmBasicHistoryTxOpticalPowerMinimum,
        cwsPmBasicHistoryTxOpticalPowerMaximum,
        cwsPmBasicHistoryTxOpticalPowerAverage,
        cwsPmBasicHistoryTxChannelPowerActual,
        cwsPmBasicHistoryTxChannelPowerMinimum,
        cwsPmBasicHistoryTxChannelPowerMaximum,
        cwsPmBasicHistoryTxChannelPowerAverage,
        cwsPmBasicHistory24hIdBinNumber,
        cwsPmBasicHistory24hIdBinName,
        cwsPmBasicHistory24hStateStartDateTime,
        cwsPmBasicHistory24hStateEndDateTime,
        cwsPmBasicHistory24hStateState,
        cwsPmBasicHistory24hStatisticsNumberOfChannels,
        cwsPmBasicHistory24hOpticalPowerChannelNumber,
        cwsPmBasicHistory24hRxOpticalPowerActual,
        cwsPmBasicHistory24hRxOpticalPowerMinimum,
        cwsPmBasicHistory24hRxOpticalPowerMaximum,
        cwsPmBasicHistory24hRxOpticalPowerAverage,
        cwsPmBasicHistory24hTxOpticalPowerActual,
        cwsPmBasicHistory24hTxOpticalPowerMinimum,
        cwsPmBasicHistory24hTxOpticalPowerMaximum,
        cwsPmBasicHistory24hTxOpticalPowerAverage,
        cwsPmBasicHistory24hRxChannelPowerActual,
        cwsPmBasicHistory24hRxChannelPowerMinimum,
        cwsPmBasicHistory24hRxChannelPowerMaximum,
        cwsPmBasicHistory24hRxChannelPowerAverage,
        cwsPmPtpAdvancedInstancesInstanceName,
        cwsPmAdvancedIdInstanceId,
        cwsPmAdvancedIdInstanceType,
        cwsPmAdvancedIdProfileType,
        cwsPmAdvancedStateAdminState,
        cwsPmAdvancedStateOperationalState,
        cwsPmAdvancedStateCurrentBinId,
        cwsPmAdvancedStateCollectionStartDateTime,
        cwsPmAdvancedStateCollectionEndDateTime,
        cwsPmAdvancedPropertiesConfigurationMode,
        cwsPmAdvancedPropertiesAlignment,
        cwsPmAdvancedPropertiesConfiguredBinCount,
        cwsPmAdvancedPropertiesConfiguredBinDuration,
        cwsPmAdvancedAttachedInterfaceType,
        cwsPmAdvancedAttachedInterfaceName,
        cwsPmAdvancedAttachedInterfaceOperationalState,
        cwsPmAdvancedCurrentIdBinNumber,
        cwsPmAdvancedCurrentIdBinName,
        cwsPmAdvancedCurrentStateStartDateTime,
        cwsPmAdvancedCurrentStateClearedDateTime,
        cwsPmAdvancedCurrentStateState,
        cwsPmAdvancedCurrentStatisticsPostFecBitErrorRate,
        cwsPmPreFecBitErrorRateBitErrorRate,
        cwsPmPreFecBitErrorRateMaximum,
        cwsPmAdvancedCurrentQFactorQFactor,
        cwsPmAdvancedCurrentQFactorMinimum,
        cwsPmAdvancedCurrentQFactorMaximum,
        cwsPmAdvancedCurrentFecErrorFrameErrorCount,
        cwsPmAdvancedCurrentFecErrorFrameErrorCountSecond,
        cwsPmAdvancedCurrentFecErrorUncorrectedBlockCount,
        cwsPmAdvancedCurrentFecErrorHighCorrectionCountSeconds,
        cwsPmAdvancedCurrent24hIdBinNumber,
        cwsPmAdvancedCurrent24hIdBinName,
        cwsPmAdvancedCurrent24hStateStartDateTime,
        cwsPmAdvancedCurrent24hStateClearedDateTime,
        cwsPmAdvancedCurrent24hStateState,
        cwsPmAdvancedCurrent24hStatisticsPostFecBitErrorRate,
        cwsPmAdvancedCurrent24hPreFecBerBitErrorRate,
        cwsPmAdvancedCurrent24hPreFecBerMaximum,
        cwsPmAdvancedCurrent24hQFactorQFactor,
        cwsPmAdvancedCurrent24hQFactorMinimum,
        cwsPmAdvancedCurrent24hQFactorMaximum,
        cwsPmAdvancedCurrent24hFecErrorFrameErrorCount,
        cwsPmAdvancedCurrent24hFecErrorFrameErrorCountSecond,
        cwsPmAdvancedCurrent24hFecErrorUncorrectedBlockCount,
        cwsPmAdvancedCurrent24hFecErrorHighCorrectionCountSeconds,
        cwsPmAdvancedHistoryBinsBinNumber,
        cwsPmAdvancedHistoryStateStartDateTime,
        cwsPmAdvancedHistoryStateEndDateTime,
        cwsPmAdvancedHistoryStateState,
        cwsPmAdvancedHistoryStatisticsPostFecBitErrorRate,
        cwsPmAdvancedHistoryPreFecBerBitErrorRate,
        cwsPmAdvancedHistoryPreFecBerMaximum,
        cwsPmAdvancedHistoryQFactorQFactor,
        cwsPmAdvancedHistoryQFactorMinimum,
        cwsPmAdvancedHistoryQFactorMaximum,
        cwsPmAdvancedHistoryFecErrorFrameErrorCount,
        cwsPmAdvancedHistoryFecErrorFrameErrorCountSecond,
        cwsPmAdvancedHistoryFecErrorUncorrectedBlockCount,
        cwsPmAdvancedHistoryFecErrorHighCorrectionCountSeconds,
        cwsPmAdvancedHistory24hIdBinNumber,
        cwsPmAdvancedHistory24hIdBinName,
        cwsPmAdvancedHistory24hStateStartDateTime,
        cwsPmAdvancedHistory24hStateEndDateTime,
        cwsPmAdvancedHistory24hStateState,
        cwsPmAdvancedHistory24hStatisticsPostFecBitErrorRate,
        cwsPmAdvancedHistory24hPreFecBerBitErrorRate,
        cwsPmAdvancedHistory24hPreFecBerMaximum,
        cwsPmAdvancedHistory24hQFactorQFactor,
        cwsPmAdvancedHistory24hQFactorMinimum,
        cwsPmAdvancedHistory24hQFactorMaximum,
        cwsPmAdvancedHistory24hFecErrorFrameErrorCount,
        cwsPmAdvancedHistory24hFecErrorFrameErrorCountSecond,
        cwsPmAdvancedHistory24hFecErrorUncorrectedBlockCount,
        cwsPmAdvancedHistory24hFecErrorHighCorrectionCountSeconds
    }
    STATUS current
    DESCRIPTION "Conformance Group"
    ::= { cienaWsPmGroups 1 }

cienaWsPmCompliances OBJECT IDENTIFIER
    ::= { cienaWsPmConformance 2 }

cienaWsPmCompliance MODULE-COMPLIANCE
    STATUS current
    DESCRIPTION "Compliance"
    MODULE MANDATORY-GROUPS { cienaWsPmGroup }
    ::= { cienaWsPmCompliances 1 }

END -- End module
