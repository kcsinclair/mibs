IANA-GMPLS-TC-MIB DEFINITIONS ::= BEGIN

   IMPORTS
       MODULE-IDENTITY, transmission       FROM SNMPv2-SMI  -- RFC2578
       TEXTUAL-CONVENTION                  FROM SNMPv2-TC;  -- RFC2579

   ianaGmpls MODULE-IDENTITY
       LAST-UPDATED "200510130001Z" -- 13 October 2005 00:00:01 GMT
       ORGANIZATION "IANA"
       CONTACT-INFO
                  "        Internet Assigned Numbers Authority
                   Postal: USC/Information Sciences Institute
                           4676 Admiralty Way, Marina del Rey, CA 90292
                   Tel:    +1 310 822 1511
                   E-Mail: iana@isi.edu"
       DESCRIPTION
         "Copyright (C) The Internet Society (2005). The initial version
          of this MIB module was published in RFC XXX. For full legal
          notices see the RFC itself.  Supplementary information
          may be available on:
          http://www.ietf.org/copyrights/ianamib.html"

          REVISION
               "200510130001Z" -- 13 October 2005 00:00:01 GMT
         DESCRIPTION
           "Initial version issued as part of RFC XXX."
       ::= { transmission 1 }

   IANAGmplsLSPEncodingType ::= TEXTUAL-CONVENTION
       STATUS       current
       DESCRIPTION
            "This data type is used as the syntax of the
             gmplsTunnelLSPEncoding object in the definition of
             GMPLS-TE-STD-MIB's gmplsTunnelTable.

             gmplsTunnelLSPEncoding is used to represent and control
             the LSP encoding type of an LSP signaled by a GMPLS
             signaling protocol.

             This textual convention is strongly tied to the LSP
             Encoding Types sub-registry of the GMPLS Signaling
             Parameters registry managed by IANA. Values should be
             assigned by IANA in step with the LSP Encoding Types
             sub-registry and using the same registry management rules.
             However, the actual values used in this textual convention
             are solely within the purview of IANA and do not
             necessarily match the values in the values in the LSP
             Encoding Types sub-registry.

             The definition of this textual convention with the
             addition of newly assigned values is published
             periodically by the IANA, in either the Assigned
             Numbers RFC, or some derivative of it specific to
             Internet Network Management number assignments. (The
             latest arrangements can be obtained by contacting the
             IANA.)

             Requests for new values should be made to IANA via
             email (iana@isi.edu)."
       REFERENCE
            "1. Generalized Multi-Protocol Label Switching (GMPLS)
                Signaling Functional Description, RFC 3471, section
                3.1.1.
             2. Generalized MPLS Signalling Extensions for G.709 Optical
                Transport Networks Control, draft-ietf-ccamp-gmpls-g709,
                work in progress, section 3.1.1."
       SYNTAX  INTEGER {
                  tunnelLspNotGmpls (0), -- GMPLS is not in use
                                         -- This is not part of the LSP
                                         -- Encoding Type registry, but
                                         -- is needed for the correct
                                         -- functioning of the
                                         -- GMPLS-TE-STD-MIB
                  tunnelLspPacket (1),          -- Packet
                  tunnelLspEthernet (2),        -- Ethernet
                  tunnelLspAnsiEtsiPdh (3),     -- PDH
                  -- the value 4 is deprecated
                  tunnelLspSdhSonet (5),        -- SDH or SONET
                  -- the value 6 is deprecated
                  tunnelLspDigitalWrapper (7),  -- Digital Wrapper
                  tunnelLspLambda (8),          -- Lambda
                  tunnelLspFiber (9),           -- Fiber
                  -- the value 10 is deprecated
                  tunnelLspFiberChannel (11),   -- Fiber Channel
                  tunnelDigitalPath (12),       -- Digital Path
                  tunnelOpticalChannel (13)     -- Optical Channel
                }

   IANAGmplsSwitchingType ::= TEXTUAL-CONVENTION
       STATUS       current
       DESCRIPTION
            "This data type is used as the syntax of the
             gmplsTunnelSwitchingType object in the definition of
             GMPLS-TE-STD-MIB's gmplsTunnelTable.

             gmplsTunnelSwitchingType is used to represent and
             control the LSP switching type of an LSP signaled by a
             GMPLS signaling protocol.

             This textual convention is strongly tied to the Switching
             Types sub-registry of the GMPLS Signaling Parameters
             registry managed by IANA. Values should be assigned by IANA
             in step with the Switching Types sub-registry and using the
             same registry management rules. However, the actual values
             used in this textual convention are solely within the
             purview of IANA and do not necessarily match the values in
             the values in the Switching Types sub-registry.

             The definition of this textual convention with the
             addition of newly assigned values is published
             periodically by the IANA, in either the Assigned
             Numbers RFC, or some derivative of it specific to
             Internet Network Management number assignments. (The
             latest arrangements can be obtained by contacting the
             IANA.)

             Requests for new values should be made to IANA via
             email (iana@isi.edu)."
       REFERENCE
            "1. Routing Extensions in Support of Generalized
                Multi-Protocol Label Switching, RFC 4202, section 2.4.
             2. Generalized Multi-Protocol Label Switching (GMPLS)
                Signaling Functional Description, RFC 3471, section
                3.1.1."
       SYNTAX  INTEGER {
                  unknown (0),   -- none of the following, or not known
                  psc1 (1),      -- Packet-Switch-Capable 1
                  psc2 (2),      -- Packet-Switch-Capable 2
                  psc3 (3),      -- Packet-Switch-Capable 3
                  psc4 (4),      -- Packet-Switch-Capable 4
                  l2sc (51),     -- Layer-2-Switch-Capable
                  tdm (100),     -- Time-Division-Multiplex
                  lsc (150),     -- Lambda-Switch-Capable
                  fsc (200)      -- Fiber-Switch-Capable
                }

   IANAGmplsGeneralizedPid ::= TEXTUAL-CONVENTION
       STATUS       current
       DESCRIPTION
            "This data type is used as the syntax of the
             gmplsTunnelGPid object in the definition of
             GMPLS-TE-STD-MIB's gmplsTunnelTable.

             gmplsTunnelGPid is used to represent and control the LSP
             Generalized Protocol Identifier (G-PID) of an LSP
             signaled by a GMPLS signaling protocol.

             This textual convention is strongly tied to the Generalized
             PIDs (G-PID) sub-registry of the GMPLS Signaling Parameters
             registry managed by IANA. Values should be assigned by IANA
             in step with the Generalized PIDs (G-PID) sub-registry and
             using the same registry management rules. However, the
             actual values used in this textual convention are solely
             within the purview of IANA and do not necessarily match the
             values in the values in the Generalized PIDs (G-PID)
             sub-registry.

             The definition of this textual convention with the
             addition of newly assigned values is published
             periodically by the IANA, in either the Assigned
             Numbers RFC, or some derivative of it specific to
             Internet Network Management number assignments. (The
             latest arrangements can be obtained by contacting the
             IANA.)

             Requests for new values should be made to IANA via
             email (iana@isi.edu)."
        REFERENCE
            "1. Generalized Multi-Protocol Label Switching (GMPLS)
                Signaling Functional Description, RFC 3471, section
                3.1.1.
             2. Generalized MPLS Signalling Extensions for G.709 Optical
                Transport Networks Control, draft-ietf-ccamp-gmpls-g709,
                work in progress, section 3.1.3."
        SYNTAX  INTEGER {
                  unknown(0),      -- unknown or none of the following
                  asynchE4(5),
                  asynchDS3T3(6),
                  asynchE3(7),
                  bitsynchE3(8),
                  bytesynchE3(9),
                  asynchDS2T2(10),
                  bitsynchDS2T2(11),
                  asynchE1(13),
                  bytesynchE1(14),
                  bytesynch31ByDS0(15),
                  asynchDS1T1(16),
                  bitsynchDS1T1(17),
                  bytesynchDS1T1(18),
                  vc1vc12(19),
                  ds1SFAsynch(22),
                  ds1ESFAsynch(23),
                  ds3M23Asynch(24),
                  ds3CBitParityAsynch(25),
                  vtLovc(26),
                  stsSpeHovc(27),
                  posNoScramble16BitCrc(28),
                  posNoScramble32BitCrc(29),
                  posScramble16BitCrc(30),
                  posScramble32BitCrc(31),
                  atm(32),
                  ethernet(33),
                  sdhSonet(34),
                  digitalwrapper(36),
                  lambda(37),
                  ansiEtsiPdh (38),
                  lapsSdh (40),
                  fddi (41),
                  dqdb (42),
                  fiberChannel3 (43),
                  hdlc (44),
                  ethernetV2DixOnly (45),
                  ethernet802dot3Only (46),
                  g709ODUj (47),
                  g709OTUk (48),
                  g709CBRorCBRa (49),
                  g709CBRb (50),
                  g709BSOT (51),
                  g709BSNT (52),
                  gfpIPorPPP (53),
                  gfpEthernetMAC (54),
                  gfpEthernetPHY (55),
                  g709ESCON (56),
                  g709FICON (57),
                  g709FiberChannel (58)
                }

   IANAGmplsAdminStatusInformation ::= TEXTUAL-CONVENTION
       STATUS       current
       DESCRIPTION
            "This data type is used as the syntax of the
             gmplsTunnelAdminStatusFlags object in the definition of
             GMPLS-TE-STD-MIB's gmplsTunnelTable.

             gmplsTunnelAdminStatusFlags determines the setting of the
             Admin Status flags in the Admin Status object or TLV, as
             described in RFC 3471. Setting this object to a non-zero
             value will result in the inclusion of the Admin Status
             object or TLV on signaling messages.

             This textual convention is strongly tied to the Admin
             Status Flags sub-registry of the GMPLS Signaling Parameters
             registry managed by IANA. Values should be assigned by IANA
             in step with the Admin Status Flags sub-registry and using
             the same registry management rules. However, the actual
             values used in this textual convention are solely within
             the purview of IANA and do not necessarily match the values
             in the values in the Admin Status Flags sub-registry.

             The definition of this textual convention with the
             addition of newly assigned values is published
             periodically by the IANA, in either the Assigned
             Numbers RFC, or some derivative of it specific to
             Internet Network Management number assignments. (The
             latest arrangements can be obtained by contacting the
             IANA.)

             Requests for new values should be made to IANA via
             email (iana@isi.edu)."

      REFERENCE
            "1. Generalized Multi-Protocol Label Switching (GMPLS)
                Signaling Functional Description, RFC 3471, section 8."
      SYNTAX  BITS {
                     reflect (0),              -- Reflect bit (RFC 3471)
                     reserved1 (1),            -- reserved
                     reserved2 (2),            -- reserved
                     reserved3 (3),            -- reserved
                     reserved4 (4),            -- reserved
                     reserved5 (5),            -- reserved
                     reserved6 (6),            -- reserved
                     reserved7 (7),            -- reserved
                     reserved8 (8),            -- reserved
                     reserved9 (9),            -- reserved
                     reserved10 (10),          -- reserved
                     reserved11 (11),          -- reserved
                     reserved12 (12),          -- reserved
                     reserved13 (13),          -- reserved
                     reserved14 (14),          -- reserved
                     reserved15 (15),          -- reserved
                     reserved16 (16),          -- reserved
                     reserved17 (17),          -- reserved
                     reserved18 (18),          -- reserved
                     reserved19 (19),          -- reserved
                     reserved20 (20),          -- reserved
                     reserved21 (21),          -- reserved
                     reserved22 (22),          -- reserved
                     reserved23 (23),          -- reserved
                     reserved24 (24),          -- reserved
                     reserved25 (25),          -- reserved
                     reserved26 (26),          -- reserved
                     reserved27 (27),          -- reserved
                     reserved28 (28),          -- reserved
                     testing (29),              -- Testing bit (RFC 3473)
                     administrativelyDown (30), -- Admin down (RFC 3473)
                     deleteInProgress (31)      -- Delete bit (RFC 3473)
                   }

   END
