CPS6000-MIB DEFINITIONS ::= BEGIN
IMPORTS
     enterprises, MODULE-IDENTITY, OBJECT-TYPE, Integer32, NOTIFICATION-TYPE 
         FROM SNMPv2-SMI
     DisplayString
         FROM SNMPv2-TC;


teps                   OBJECT IDENTIFIER ::= { enterprises 10520 }
controllermibs         OBJECT IDENTIFIER ::= { teps 2 }
release                OBJECT IDENTIFIER ::= { controllermibs 1 }
prototypes             OBJECT IDENTIFIER ::= { controllermibs 2 }

cps6000 MODULE-IDENTITY
   LAST-UPDATED "200906181617Z"
   ORGANIZATION "Lineage Power"
   CONTACT-INFO "Chris Brooke - Power Systems

                 Phone: +1 972 284 2000

                 Postal: Power Systems
                         3000 Skyline Dr.
                         Mesquite, TX 75149
                         USA"

   DESCRIPTION "MIB for CPS6000 Power System."

   REVISION "200906181617Z"
   DESCRIPTION "Switch to unique object names"

   REVISION "200905272243Z"
   DESCRIPTION "Add FTTN and other new objects"

   REVISION "200703212156Z"
   DESCRIPTION "Clean up syntax and add units"

   REVISION "200601201618Z"
   DESCRIPTION "Add more data"
   
   REVISION "200510111847Z"
   DESCRIPTION "Initial release"

   ::= { release 1 }

--
-- object cps6000Dc1
--

cps6000Dc1 OBJECT IDENTIFIER  ::= { cps6000  1 }

cps6000Dc1Ide OBJECT-TYPE
SYNTAX      DisplayString
MAX-ACCESS  read-only
STATUS      current
DESCRIPTION
"Identifier"
 ::= { cps6000Dc1  1 }

cps6000Dc1Des OBJECT-TYPE
SYNTAX      DisplayString
MAX-ACCESS  read-write
STATUS      current
DESCRIPTION
"Description"
 ::= { cps6000Dc1  2 }

cps6000Dc1Typ OBJECT-TYPE
SYNTAX      DisplayString
MAX-ACCESS  read-only
STATUS      current
DESCRIPTION
"Type"
 ::= { cps6000Dc1  3 }

cps6000Dc1Stt OBJECT-TYPE
SYNTAX      DisplayString
MAX-ACCESS  read-write
STATUS      current
DESCRIPTION
"State
Values:
FLOAT,
BOOST
"
 ::= { cps6000Dc1  4 }

cps6000Dc1Vdc OBJECT-TYPE
SYNTAX      Integer32
UNITS       "mV"
MAX-ACCESS  read-only
STATUS      current
DESCRIPTION
"Voltage (mV)"
 ::= { cps6000Dc1  5 }

cps6000Dc1Adc OBJECT-TYPE
SYNTAX      Integer32
UNITS       "Amps"
MAX-ACCESS  read-only
STATUS      current
DESCRIPTION
"Current (Amps)"
 ::= { cps6000Dc1  6 }

cps6000Dc1Cap OBJECT-TYPE
SYNTAX      Integer32
UNITS       "Amps"
MAX-ACCESS  read-only
STATUS      current
DESCRIPTION
"Total Installed Rectifier Capacity (Amps)"
 ::= { cps6000Dc1  7 }

cps6000Dc1Olcap OBJECT-TYPE
SYNTAX      Integer32
UNITS       "Amps"
MAX-ACCESS  read-only
STATUS      current
DESCRIPTION
"Total On-line Rectifier Capacity (Amps)"
 ::= { cps6000Dc1  8 }

cps6000Dc1Scap OBJECT-TYPE
SYNTAX      Integer32
UNITS       "Amps"
MAX-ACCESS  read-write
STATUS      current
DESCRIPTION
"String Capacity (Amps)"
 ::= { cps6000Dc1  9 }

cps6000Dc1Nst OBJECT-TYPE
SYNTAX      Integer32
MAX-ACCESS  read-only
STATUS      current
DESCRIPTION
"Number of Strings"
 ::= { cps6000Dc1  10 }

cps6000Dc1Cps OBJECT-TYPE
SYNTAX      Integer32
MAX-ACCESS  read-only
STATUS      current
DESCRIPTION
"Cells per String"
 ::= { cps6000Dc1  11 }

cps6000Dc1Bty OBJECT-TYPE
SYNTAX      DisplayString
MAX-ACCESS  read-only
STATUS      current
DESCRIPTION
"Battery Type"
 ::= { cps6000Dc1  12 }

cps6000Dc1Trd OBJECT-TYPE
SYNTAX      Integer32
UNITS       "Amps"
MAX-ACCESS  read-only
STATUS      current
DESCRIPTION
"Total Rectifier Drain (Amps)"
 ::= { cps6000Dc1  13 }

cps6000Dc1Isd OBJECT-TYPE
SYNTAX      INTEGER {
disable(0),
enable(1)
}
MAX-ACCESS  read-write
STATUS      current
DESCRIPTION
"Imminent Shutdown
Values:
disable(0),
enable(1)
"
 ::= { cps6000Dc1  14 }

cps6000Dc1Bod OBJECT-TYPE
SYNTAX      DisplayString
MAX-ACCESS  read-only
STATUS      current
DESCRIPTION
"Battery On Discharge"
 ::= { cps6000Dc1  15 }

cps6000Dc1Rss OBJECT-TYPE
SYNTAX      INTEGER {
off(0),
on(1)
}
MAX-ACCESS  read-write
STATUS      current
DESCRIPTION
"Rectifier Restart
Values:
off(0),
on(1)
"
 ::= { cps6000Dc1  16 }

cps6000Dc1Rot OBJECT-TYPE
SYNTAX      Integer32(20000..50000)
MAX-ACCESS  read-write
STATUS      current
DESCRIPTION
"All Rectifier On Threshold"
 ::= { cps6000Dc1  17 }

cps6000Dc1Bst OBJECT-TYPE
SYNTAX      DisplayString
MAX-ACCESS  read-only
STATUS      current
DESCRIPTION
"Boost"
 ::= { cps6000Dc1  18 }

cps6000Dc1Amj OBJECT-TYPE
SYNTAX      DisplayString
MAX-ACCESS  read-only
STATUS      current
DESCRIPTION
"Auxiliary Fuse Major
Value:
Alarm report from AMJ1
"
 ::= { cps6000Dc1  19 }

cps6000Dc1Epo OBJECT-TYPE
SYNTAX      DisplayString
MAX-ACCESS  read-only
STATUS      current
DESCRIPTION
"Emergency Power Off
Value:
Alarm report from EPO1
"
 ::= { cps6000Dc1  20 }

cps6000Dc1Faj OBJECT-TYPE
SYNTAX      DisplayString
MAX-ACCESS  read-only
STATUS      current
DESCRIPTION
"External Fuse Major
Value:
Alarm report from FAJ1
"
 ::= { cps6000Dc1  21 }

cps6000Dc1Fan OBJECT-TYPE
SYNTAX      DisplayString
MAX-ACCESS  read-only
STATUS      current
DESCRIPTION
"External Fuse Minor
Value:
Alarm report from FAN1
"
 ::= { cps6000Dc1  22 }

cps6000Dc1Vsf OBJECT-TYPE
SYNTAX      DisplayString
MAX-ACCESS  read-only
STATUS      current
DESCRIPTION
"Sense/Control Fuse
Value:
Alarm report from VSF1
"
 ::= { cps6000Dc1  23 }

cps6000Dc1Osa OBJECT-TYPE
SYNTAX      DisplayString
MAX-ACCESS  read-only
STATUS      current
DESCRIPTION
"Open String
Value:
Alarm report from OSA1
"
 ::= { cps6000Dc1  24 }

cps6000Dc1Zid OBJECT-TYPE
SYNTAX      DisplayString
MAX-ACCESS  read-only
STATUS      current
DESCRIPTION
"ID Not Configured
Value:
Alarm report from ZID1
"
 ::= { cps6000Dc1  25 }

cps6000Dc1Tpa OBJECT-TYPE
SYNTAX      DisplayString
MAX-ACCESS  read-only
STATUS      current
DESCRIPTION
"Thermal Probe Alarm
Value:
Alarm report from TPA1
"
 ::= { cps6000Dc1  26 }

cps6000Dc1Vmf OBJECT-TYPE
SYNTAX      DisplayString
MAX-ACCESS  read-only
STATUS      current
DESCRIPTION
"Voltage Module Fail
Value:
Alarm report from VMF1
"
 ::= { cps6000Dc1  27 }

cps6000Dc1Cma OBJECT-TYPE
SYNTAX      DisplayString
MAX-ACCESS  read-only
STATUS      current
DESCRIPTION
"Minor Communication Failure
Value:
Alarm report from CMA1
"
 ::= { cps6000Dc1  28 }

cps6000Dc1Macf OBJECT-TYPE
SYNTAX      DisplayString
MAX-ACCESS  read-only
STATUS      current
DESCRIPTION
"Multiple AC Failure
Value:
Alarm report from MACF1
"
 ::= { cps6000Dc1  29 }

cps6000Dc1Mcm OBJECT-TYPE
SYNTAX      DisplayString
MAX-ACCESS  read-only
STATUS      current
DESCRIPTION
"Major Communication Failure
Value:
Alarm report from MCM1
"
 ::= { cps6000Dc1  30 }

cps6000Dc1Rfa OBJECT-TYPE
SYNTAX      DisplayString
MAX-ACCESS  read-only
STATUS      current
DESCRIPTION
"Rectifier Fail
Value:
Alarm report from RFA1
"
 ::= { cps6000Dc1  31 }

cps6000Dc1Did OBJECT-TYPE
SYNTAX      DisplayString
MAX-ACCESS  read-only
STATUS      current
DESCRIPTION
"ID Conflict
Value:
Alarm report from DID1
"
 ::= { cps6000Dc1  32 }

cps6000Dc1Clm OBJECT-TYPE
SYNTAX      DisplayString
MAX-ACCESS  read-only
STATUS      current
DESCRIPTION
"Rectifier Current Limit
Value:
Alarm report from CLM1
"
 ::= { cps6000Dc1  33 }

cps6000Dc1Vla OBJECT-TYPE
SYNTAX      DisplayString
MAX-ACCESS  read-only
STATUS      current
DESCRIPTION
"Very Low Voltage
Value:
Alarm report from VLA1
"
 ::= { cps6000Dc1  34 }

cps6000Dc1Acf OBJECT-TYPE
SYNTAX      DisplayString
MAX-ACCESS  read-only
STATUS      current
DESCRIPTION
"AC Fail
Value:
Alarm report from ACF1
"
 ::= { cps6000Dc1  35 }

cps6000Dc1Man OBJECT-TYPE
SYNTAX      DisplayString
MAX-ACCESS  read-only
STATUS      current
DESCRIPTION
"Manual Off
Value:
Alarm report from MAN1
"
 ::= { cps6000Dc1  36 }

cps6000Dc1Mman OBJECT-TYPE
SYNTAX      DisplayString
MAX-ACCESS  read-only
STATUS      current
DESCRIPTION
"Multiple Manual Off
Value:
Alarm report from MMAN1
"
 ::= { cps6000Dc1  37 }

cps6000Dc1Mfa OBJECT-TYPE
SYNTAX      DisplayString
MAX-ACCESS  read-only
STATUS      current
DESCRIPTION
"Multiple Rectifier Fail
Value:
Alarm report from MFA1
"
 ::= { cps6000Dc1  38 }

cps6000Dc1Rtl OBJECT-TYPE
SYNTAX      DisplayString
MAX-ACCESS  read-only
STATUS      current
DESCRIPTION
"Reserve Time Low
Value:
Alarm report from RTL1
"
 ::= { cps6000Dc1  39 }

cps6000Dc1Rrtl OBJECT-TYPE
SYNTAX      DisplayString
MAX-ACCESS  read-only
STATUS      current
DESCRIPTION
"Real-time Reserve Time Low
Value:
Alarm report from RRTL1
"
 ::= { cps6000Dc1  40 }

cps6000Dc1Rls OBJECT-TYPE
SYNTAX      DisplayString
MAX-ACCESS  read-only
STATUS      current
DESCRIPTION
"Redundancy Loss
Value:
Alarm report from RLS1
"
 ::= { cps6000Dc1  41 }

cps6000Dc1Bda OBJECT-TYPE
SYNTAX      DisplayString
MAX-ACCESS  read-only
STATUS      current
DESCRIPTION
"Battery On Discharge
Value:
Alarm report from BDA1
"
 ::= { cps6000Dc1  42 }

cps6000Dc1Hva OBJECT-TYPE
SYNTAX      DisplayString
MAX-ACCESS  read-only
STATUS      current
DESCRIPTION
"High Voltage
Value:
Alarm report from HVA1
"
 ::= { cps6000Dc1  43 }

cps6000Dc1Hfv OBJECT-TYPE
SYNTAX      DisplayString
MAX-ACCESS  read-only
STATUS      current
DESCRIPTION
"High Float Voltage
Value:
Alarm report from HFV1
"
 ::= { cps6000Dc1  44 }

cps6000Dc1Ron OBJECT-TYPE
SYNTAX      Integer32
MAX-ACCESS  read-write
STATUS      current
DESCRIPTION
"External Standby"
 ::= { cps6000Dc1  45 }

cps6000Dc1Rsq OBJECT-TYPE
SYNTAX      INTEGER {
disable(0),
enable(1)
}
MAX-ACCESS  read-write
STATUS      current
DESCRIPTION
"Rectifier Sequencing
Values:
disable(0),
enable(1)
"
 ::= { cps6000Dc1  46 }

cps6000Dc1Rtm OBJECT-TYPE
SYNTAX      DisplayString
MAX-ACCESS  read-only
STATUS      current
DESCRIPTION
"Reserve Time"
 ::= { cps6000Dc1  47 }

cps6000Dc1Icr OBJECT-TYPE
SYNTAX      DisplayString
MAX-ACCESS  read-only
STATUS      current
DESCRIPTION
"Incompatible Rectifier
Value:
Alarm report from ICR1
"
 ::= { cps6000Dc1  48 }

cps6000Dc1Rfn OBJECT-TYPE
SYNTAX      DisplayString
MAX-ACCESS  read-only
STATUS      current
DESCRIPTION
"Rectifier Fan Fail
Value:
Alarm report from RFN1
"
 ::= { cps6000Dc1  49 }

cps6000Dc1Emd OBJECT-TYPE
SYNTAX      DisplayString
MAX-ACCESS  read-only
STATUS      current
DESCRIPTION
"Energy Management Disabled
Value:
Alarm report from EMD1
"
 ::= { cps6000Dc1  50 }

cps6000Dc1Mls OBJECT-TYPE
SYNTAX      INTEGER {
disable(0),
enable(1)
}
MAX-ACCESS  read-write
STATUS      current
DESCRIPTION
"All Shunts Monitored
Values:
disable(0),
enable(1)
"
 ::= { cps6000Dc1  51 }

cps6000Dc1Bdt OBJECT-TYPE
SYNTAX      DisplayString
MAX-ACCESS  read-only
STATUS      current
DESCRIPTION
"BD Duration"
 ::= { cps6000Dc1  52 }

cps6000Dc1Ems OBJECT-TYPE
SYNTAX      DisplayString
MAX-ACCESS  read-only
STATUS      current
DESCRIPTION
"Energy Management State"
 ::= { cps6000Dc1  53 }

cps6000Dc1Eme OBJECT-TYPE
SYNTAX      INTEGER {
disable(0),
enable(1)
}
MAX-ACCESS  read-write
STATUS      current
DESCRIPTION
"Energy Management Enable
Values:
disable(0),
enable(1)
"
 ::= { cps6000Dc1  54 }

cps6000Dc1Emt OBJECT-TYPE
SYNTAX      Integer32(20..95)
UNITS       "%"
MAX-ACCESS  read-write
STATUS      current
DESCRIPTION
"Efficiency Target (%)"
 ::= { cps6000Dc1  55 }

cps6000Dc1Emo OBJECT-TYPE
SYNTAX      Integer32(25..100)
UNITS       "%"
MAX-ACCESS  read-write
STATUS      current
DESCRIPTION
"Efficiency Rectifier Turn On Threshold (%)"
 ::= { cps6000Dc1  56 }

cps6000Dc1Poc OBJECT-TYPE
SYNTAX      DisplayString
UNITS       "%"
MAX-ACCESS  read-only
STATUS      current
DESCRIPTION
"Percent of Charge (%)"
 ::= { cps6000Dc1  57 }

cps6000Dc1Lsf OBJECT-TYPE
SYNTAX      DisplayString
MAX-ACCESS  read-only
STATUS      current
DESCRIPTION
"Loadshare Fail
Value:
Alarm report from LSF1
"
 ::= { cps6000Dc1  58 }


--
-- object cps6000Ps1
--

cps6000Ps1 OBJECT IDENTIFIER  ::= { cps6000  2 }

cps6000Ps1Ide OBJECT-TYPE
SYNTAX      DisplayString
MAX-ACCESS  read-only
STATUS      current
DESCRIPTION
"Identifier"
 ::= { cps6000Ps1  1 }

cps6000Ps1Des OBJECT-TYPE
SYNTAX      DisplayString
MAX-ACCESS  read-write
STATUS      current
DESCRIPTION
"Description"
 ::= { cps6000Ps1  2 }

cps6000Ps1Sid OBJECT-TYPE
SYNTAX      DisplayString
MAX-ACCESS  read-write
STATUS      current
DESCRIPTION
"Site ID"
 ::= { cps6000Ps1  3 }

cps6000Ps1Sde OBJECT-TYPE
SYNTAX      DisplayString
MAX-ACCESS  read-write
STATUS      current
DESCRIPTION
"Site Description"
 ::= { cps6000Ps1  4 }

cps6000Ps1Swv OBJECT-TYPE
SYNTAX      DisplayString
MAX-ACCESS  read-only
STATUS      current
DESCRIPTION
"Software Version"
 ::= { cps6000Ps1  5 }

cps6000Ps1Verb OBJECT-TYPE
SYNTAX      DisplayString
MAX-ACCESS  read-only
STATUS      current
DESCRIPTION
"Boot Block Version"
 ::= { cps6000Ps1  6 }

cps6000Ps1Verw OBJECT-TYPE
SYNTAX      DisplayString
MAX-ACCESS  read-only
STATUS      current
DESCRIPTION
"Web Page Version"
 ::= { cps6000Ps1  7 }

cps6000Ps1Verd OBJECT-TYPE
SYNTAX      DisplayString
MAX-ACCESS  read-only
STATUS      current
DESCRIPTION
"Display Version"
 ::= { cps6000Ps1  8 }

cps6000Ps1Dflt OBJECT-TYPE
SYNTAX      DisplayString
MAX-ACCESS  read-only
STATUS      current
DESCRIPTION
"Defaults Version"
 ::= { cps6000Ps1  9 }

cps6000Ps1Brc OBJECT-TYPE
SYNTAX      DisplayString
MAX-ACCESS  read-only
STATUS      current
DESCRIPTION
"Board Code"
 ::= { cps6000Ps1  10 }

cps6000Ps1Sn OBJECT-TYPE
SYNTAX      DisplayString
MAX-ACCESS  read-only
STATUS      current
DESCRIPTION
"Serial Number"
 ::= { cps6000Ps1  11 }

cps6000Ps1Usl OBJECT-TYPE
SYNTAX      INTEGER {
uninstall(1)
}
MAX-ACCESS  read-write
STATUS      current
DESCRIPTION
"Uninstall Missing Equipment
Values:
uninstall(1)
"
 ::= { cps6000Ps1  12 }

cps6000Ps1Dat OBJECT-TYPE
SYNTAX      DisplayString
MAX-ACCESS  read-write
STATUS      current
DESCRIPTION
"System Date"
 ::= { cps6000Ps1  13 }

cps6000Ps1Dtf OBJECT-TYPE
SYNTAX      DisplayString
MAX-ACCESS  read-write
STATUS      current
DESCRIPTION
"Date Format
Values:
mm/dd/yyyy,
dd/mm/yyyy,
yyyy/mm/dd
"
 ::= { cps6000Ps1  14 }

cps6000Ps1Tim OBJECT-TYPE
SYNTAX      DisplayString
MAX-ACCESS  read-write
STATUS      current
DESCRIPTION
"System Time"
 ::= { cps6000Ps1  15 }

cps6000Ps1Tmf OBJECT-TYPE
SYNTAX      INTEGER {
h12(12),
h24(24)
}
MAX-ACCESS  read-write
STATUS      current
DESCRIPTION
"System Time Format
Values:
h12(12),
h24(24)
"
 ::= { cps6000Ps1  16 }

cps6000Ps1Dls OBJECT-TYPE
SYNTAX      INTEGER {
off(0),
on(1)
}
MAX-ACCESS  read-write
STATUS      current
DESCRIPTION
"Daylight Savings
Values:
off(0),
on(1)
"
 ::= { cps6000Ps1  17 }

cps6000Ps1Lng OBJECT-TYPE
SYNTAX      DisplayString
MAX-ACCESS  read-write
STATUS      current
DESCRIPTION
"Front Panel Language"
 ::= { cps6000Ps1  18 }

cps6000Ps1Ptt OBJECT-TYPE
SYNTAX      DisplayString
MAX-ACCESS  read-write
STATUS      current
DESCRIPTION
"Communication Port Type
Values:
LOCAL,
MODEM
"
 ::= { cps6000Ps1  19 }

cps6000Ps1Amt OBJECT-TYPE
SYNTAX      DisplayString
UNITS       "C"
MAX-ACCESS  read-only
STATUS      current
DESCRIPTION
"Ambient Temperature (C)"
 ::= { cps6000Ps1  20 }

cps6000Ps1Tun OBJECT-TYPE
SYNTAX      DisplayString
MAX-ACCESS  read-write
STATUS      current
DESCRIPTION
"Temperature Units
Values:
C,
F
"
 ::= { cps6000Ps1  21 }

cps6000Ps1Usr OBJECT-TYPE
SYNTAX      INTEGER {
disable(0),
enable(1)
}
MAX-ACCESS  read-write
STATUS      current
DESCRIPTION
"Enable User Accounts
Values:
disable(0),
enable(1)
"
 ::= { cps6000Ps1  22 }

cps6000Ps1Poe OBJECT-TYPE
SYNTAX      INTEGER {
disable(0),
enable(1)
}
MAX-ACCESS  read-write
STATUS      current
DESCRIPTION
"Power Off Enable
Values:
disable(0),
enable(1)
"
 ::= { cps6000Ps1  23 }

cps6000Ps1Fpc OBJECT-TYPE
SYNTAX      INTEGER {
disable(0),
enable(1)
}
MAX-ACCESS  read-write
STATUS      current
DESCRIPTION
"Front Panel Configuration
Values:
disable(0),
enable(1)
"
 ::= { cps6000Ps1  24 }

cps6000Ps1Rrf OBJECT-TYPE
SYNTAX      INTEGER {
disable(0),
enable(1)
}
MAX-ACCESS  read-write
STATUS      current
DESCRIPTION
"Remote Rectifier Off
Values:
disable(0),
enable(1)
"
 ::= { cps6000Ps1  25 }

cps6000Ps1Amth OBJECT-TYPE
SYNTAX      DisplayString
MAX-ACCESS  read-only
STATUS      current
DESCRIPTION
"High Ambient Temperature
Value:
Alarm report from AMTH1
"
 ::= { cps6000Ps1  26 }

cps6000Ps1Amtl OBJECT-TYPE
SYNTAX      DisplayString
MAX-ACCESS  read-only
STATUS      current
DESCRIPTION
"Low Ambient Temperature
Value:
Alarm report from AMTL1
"
 ::= { cps6000Ps1  27 }

cps6000Ps1Bbl OBJECT-TYPE
SYNTAX      DisplayString
MAX-ACCESS  read-only
STATUS      current
DESCRIPTION
"Memory Backup Battery Low
Value:
Alarm report from BBL1
"
 ::= { cps6000Ps1  28 }

cps6000Ps1Cch OBJECT-TYPE
SYNTAX      DisplayString
MAX-ACCESS  read-only
STATUS      current
DESCRIPTION
"Configuration Changed
Value:
Alarm report from CCH1
"
 ::= { cps6000Ps1  29 }

cps6000Ps1Clc OBJECT-TYPE
SYNTAX      DisplayString
MAX-ACCESS  read-only
STATUS      current
DESCRIPTION
"Clock Changed
Value:
Alarm report from CLC1
"
 ::= { cps6000Ps1  30 }

cps6000Ps1Epr OBJECT-TYPE
SYNTAX      DisplayString
MAX-ACCESS  read-only
STATUS      current
DESCRIPTION
"External Password Reset
Value:
Alarm report from EPR1
"
 ::= { cps6000Ps1  31 }

cps6000Ps1Exl OBJECT-TYPE
SYNTAX      DisplayString
MAX-ACCESS  read-only
STATUS      current
DESCRIPTION
"Excessive Login Attempts
Value:
Alarm report from EXL1
"
 ::= { cps6000Ps1  32 }

cps6000Ps1Hcl OBJECT-TYPE
SYNTAX      DisplayString
MAX-ACCESS  read-only
STATUS      current
DESCRIPTION
"History Cleared
Value:
Alarm report from HCL1
"
 ::= { cps6000Ps1  33 }

cps6000Ps1Pfd OBJECT-TYPE
SYNTAX      DisplayString
MAX-ACCESS  read-only
STATUS      current
DESCRIPTION
"Passwords At Default
Value:
Alarm report from PFD1
"
 ::= { cps6000Ps1  34 }

cps6000Ps1Pht OBJECT-TYPE
SYNTAX      DisplayString
MAX-ACCESS  read-only
STATUS      current
DESCRIPTION
"Processor Halt
Value:
Alarm report from PHT1
"
 ::= { cps6000Ps1  35 }

cps6000Ps1Stf OBJECT-TYPE
SYNTAX      DisplayString
MAX-ACCESS  read-only
STATUS      current
DESCRIPTION
"Self Test Failed
Value:
Alarm report from STF1
"
 ::= { cps6000Ps1  36 }

cps6000Ps1Pgi OBJECT-TYPE
SYNTAX      DisplayString
MAX-ACCESS  read-only
STATUS      current
DESCRIPTION
"Program Line Invalid
Value:
Alarm report from PGI1
"
 ::= { cps6000Ps1  37 }

cps6000Ps1Ax1 OBJECT-TYPE
SYNTAX      DisplayString
MAX-ACCESS  read-only
STATUS      current
DESCRIPTION
"Auxilliary Event 1
Value:
Alarm report from AUX1
"
 ::= { cps6000Ps1  38 }

cps6000Ps1Ax2 OBJECT-TYPE
SYNTAX      DisplayString
MAX-ACCESS  read-only
STATUS      current
DESCRIPTION
"Auxilliary Event 1
Value:
Alarm report from AUX2
"
 ::= { cps6000Ps1  39 }

cps6000Ps1Ax3 OBJECT-TYPE
SYNTAX      DisplayString
MAX-ACCESS  read-only
STATUS      current
DESCRIPTION
"Auxilliary Event 1
Value:
Alarm report from AUX3
"
 ::= { cps6000Ps1  40 }

cps6000Ps1Ax4 OBJECT-TYPE
SYNTAX      DisplayString
MAX-ACCESS  read-only
STATUS      current
DESCRIPTION
"Auxilliary Event 1
Value:
Alarm report from AUX4
"
 ::= { cps6000Ps1  41 }

cps6000Ps1Ax5 OBJECT-TYPE
SYNTAX      DisplayString
MAX-ACCESS  read-only
STATUS      current
DESCRIPTION
"Auxilliary Event 1
Value:
Alarm report from AUX5
"
 ::= { cps6000Ps1  42 }

cps6000Ps1Ax6 OBJECT-TYPE
SYNTAX      DisplayString
MAX-ACCESS  read-only
STATUS      current
DESCRIPTION
"Auxilliary Event 1
Value:
Alarm report from AUX6
"
 ::= { cps6000Ps1  43 }

cps6000Ps1Rss OBJECT-TYPE
SYNTAX      INTEGER {
restart(1)
}
MAX-ACCESS  read-write
STATUS      current
DESCRIPTION
"Restart Devices
Values:
restart(1)
"
 ::= { cps6000Ps1  44 }

cps6000Ps1Sys OBJECT-TYPE
SYNTAX      DisplayString
MAX-ACCESS  read-write
STATUS      current
DESCRIPTION
"System Description"
 ::= { cps6000Ps1  45 }

cps6000Ps1Lngl OBJECT-TYPE
SYNTAX      DisplayString
MAX-ACCESS  read-only
STATUS      current
DESCRIPTION
"Available Languages"
 ::= { cps6000Ps1  46 }

cps6000Ps1Fst OBJECT-TYPE
SYNTAX      DisplayString
MAX-ACCESS  read-write
STATUS      current
DESCRIPTION
"Factory Defaults"
 ::= { cps6000Ps1  47 }

cps6000Ps1Fstl OBJECT-TYPE
SYNTAX      DisplayString
MAX-ACCESS  read-only
STATUS      current
DESCRIPTION
"Factory Defaults List"
 ::= { cps6000Ps1  48 }

cps6000Ps1Fpe OBJECT-TYPE
SYNTAX      INTEGER {
disable(0),
enable(1)
}
MAX-ACCESS  read-write
STATUS      current
DESCRIPTION
"Front Panel Pin Enable
Values:
disable(0),
enable(1)
"
 ::= { cps6000Ps1  49 }

cps6000Ps1Fpt OBJECT-TYPE
SYNTAX      Integer32
MAX-ACCESS  read-write
STATUS      current
DESCRIPTION
"Front Panel Pin Timeout"
 ::= { cps6000Ps1  50 }

cps6000Ps1Ast OBJECT-TYPE
SYNTAX      DisplayString
MAX-ACCESS  read-only
STATUS      current
DESCRIPTION
"System Alarm State"
 ::= { cps6000Ps1  51 }

cps6000Ps1Dss OBJECT-TYPE
SYNTAX      DisplayString
MAX-ACCESS  read-write
STATUS      current
DESCRIPTION
"Daylight Saving Start mon:wk:dow:min or, mon:-1:dom:min"
 ::= { cps6000Ps1  52 }

cps6000Ps1Dse OBJECT-TYPE
SYNTAX      DisplayString
MAX-ACCESS  read-write
STATUS      current
DESCRIPTION
"Daylight Saving End mon:wk:dow:min or, mon:-1:dom:min"
 ::= { cps6000Ps1  53 }


--
-- object cps6000At1
--

cps6000At1 OBJECT IDENTIFIER  ::= { cps6000  3 }

cps6000At1Ide OBJECT-TYPE
SYNTAX      DisplayString
MAX-ACCESS  read-only
STATUS      current
DESCRIPTION
"Identifier"
 ::= { cps6000At1  1 }

cps6000At1Des OBJECT-TYPE
SYNTAX      DisplayString
MAX-ACCESS  read-write
STATUS      current
DESCRIPTION
"Description"
 ::= { cps6000At1  2 }

cps6000At1Stt OBJECT-TYPE
SYNTAX      INTEGER {
inactive(0),
active(1)
}
MAX-ACCESS  read-write
STATUS      current
DESCRIPTION
"Alarm Test Active
Values:
inactive(0),
active(1)
"
 ::= { cps6000At1  3 }

cps6000At1Stg OBJECT-TYPE
SYNTAX      DisplayString
MAX-ACCESS  read-only
STATUS      current
DESCRIPTION
"Stage"
 ::= { cps6000At1  4 }

cps6000At1Lte OBJECT-TYPE
SYNTAX      INTEGER {
disable(0),
enable(1)
}
MAX-ACCESS  read-write
STATUS      current
DESCRIPTION
"Alarm Test Enable
Values:
disable(0),
enable(1)
"
 ::= { cps6000At1  5 }

cps6000At1Dur OBJECT-TYPE
SYNTAX      Integer32(5..300)
UNITS       "Seconds"
MAX-ACCESS  read-write
STATUS      current
DESCRIPTION
"Alarm Contact Duration (Seconds)"
 ::= { cps6000At1  6 }

cps6000At1Pmj OBJECT-TYPE
SYNTAX      INTEGER {
no(0),
yes(1)
}
MAX-ACCESS  read-write
STATUS      current
DESCRIPTION
"Power Major
Values:
no(0),
yes(1)
"
 ::= { cps6000At1  7 }

cps6000At1Pmn OBJECT-TYPE
SYNTAX      INTEGER {
no(0),
yes(1)
}
MAX-ACCESS  read-write
STATUS      current
DESCRIPTION
"Power Minor
Values:
no(0),
yes(1)
"
 ::= { cps6000At1  8 }

cps6000At1R1 OBJECT-TYPE
SYNTAX      INTEGER {
no(0),
yes(1)
}
MAX-ACCESS  read-write
STATUS      current
DESCRIPTION
"Test Relay 1
Values:
no(0),
yes(1)
"
 ::= { cps6000At1  9 }

cps6000At1R2 OBJECT-TYPE
SYNTAX      INTEGER {
no(0),
yes(1)
}
MAX-ACCESS  read-write
STATUS      current
DESCRIPTION
"Test Relay 2
Values:
no(0),
yes(1)
"
 ::= { cps6000At1  10 }

cps6000At1R3 OBJECT-TYPE
SYNTAX      INTEGER {
no(0),
yes(1)
}
MAX-ACCESS  read-write
STATUS      current
DESCRIPTION
"Test Relay 3
Values:
no(0),
yes(1)
"
 ::= { cps6000At1  11 }

cps6000At1R4 OBJECT-TYPE
SYNTAX      INTEGER {
no(0),
yes(1)
}
MAX-ACCESS  read-write
STATUS      current
DESCRIPTION
"Test Relay 4
Values:
no(0),
yes(1)
"
 ::= { cps6000At1  12 }

cps6000At1Ata OBJECT-TYPE
SYNTAX      DisplayString
MAX-ACCESS  read-only
STATUS      current
DESCRIPTION
"Alarm Test Active
Value:
Alarm report from ATA1
"
 ::= { cps6000At1  13 }

cps6000At1Atb OBJECT-TYPE
SYNTAX      DisplayString
MAX-ACCESS  read-only
STATUS      current
DESCRIPTION
"Alarm Test Aborted
Value:
Alarm report from ATB1
"
 ::= { cps6000At1  14 }

cps6000At1Ets OBJECT-TYPE
SYNTAX      INTEGER {
start(1)
}
MAX-ACCESS  read-write
STATUS      current
DESCRIPTION
"Do Email Test
Values:
start(1)
"
 ::= { cps6000At1  15 }

cps6000At1Ems OBJECT-TYPE
SYNTAX      DisplayString
MAX-ACCESS  read-only
STATUS      current
DESCRIPTION
"Email Test Results"
 ::= { cps6000At1  16 }

cps6000At1Irt OBJECT-TYPE
SYNTAX      DisplayString
MAX-ACCESS  read-write
STATUS      current
DESCRIPTION
"Individual Relay Test State
Values:
,
PMJ,
PMN,
R1,
R2,
R3,
R4
"
 ::= { cps6000At1  17 }


--
-- object cps6000Dct1
--

cps6000Dct1 OBJECT IDENTIFIER  ::= { cps6000  4 }

cps6000Dct1Ide OBJECT-TYPE
SYNTAX      DisplayString
MAX-ACCESS  read-only
STATUS      current
DESCRIPTION
"Identifier"
 ::= { cps6000Dct1  1 }

cps6000Dct1Des OBJECT-TYPE
SYNTAX      DisplayString
MAX-ACCESS  read-write
STATUS      current
DESCRIPTION
"Description"
 ::= { cps6000Dct1  2 }

cps6000Dct1Src OBJECT-TYPE
SYNTAX      DisplayString
MAX-ACCESS  read-write
STATUS      current
DESCRIPTION
"Source"
 ::= { cps6000Dct1  3 }


--
-- object cps6000Gm1
--

cps6000Gm1 OBJECT IDENTIFIER  ::= { cps6000  5 }

cps6000Gm1Ide OBJECT-TYPE
SYNTAX      DisplayString
MAX-ACCESS  read-only
STATUS      current
DESCRIPTION
"Identifier"
 ::= { cps6000Gm1  1 }

cps6000Gm1Des OBJECT-TYPE
SYNTAX      DisplayString
MAX-ACCESS  read-write
STATUS      current
DESCRIPTION
"Description"
 ::= { cps6000Gm1  2 }

cps6000Gm1Lse OBJECT-TYPE
SYNTAX      INTEGER {
disable(0),
enable(1)
}
MAX-ACCESS  read-write
STATUS      current
DESCRIPTION
"Load Share Enable
Values:
disable(0),
enable(1)
"
 ::= { cps6000Gm1  3 }

cps6000Gm1Fsd OBJECT-TYPE
SYNTAX      Integer32(25000..60000)
UNITS       "mV"
MAX-ACCESS  read-write
STATUS      current
DESCRIPTION
"Float High Voltage Shutdown (mV)"
 ::= { cps6000Gm1  4 }

cps6000Gm1Bsd OBJECT-TYPE
SYNTAX      Integer32(26000..60000)
UNITS       "mV"
MAX-ACCESS  read-write
STATUS      current
DESCRIPTION
"Boost High Voltage Shutdown (mV)"
 ::= { cps6000Gm1  5 }

cps6000Gm1Fsp OBJECT-TYPE
SYNTAX      Integer32(22000..56000)
UNITS       "mV"
MAX-ACCESS  read-write
STATUS      current
DESCRIPTION
"Float Set Point (mV)"
 ::= { cps6000Gm1  6 }

cps6000Gm1Bsp OBJECT-TYPE
SYNTAX      Integer32(22000..60000)
UNITS       "mV"
MAX-ACCESS  read-write
STATUS      current
DESCRIPTION
"Boost Set Point (mV)"
 ::= { cps6000Gm1  7 }

cps6000Gm1Fcl OBJECT-TYPE
SYNTAX      Integer32(30..110)
UNITS       "%"
MAX-ACCESS  read-write
STATUS      current
DESCRIPTION
"Float Current Limit (%)"
 ::= { cps6000Gm1  8 }

cps6000Gm1Bcl OBJECT-TYPE
SYNTAX      Integer32(30..110)
UNITS       "%"
MAX-ACCESS  read-write
STATUS      current
DESCRIPTION
"Boost Current Limit (%)"
 ::= { cps6000Gm1  9 }

cps6000Gm1Rme OBJECT-TYPE
SYNTAX      INTEGER {
disable(0),
enable(1)
}
MAX-ACCESS  read-write
STATUS      current
DESCRIPTION
"Redundancy Monitor
Values:
disable(0),
enable(1)
"
 ::= { cps6000Gm1  10 }


--
-- table REC
--

cps6000RecTable    OBJECT-TYPE
SYNTAX SEQUENCE OF Cps6000RecEntry
MAX-ACCESS not-accessible
STATUS current
DESCRIPTION
        "Table of all Rectifier data"
 ::= { cps6000  6 }

cps6000RecEntry OBJECT-TYPE
SYNTAX     Cps6000RecEntry
MAX-ACCESS  not-accessible
STATUS      current
DESCRIPTION
       "Entry of information for one Rectifier"
INDEX { cps6000RecEntryIndex }
 ::= { cps6000RecTable  1 }

Cps6000RecEntry ::= SEQUENCE {
cps6000RecEntryIndex   INTEGER,
cps6000RecEntryIde   DisplayString,
cps6000RecEntryDes   DisplayString,
cps6000RecEntryTyp   DisplayString,
cps6000RecEntryAdc   DisplayString,
cps6000RecEntryVdc   DisplayString,
cps6000RecEntryStt   DisplayString,
cps6000RecEntryCap   DisplayString,
cps6000RecEntryTmp   DisplayString,
cps6000RecEntrySeq   INTEGER,
cps6000RecEntryRfa   DisplayString,
cps6000RecEntryAcf   DisplayString,
cps6000RecEntryMan   DisplayString,
cps6000RecEntryDid   DisplayString,
cps6000RecEntryClm   DisplayString,
cps6000RecEntryRcf   DisplayString,
cps6000RecEntryRfn   DisplayString,
cps6000RecEntrySn   DisplayString,
cps6000RecEntryVac   Integer32,
cps6000RecEntryAac   Integer32
}

cps6000RecEntryIndex OBJECT-TYPE
SYNTAX      INTEGER (0..2147483647)
MAX-ACCESS  read-only
STATUS      current
DESCRIPTION
"Table Index"
 ::= { cps6000RecEntry  1 }

cps6000RecEntryIde OBJECT-TYPE
SYNTAX      DisplayString
MAX-ACCESS  read-only
STATUS      current
DESCRIPTION
"Identifier"
 ::= { cps6000RecEntry  2 }

cps6000RecEntryDes OBJECT-TYPE
SYNTAX      DisplayString
MAX-ACCESS  read-write
STATUS      current
DESCRIPTION
"Description"
 ::= { cps6000RecEntry  3 }

cps6000RecEntryTyp OBJECT-TYPE
SYNTAX      DisplayString
MAX-ACCESS  read-write
STATUS      current
DESCRIPTION
"Type"
 ::= { cps6000RecEntry  4 }

cps6000RecEntryAdc OBJECT-TYPE
SYNTAX      DisplayString
UNITS       "Amps"
MAX-ACCESS  read-only
STATUS      current
DESCRIPTION
"DC Current (Amps)"
 ::= { cps6000RecEntry  5 }

cps6000RecEntryVdc OBJECT-TYPE
SYNTAX      DisplayString
UNITS       "Volts"
MAX-ACCESS  read-only
STATUS      current
DESCRIPTION
"DC Voltage (Volts)"
 ::= { cps6000RecEntry  6 }

cps6000RecEntryStt OBJECT-TYPE
SYNTAX      DisplayString
MAX-ACCESS  read-write
STATUS      current
DESCRIPTION
"State
Values:
ON,
OFF,
STANDBY,
VACANT
"
 ::= { cps6000RecEntry  7 }

cps6000RecEntryCap OBJECT-TYPE
SYNTAX      DisplayString
UNITS       "Amps"
MAX-ACCESS  read-only
STATUS      current
DESCRIPTION
"Capacity (Amps)"
 ::= { cps6000RecEntry  8 }

cps6000RecEntryTmp OBJECT-TYPE
SYNTAX      DisplayString
UNITS       "C"
MAX-ACCESS  read-only
STATUS      current
DESCRIPTION
"Temperature (C)"
 ::= { cps6000RecEntry  9 }

cps6000RecEntrySeq OBJECT-TYPE
SYNTAX      INTEGER {
no(0),
yes(1)
}
MAX-ACCESS  read-write
STATUS      current
DESCRIPTION
"Use in Sequence Enable
Values:
no(0),
yes(1)
"
 ::= { cps6000RecEntry  10 }

cps6000RecEntryRfa OBJECT-TYPE
SYNTAX      DisplayString
MAX-ACCESS  read-only
STATUS      current
DESCRIPTION
"Rectifier Fail"
 ::= { cps6000RecEntry  11 }

cps6000RecEntryAcf OBJECT-TYPE
SYNTAX      DisplayString
MAX-ACCESS  read-only
STATUS      current
DESCRIPTION
"AC Fail"
 ::= { cps6000RecEntry  12 }

cps6000RecEntryMan OBJECT-TYPE
SYNTAX      DisplayString
MAX-ACCESS  read-only
STATUS      current
DESCRIPTION
"Standby or Manual Off"
 ::= { cps6000RecEntry  13 }

cps6000RecEntryDid OBJECT-TYPE
SYNTAX      DisplayString
MAX-ACCESS  read-only
STATUS      current
DESCRIPTION
"ID Conflict"
 ::= { cps6000RecEntry  14 }

cps6000RecEntryClm OBJECT-TYPE
SYNTAX      DisplayString
MAX-ACCESS  read-only
STATUS      current
DESCRIPTION
"Current Limit"
 ::= { cps6000RecEntry  15 }

cps6000RecEntryRcf OBJECT-TYPE
SYNTAX      DisplayString
MAX-ACCESS  read-only
STATUS      current
DESCRIPTION
"Communication Failure"
 ::= { cps6000RecEntry  16 }

cps6000RecEntryRfn OBJECT-TYPE
SYNTAX      DisplayString
MAX-ACCESS  read-only
STATUS      current
DESCRIPTION
"Fan Failure"
 ::= { cps6000RecEntry  17 }

cps6000RecEntrySn OBJECT-TYPE
SYNTAX      DisplayString
MAX-ACCESS  read-only
STATUS      current
DESCRIPTION
"Serial Number"
 ::= { cps6000RecEntry  18 }

cps6000RecEntryVac OBJECT-TYPE
SYNTAX      Integer32
UNITS       "Volts"
MAX-ACCESS  read-only
STATUS      current
DESCRIPTION
"AC Voltage (Volts)"
 ::= { cps6000RecEntry  19 }

cps6000RecEntryAac OBJECT-TYPE
SYNTAX      Integer32
UNITS       "mA"
MAX-ACCESS  read-only
STATUS      current
DESCRIPTION
"AC Current (mA)"
 ::= { cps6000RecEntry  20 }



--
-- object cps6000Cp1
--

cps6000Cp1 OBJECT IDENTIFIER  ::= { cps6000  7 }

cps6000Cp1Ide OBJECT-TYPE
SYNTAX      DisplayString
MAX-ACCESS  read-only
STATUS      current
DESCRIPTION
"Identifier"
 ::= { cps6000Cp1  1 }

cps6000Cp1Des OBJECT-TYPE
SYNTAX      DisplayString
MAX-ACCESS  read-write
STATUS      current
DESCRIPTION
"Description"
 ::= { cps6000Cp1  2 }

cps6000Cp1Vdc OBJECT-TYPE
SYNTAX      DisplayString
UNITS       "Volts"
MAX-ACCESS  read-only
STATUS      current
DESCRIPTION
"DC Voltage (Volts)"
 ::= { cps6000Cp1  3 }

cps6000Cp1Adc OBJECT-TYPE
SYNTAX      DisplayString
UNITS       "Amps"
MAX-ACCESS  read-only
STATUS      current
DESCRIPTION
"DC Current (Amps)"
 ::= { cps6000Cp1  4 }

cps6000Cp1Cap OBJECT-TYPE
SYNTAX      DisplayString
UNITS       "Amps"
MAX-ACCESS  read-only
STATUS      current
DESCRIPTION
"Capacity (Amps)"
 ::= { cps6000Cp1  5 }

cps6000Cp1Vsp OBJECT-TYPE
SYNTAX      Integer32(48000..52000)
UNITS       "mV"
MAX-ACCESS  read-write
STATUS      current
DESCRIPTION
"Voltage Set Point (mV)"
 ::= { cps6000Cp1  6 }

cps6000Cp1Dth OBJECT-TYPE
SYNTAX      Integer32(20000..25000)
UNITS       "mV"
MAX-ACCESS  read-write
STATUS      current
DESCRIPTION
"Low Voltage Disconnect (mV)"
 ::= { cps6000Cp1  7 }

cps6000Cp1Rth OBJECT-TYPE
SYNTAX      Integer32(22000..27000)
UNITS       "mV"
MAX-ACCESS  read-write
STATUS      current
DESCRIPTION
"Low Voltage Reconnect (mV)"
 ::= { cps6000Cp1  8 }

cps6000Cp1Lvd OBJECT-TYPE
SYNTAX      INTEGER {
disable(0),
enable(1)
}
MAX-ACCESS  read-write
STATUS      current
DESCRIPTION
"Low Voltage Disconnect Enable
Values:
disable(0),
enable(1)
"
 ::= { cps6000Cp1  9 }

cps6000Cp1Cfa OBJECT-TYPE
SYNTAX      DisplayString
MAX-ACCESS  read-only
STATUS      current
DESCRIPTION
"Converter Fail
Value:
Alarm report from CFA1
"
 ::= { cps6000Cp1  10 }

cps6000Cp1Dfa OBJECT-TYPE
SYNTAX      DisplayString
MAX-ACCESS  read-only
STATUS      current
DESCRIPTION
"Distribution Fail
Value:
Alarm report from CDFA1
"
 ::= { cps6000Cp1  11 }

cps6000Cp1Did OBJECT-TYPE
SYNTAX      DisplayString
MAX-ACCESS  read-only
STATUS      current
DESCRIPTION
"ID Conflict
Value:
Alarm report from CDID1
"
 ::= { cps6000Cp1  12 }

cps6000Cp1Mfa OBJECT-TYPE
SYNTAX      DisplayString
MAX-ACCESS  read-only
STATUS      current
DESCRIPTION
"Multiple Converter Fail
Value:
Alarm report from CMFA1
"
 ::= { cps6000Cp1  13 }

cps6000Cp1Cfn OBJECT-TYPE
SYNTAX      DisplayString
MAX-ACCESS  read-only
STATUS      current
DESCRIPTION
"Converter Fan Minor
Value:
Alarm report from CFN1
"
 ::= { cps6000Cp1  14 }

cps6000Cp1Cfj OBJECT-TYPE
SYNTAX      DisplayString
MAX-ACCESS  read-only
STATUS      current
DESCRIPTION
"Converter Fan Major
Value:
Alarm report from CFJ1
"
 ::= { cps6000Cp1  15 }

cps6000Cp1Icc OBJECT-TYPE
SYNTAX      DisplayString
MAX-ACCESS  read-only
STATUS      current
DESCRIPTION
"Incompatible Converter Alarm
Value:
Alarm report from ICC1
"
 ::= { cps6000Cp1  16 }

cps6000Cp1Hva OBJECT-TYPE
SYNTAX      DisplayString
MAX-ACCESS  read-only
STATUS      current
DESCRIPTION
"Converter High Voltage Major
Value:
Alarm report from CHVA1
"
 ::= { cps6000Cp1  17 }

cps6000Cp1Hfv OBJECT-TYPE
SYNTAX      DisplayString
MAX-ACCESS  read-only
STATUS      current
DESCRIPTION
"Converter High Voltage Minor
Value:
Alarm report from CHFV1
"
 ::= { cps6000Cp1  18 }

cps6000Cp1Vla OBJECT-TYPE
SYNTAX      DisplayString
MAX-ACCESS  read-only
STATUS      current
DESCRIPTION
"Converter Very Low Voltage
Value:
Alarm report from CVLA
"
 ::= { cps6000Cp1  19 }

cps6000Cp1Rl OBJECT-TYPE
SYNTAX      DisplayString
MAX-ACCESS  read-only
STATUS      current
DESCRIPTION
"Converter Redundancy Loss
Value:
Alarm report from CRL1
"
 ::= { cps6000Cp1  20 }

cps6000Cp1Typ OBJECT-TYPE
SYNTAX      DisplayString
MAX-ACCESS  read-only
STATUS      current
DESCRIPTION
"Type"
 ::= { cps6000Cp1  21 }

cps6000Cp1Olcap OBJECT-TYPE
SYNTAX      Integer32
UNITS       "Amps"
MAX-ACCESS  read-only
STATUS      current
DESCRIPTION
"Total On-line Converter Capacity (Amps)"
 ::= { cps6000Cp1  22 }

cps6000Cp1Vsd OBJECT-TYPE
SYNTAX      Integer32(48000..52000)
UNITS       "mV"
MAX-ACCESS  read-write
STATUS      current
DESCRIPTION
"Voltage Shutdown (mV)"
 ::= { cps6000Cp1  23 }

cps6000Cp1Clm OBJECT-TYPE
SYNTAX      Integer32(30..100)
UNITS       "%"
MAX-ACCESS  read-write
STATUS      current
DESCRIPTION
"Current Limit (%)"
 ::= { cps6000Cp1  24 }

cps6000Cp1Rof OBJECT-TYPE
SYNTAX      INTEGER {
disable(0),
enable(1)
}
MAX-ACCESS  read-write
STATUS      current
DESCRIPTION
"Remote Turn Off Enable
Values:
disable(0),
enable(1)
"
 ::= { cps6000Cp1  25 }

cps6000Cp1Rme OBJECT-TYPE
SYNTAX      INTEGER {
disable(0),
enable(1)
}
MAX-ACCESS  read-write
STATUS      current
DESCRIPTION
"Redundancy Monitor
Values:
disable(0),
enable(1)
"
 ::= { cps6000Cp1  26 }

cps6000Cp1Rss OBJECT-TYPE
SYNTAX      INTEGER {
restart(1)
}
MAX-ACCESS  read-write
STATUS      current
DESCRIPTION
"Restart
Values:
restart(1)
"
 ::= { cps6000Cp1  27 }


--
-- table DCC
--

cps6000DccTable    OBJECT-TYPE
SYNTAX SEQUENCE OF Cps6000DccEntry
MAX-ACCESS not-accessible
STATUS current
DESCRIPTION
        "Table of all Converter data"
 ::= { cps6000  8 }

cps6000DccEntry OBJECT-TYPE
SYNTAX     Cps6000DccEntry
MAX-ACCESS  not-accessible
STATUS      current
DESCRIPTION
       "Entry of information for one Converter"
INDEX { cps6000DccEntryIndex }
 ::= { cps6000DccTable  1 }

Cps6000DccEntry ::= SEQUENCE {
cps6000DccEntryIndex   INTEGER,
cps6000DccEntryIde   DisplayString,
cps6000DccEntryDes   DisplayString,
cps6000DccEntryTyp   DisplayString,
cps6000DccEntryAdc   DisplayString,
cps6000DccEntryCap   DisplayString,
cps6000DccEntryStt   DisplayString,
cps6000DccEntryCfa   DisplayString,
cps6000DccEntryDfa   DisplayString,
cps6000DccEntryDid   DisplayString,
cps6000DccEntryCcf   DisplayString,
cps6000DccEntryCfn   DisplayString,
cps6000DccEntrySn   DisplayString
}

cps6000DccEntryIndex OBJECT-TYPE
SYNTAX      INTEGER (0..2147483647)
MAX-ACCESS  read-only
STATUS      current
DESCRIPTION
"Table Index"
 ::= { cps6000DccEntry  1 }

cps6000DccEntryIde OBJECT-TYPE
SYNTAX      DisplayString
MAX-ACCESS  read-only
STATUS      current
DESCRIPTION
"Identifier"
 ::= { cps6000DccEntry  2 }

cps6000DccEntryDes OBJECT-TYPE
SYNTAX      DisplayString
MAX-ACCESS  read-write
STATUS      current
DESCRIPTION
"Description"
 ::= { cps6000DccEntry  3 }

cps6000DccEntryTyp OBJECT-TYPE
SYNTAX      DisplayString
MAX-ACCESS  read-only
STATUS      current
DESCRIPTION
"Type"
 ::= { cps6000DccEntry  4 }

cps6000DccEntryAdc OBJECT-TYPE
SYNTAX      DisplayString
UNITS       "Amps"
MAX-ACCESS  read-only
STATUS      current
DESCRIPTION
"DC Current (Amps)"
 ::= { cps6000DccEntry  5 }

cps6000DccEntryCap OBJECT-TYPE
SYNTAX      DisplayString
UNITS       "Amps"
MAX-ACCESS  read-only
STATUS      current
DESCRIPTION
"Capacity (Amps)"
 ::= { cps6000DccEntry  6 }

cps6000DccEntryStt OBJECT-TYPE
SYNTAX      DisplayString
MAX-ACCESS  read-write
STATUS      current
DESCRIPTION
"State
Values:
ON,
OFF,
STANDBY,
VACANT
"
 ::= { cps6000DccEntry  7 }

cps6000DccEntryCfa OBJECT-TYPE
SYNTAX      DisplayString
MAX-ACCESS  read-only
STATUS      current
DESCRIPTION
"Converter Fail"
 ::= { cps6000DccEntry  8 }

cps6000DccEntryDfa OBJECT-TYPE
SYNTAX      DisplayString
MAX-ACCESS  read-only
STATUS      current
DESCRIPTION
"Distribution Fuse Fail"
 ::= { cps6000DccEntry  9 }

cps6000DccEntryDid OBJECT-TYPE
SYNTAX      DisplayString
MAX-ACCESS  read-only
STATUS      current
DESCRIPTION
"ID Conflict"
 ::= { cps6000DccEntry  10 }

cps6000DccEntryCcf OBJECT-TYPE
SYNTAX      DisplayString
MAX-ACCESS  read-only
STATUS      current
DESCRIPTION
"Communication Failure"
 ::= { cps6000DccEntry  11 }

cps6000DccEntryCfn OBJECT-TYPE
SYNTAX      DisplayString
MAX-ACCESS  read-only
STATUS      current
DESCRIPTION
"Fan Failure"
 ::= { cps6000DccEntry  12 }

cps6000DccEntrySn OBJECT-TYPE
SYNTAX      DisplayString
MAX-ACCESS  read-only
STATUS      current
DESCRIPTION
"Serial Number"
 ::= { cps6000DccEntry  13 }



--
-- object cps6000Bs1
--

cps6000Bs1 OBJECT IDENTIFIER  ::= { cps6000  9 }

cps6000Bs1Ide OBJECT-TYPE
SYNTAX      DisplayString
MAX-ACCESS  read-only
STATUS      current
DESCRIPTION
"Identifier"
 ::= { cps6000Bs1  1 }

cps6000Bs1Des OBJECT-TYPE
SYNTAX      DisplayString
MAX-ACCESS  read-write
STATUS      current
DESCRIPTION
"Description"
 ::= { cps6000Bs1  2 }

cps6000Bs1Stt OBJECT-TYPE
SYNTAX      DisplayString
MAX-ACCESS  read-only
STATUS      current
DESCRIPTION
"State
Values:
QRCT,
MANUAL,
BTP,
TIMED AUTO,
OFF
"
 ::= { cps6000Bs1  3 }

cps6000Bs1Atm OBJECT-TYPE
SYNTAX      DisplayString
MAX-ACCESS  read-write
STATUS      current
DESCRIPTION
"Auto Mode
Values:
OFF,
QRCT,
TIMED
"
 ::= { cps6000Bs1  4 }

cps6000Bs1Tmd OBJECT-TYPE
SYNTAX      Integer32(1..80)
UNITS       "Hours"
MAX-ACCESS  read-write
STATUS      current
DESCRIPTION
"Timed Manual Duration (Hours)"
 ::= { cps6000Bs1  5 }

cps6000Bs1Amf OBJECT-TYPE
SYNTAX      Integer32(1..9)
MAX-ACCESS  read-write
STATUS      current
DESCRIPTION
"Auto Multiplication Factor"
 ::= { cps6000Bs1  6 }

cps6000Bs1Cta OBJECT-TYPE
SYNTAX      Integer32(0..100)
UNITS       "Amps"
MAX-ACCESS  read-write
STATUS      current
DESCRIPTION
"Current Terminated Current Threshold (Amps)"
 ::= { cps6000Bs1  7 }

cps6000Bs1Bsa OBJECT-TYPE
SYNTAX      DisplayString
MAX-ACCESS  read-only
STATUS      current
DESCRIPTION
"Boost State Alarm
Value:
Alarm report from linked object"
 ::= { cps6000Bs1  8 }


--
-- object cps6000Sc1
--

cps6000Sc1 OBJECT IDENTIFIER  ::= { cps6000  10 }

cps6000Sc1Ide OBJECT-TYPE
SYNTAX      DisplayString
MAX-ACCESS  read-only
STATUS      current
DESCRIPTION
"Identifier"
 ::= { cps6000Sc1  1 }

cps6000Sc1Des OBJECT-TYPE
SYNTAX      DisplayString
MAX-ACCESS  read-write
STATUS      current
DESCRIPTION
"Description"
 ::= { cps6000Sc1  2 }

cps6000Sc1Stt OBJECT-TYPE
SYNTAX      INTEGER {
disable(0),
enable(1)
}
MAX-ACCESS  read-write
STATUS      current
DESCRIPTION
"State
Values:
disable(0),
enable(1)
"
 ::= { cps6000Sc1  3 }

cps6000Sc1Rve OBJECT-TYPE
SYNTAX      INTEGER {
disable(0),
enable(1)
}
MAX-ACCESS  read-write
STATUS      current
DESCRIPTION
"Raise Voltage Enable
Values:
disable(0),
enable(1)
"
 ::= { cps6000Sc1  4 }

cps6000Sc1Ltt OBJECT-TYPE
SYNTAX      Integer32
UNITS       "C"
MAX-ACCESS  read-write
STATUS      current
DESCRIPTION
"Lower Temperature Threshold (C)"
 ::= { cps6000Sc1  5 }

cps6000Sc1Ntt OBJECT-TYPE
SYNTAX      Integer32
UNITS       "C"
MAX-ACCESS  read-write
STATUS      current
DESCRIPTION
"Nominal Temperature Threshold (C)"
 ::= { cps6000Sc1  6 }

cps6000Sc1Utt OBJECT-TYPE
SYNTAX      Integer32
UNITS       "C"
MAX-ACCESS  read-write
STATUS      current
DESCRIPTION
"Upper Temperature Threshold (C)"
 ::= { cps6000Sc1  7 }

cps6000Sc1Spt OBJECT-TYPE
SYNTAX      Integer32
UNITS       "C"
MAX-ACCESS  read-write
STATUS      current
DESCRIPTION
"Step Temperature (C)"
 ::= { cps6000Sc1  8 }

cps6000Sc1Lsp OBJECT-TYPE
SYNTAX      Integer32
UNITS       "mV/C/Cell"
MAX-ACCESS  read-write
STATUS      current
DESCRIPTION
"Lower Temperature Slope/Cell (mV/C/Cell)"
 ::= { cps6000Sc1  9 }

cps6000Sc1Usp OBJECT-TYPE
SYNTAX      Integer32
UNITS       "mV/C/Cell"
MAX-ACCESS  read-write
STATUS      current
DESCRIPTION
"Upper Temperature Slope/Cell (mV/C/Cell)"
 ::= { cps6000Sc1  10 }


--
-- table BTD
--

cps6000BtdTable    OBJECT-TYPE
SYNTAX SEQUENCE OF Cps6000BtdEntry
MAX-ACCESS not-accessible
STATUS current
DESCRIPTION
        "Table of all Battery Type Definition data"
 ::= { cps6000  11 }

cps6000BtdEntry OBJECT-TYPE
SYNTAX     Cps6000BtdEntry
MAX-ACCESS  not-accessible
STATUS      current
DESCRIPTION
       "Entry of information for one Battery Type Definition"
INDEX { cps6000BtdEntryIndex }
 ::= { cps6000BtdTable  1 }

Cps6000BtdEntry ::= SEQUENCE {
cps6000BtdEntryIndex   INTEGER,
cps6000BtdEntryIde   DisplayString,
cps6000BtdEntryDes   DisplayString,
cps6000BtdEntryBty   DisplayString,
cps6000BtdEntryBtc   DisplayString,
cps6000BtdEntryCap   DisplayString
}

cps6000BtdEntryIndex OBJECT-TYPE
SYNTAX      INTEGER (0..2147483647)
MAX-ACCESS  read-only
STATUS      current
DESCRIPTION
"Table Index"
 ::= { cps6000BtdEntry  1 }

cps6000BtdEntryIde OBJECT-TYPE
SYNTAX      DisplayString
MAX-ACCESS  read-only
STATUS      current
DESCRIPTION
"Identifier"
 ::= { cps6000BtdEntry  2 }

cps6000BtdEntryDes OBJECT-TYPE
SYNTAX      DisplayString
MAX-ACCESS  read-write
STATUS      current
DESCRIPTION
"Description"
 ::= { cps6000BtdEntry  3 }

cps6000BtdEntryBty OBJECT-TYPE
SYNTAX      DisplayString
MAX-ACCESS  read-write
STATUS      current
DESCRIPTION
"Battery Type"
 ::= { cps6000BtdEntry  4 }

cps6000BtdEntryBtc OBJECT-TYPE
SYNTAX      DisplayString
MAX-ACCESS  read-write
STATUS      current
DESCRIPTION
"Battery Class
Values:
FLOODED,
SEALED
"
 ::= { cps6000BtdEntry  5 }

cps6000BtdEntryCap OBJECT-TYPE
SYNTAX      DisplayString
UNITS       "Amps"
MAX-ACCESS  read-write
STATUS      current
DESCRIPTION
"Capacity (Amps)"
 ::= { cps6000BtdEntry  6 }



--
-- object cps6000Br1
--

cps6000Br1 OBJECT IDENTIFIER  ::= { cps6000  12 }

cps6000Br1Ide OBJECT-TYPE
SYNTAX      DisplayString
MAX-ACCESS  read-only
STATUS      current
DESCRIPTION
"Identifier"
 ::= { cps6000Br1  1 }

cps6000Br1Des OBJECT-TYPE
SYNTAX      DisplayString
MAX-ACCESS  read-write
STATUS      current
DESCRIPTION
"Description"
 ::= { cps6000Br1  2 }

cps6000Br1Hbt OBJECT-TYPE
SYNTAX      DisplayString
UNITS       "C"
MAX-ACCESS  read-only
STATUS      current
DESCRIPTION
"Highest Battery Temperature (C)"
 ::= { cps6000Br1  3 }

cps6000Br1Adc OBJECT-TYPE
SYNTAX      DisplayString
UNITS       "Amps"
MAX-ACCESS  read-only
STATUS      current
DESCRIPTION
"Total Battery Current (Amps)"
 ::= { cps6000Br1  4 }

cps6000Br1Cap OBJECT-TYPE
SYNTAX      DisplayString
UNITS       "Amps"
MAX-ACCESS  read-only
STATUS      current
DESCRIPTION
"Installed Battery Capacity (Amps)"
 ::= { cps6000Br1  5 }

cps6000Br1Olcap OBJECT-TYPE
SYNTAX      DisplayString
UNITS       "Amps"
MAX-ACCESS  read-only
STATUS      current
DESCRIPTION
"On-line Battery Capacity (Amps)"
 ::= { cps6000Br1  6 }

cps6000Br1Bts OBJECT-TYPE
SYNTAX      INTEGER {
inactive(0),
active(1)
}
MAX-ACCESS  read-write
STATUS      current
DESCRIPTION
"Battery Test State
Values:
inactive(0),
active(1)
"
 ::= { cps6000Br1  7 }

cps6000Br1Scd OBJECT-TYPE
SYNTAX      INTEGER {
disable(0),
enable(1)
}
MAX-ACCESS  read-write
STATUS      current
DESCRIPTION
"Battery Voltage Imbalance Detection
Values:
disable(0),
enable(1)
"
 ::= { cps6000Br1  8 }

cps6000Br1Scv OBJECT-TYPE
SYNTAX      Integer32(1500..3000)
UNITS       "mV"
MAX-ACCESS  read-write
STATUS      current
DESCRIPTION
"Battery Imbalance Threshold (mV)"
 ::= { cps6000Br1  9 }

cps6000Br1Ntm OBJECT-TYPE
SYNTAX      Integer32
MAX-ACCESS  read-only
STATUS      current
DESCRIPTION
"Number of Temperature Probes Present"
 ::= { cps6000Br1  10 }

cps6000Br1Nvm OBJECT-TYPE
SYNTAX      Integer32
MAX-ACCESS  read-only
STATUS      current
DESCRIPTION
"Number of Mid-cell V PresentTemperature"
 ::= { cps6000Br1  11 }

cps6000Br1Cle OBJECT-TYPE
SYNTAX      INTEGER {
disable(0),
enable(1)
}
MAX-ACCESS  read-write
STATUS      current
DESCRIPTION
"Current Limit Enable
Values:
disable(0),
enable(1)
"
 ::= { cps6000Br1  12 }

cps6000Br1Clt OBJECT-TYPE
SYNTAX      Integer32(10..1000)
UNITS       "Amps"
MAX-ACCESS  read-write
STATUS      current
DESCRIPTION
"Current Limit Threshold (Amps)"
 ::= { cps6000Br1  13 }

cps6000Br1Mtt OBJECT-TYPE
SYNTAX      DisplayString
MAX-ACCESS  read-write
STATUS      current
DESCRIPTION
"Manual Test Type
Values:
DISABLE,
20%,
TIMED
"
 ::= { cps6000Br1  14 }

cps6000Br1Bte OBJECT-TYPE
SYNTAX      DisplayString
MAX-ACCESS  read-write
STATUS      current
DESCRIPTION
"Automatic Test Type
Values:
DISABLE,
20%,
TIMED
"
 ::= { cps6000Br1  15 }

cps6000Br1Atd OBJECT-TYPE
SYNTAX      DisplayString
MAX-ACCESS  read-write
STATUS      current
DESCRIPTION
"Auto Test Date"
 ::= { cps6000Br1  16 }

cps6000Br1Ath OBJECT-TYPE
SYNTAX      Integer32(0..23)
MAX-ACCESS  read-write
STATUS      current
DESCRIPTION
"Auto Test Hour"
 ::= { cps6000Br1  17 }

cps6000Br1Atw OBJECT-TYPE
SYNTAX      Integer32(0..240)
MAX-ACCESS  read-write
STATUS      current
DESCRIPTION
"Auto Test Minimum Hours after BD"
 ::= { cps6000Br1  18 }

cps6000Br1Tin OBJECT-TYPE
SYNTAX      Integer32(1..18)
UNITS       "Months"
MAX-ACCESS  read-write
STATUS      current
DESCRIPTION
"Auto Test Interval (Months)"
 ::= { cps6000Br1  19 }

cps6000Br1Tmd OBJECT-TYPE
SYNTAX      DisplayString
MAX-ACCESS  read-write
STATUS      current
DESCRIPTION
"Manual Test Duration"
 ::= { cps6000Br1  20 }

cps6000Br1Tev OBJECT-TYPE
SYNTAX      Integer32(36000..48000)
UNITS       "mV"
MAX-ACCESS  read-write
STATUS      current
DESCRIPTION
"Manual Test Alarm Voltage (mV)"
 ::= { cps6000Br1  21 }

cps6000Br1Btv OBJECT-TYPE
SYNTAX      Integer32(42000..52000)
UNITS       "mV"
MAX-ACCESS  read-write
STATUS      current
DESCRIPTION
"Battery Test Rectifier Voltage (mV)"
 ::= { cps6000Br1  22 }

cps6000Br1Tth OBJECT-TYPE
SYNTAX      Integer32(30..194)
UNITS       "C"
MAX-ACCESS  read-write
STATUS      current
DESCRIPTION
"High Temperature Threshold (C)"
 ::= { cps6000Br1  23 }

cps6000Br1Cev OBJECT-TYPE
SYNTAX      Integer32(1750..1950)
UNITS       "mV"
MAX-ACCESS  read-write
STATUS      current
DESCRIPTION
"End Volts per Cell (mV)"
 ::= { cps6000Br1  24 }

cps6000Br1Btr OBJECT-TYPE
SYNTAX      DisplayString
MAX-ACCESS  read-only
STATUS      current
DESCRIPTION
"Battery Test Results"
 ::= { cps6000Br1  25 }

cps6000Br1Bta OBJECT-TYPE
SYNTAX      DisplayString
MAX-ACCESS  read-only
STATUS      current
DESCRIPTION
"Battery Test Active
Value:
Alarm report from BTA1
"
 ::= { cps6000Br1  26 }

cps6000Br1Bfa OBJECT-TYPE
SYNTAX      DisplayString
MAX-ACCESS  read-only
STATUS      current
DESCRIPTION
"Battery Test Failed
Value:
Alarm report from BFA1
"
 ::= { cps6000Br1  27 }

cps6000Br1Btha OBJECT-TYPE
SYNTAX      DisplayString
MAX-ACCESS  read-only
STATUS      current
DESCRIPTION
"High Battery Temperature
Value:
Alarm report from BTHA1
"
 ::= { cps6000Br1  28 }

cps6000Br1Isda OBJECT-TYPE
SYNTAX      DisplayString
MAX-ACCESS  read-only
STATUS      current
DESCRIPTION
"Imminent Shutdown
Value:
Alarm report from ISD1
"
 ::= { cps6000Br1  29 }

cps6000Br1Mdp OBJECT-TYPE
SYNTAX      DisplayString
MAX-ACCESS  read-only
STATUS      current
DESCRIPTION
"Voltage Duplicate ID
Value:
Alarm report from MDP1
"
 ::= { cps6000Br1  30 }

cps6000Br1Mzd OBJECT-TYPE
SYNTAX      DisplayString
MAX-ACCESS  read-only
STATUS      current
DESCRIPTION
"Voltage ID Not Configured
Value:
Alarm report from MZD1
"
 ::= { cps6000Br1  31 }

cps6000Br1Scda OBJECT-TYPE
SYNTAX      DisplayString
MAX-ACCESS  read-only
STATUS      current
DESCRIPTION
"Shorted Cell Detected
Value:
Alarm report from SCD1
"
 ::= { cps6000Br1  32 }


--
-- table CNT
--

cps6000CntTable    OBJECT-TYPE
SYNTAX SEQUENCE OF Cps6000CntEntry
MAX-ACCESS not-accessible
STATUS current
DESCRIPTION
        "Table of all Contactor data"
 ::= { cps6000  13 }

cps6000CntEntry OBJECT-TYPE
SYNTAX     Cps6000CntEntry
MAX-ACCESS  not-accessible
STATUS      current
DESCRIPTION
       "Entry of information for one Contactor"
INDEX { cps6000CntEntryIndex }
 ::= { cps6000CntTable  1 }

Cps6000CntEntry ::= SEQUENCE {
cps6000CntEntryIndex   INTEGER,
cps6000CntEntryIde   DisplayString,
cps6000CntEntryDes   DisplayString,
cps6000CntEntryStt   DisplayString,
cps6000CntEntryEna   INTEGER,
cps6000CntEntryDth   Integer32,
cps6000CntEntryDdy   Integer32,
cps6000CntEntryDam   INTEGER,
cps6000CntEntryDtm   Integer32,
cps6000CntEntryRth   Integer32,
cps6000CntEntryRdy   Integer32,
cps6000CntEntryRam   INTEGER,
cps6000CntEntryRtm   Integer32,
cps6000CntEntryCno   DisplayString,
cps6000CntEntryCnf   DisplayString
}

cps6000CntEntryIndex OBJECT-TYPE
SYNTAX      INTEGER (0..2147483647)
MAX-ACCESS  read-only
STATUS      current
DESCRIPTION
"Table Index"
 ::= { cps6000CntEntry  1 }

cps6000CntEntryIde OBJECT-TYPE
SYNTAX      DisplayString
MAX-ACCESS  read-only
STATUS      current
DESCRIPTION
"Identifier"
 ::= { cps6000CntEntry  2 }

cps6000CntEntryDes OBJECT-TYPE
SYNTAX      DisplayString
MAX-ACCESS  read-write
STATUS      current
DESCRIPTION
"Description"
 ::= { cps6000CntEntry  3 }

cps6000CntEntryStt OBJECT-TYPE
SYNTAX      DisplayString
MAX-ACCESS  read-write
STATUS      current
DESCRIPTION
"Status
Values:
NONE,
DISCON,
CONNECT,
FAILED
"
 ::= { cps6000CntEntry  4 }

cps6000CntEntryEna OBJECT-TYPE
SYNTAX      INTEGER {
disable(0),
enable(1)
}
MAX-ACCESS  read-write
STATUS      current
DESCRIPTION
"Control
Values:
disable(0),
enable(1)
"
 ::= { cps6000CntEntry  5 }

cps6000CntEntryDth OBJECT-TYPE
SYNTAX      Integer32(20000..50000)
UNITS       "mV"
MAX-ACCESS  read-write
STATUS      current
DESCRIPTION
"Disconnect Threshold (mV)"
 ::= { cps6000CntEntry  6 }

cps6000CntEntryDdy OBJECT-TYPE
SYNTAX      Integer32(0..300)
UNITS       "Minutes"
MAX-ACCESS  read-write
STATUS      current
DESCRIPTION
"Disconnect Delay (Minutes)"
 ::= { cps6000CntEntry  7 }

cps6000CntEntryDam OBJECT-TYPE
SYNTAX      INTEGER {
none(0),
voltage(1),
voltageAndTime(2)
}
MAX-ACCESS  read-write
STATUS      current
DESCRIPTION
"Disconnect Automode
Values:
none(0),
voltage(1),
voltageAndTime(2)
"
 ::= { cps6000CntEntry  8 }

cps6000CntEntryDtm OBJECT-TYPE
SYNTAX      Integer32
UNITS       "Minutes"
MAX-ACCESS  read-only
STATUS      current
DESCRIPTION
"Disconnect Time Remaining (Minutes)"
 ::= { cps6000CntEntry  9 }

cps6000CntEntryRth OBJECT-TYPE
SYNTAX      Integer32(22000..55000)
UNITS       "mV"
MAX-ACCESS  read-write
STATUS      current
DESCRIPTION
"Reconnect Threshold (mV)"
 ::= { cps6000CntEntry  10 }

cps6000CntEntryRdy OBJECT-TYPE
SYNTAX      Integer32(0..300)
UNITS       "Seconds"
MAX-ACCESS  read-write
STATUS      current
DESCRIPTION
"Reconnect Delay (Seconds)"
 ::= { cps6000CntEntry  11 }

cps6000CntEntryRam OBJECT-TYPE
SYNTAX      INTEGER {
none(0),
voltage(1),
voltageAndTime(2)
}
MAX-ACCESS  read-write
STATUS      current
DESCRIPTION
"Reconnect Automode
Values:
none(0),
voltage(1),
voltageAndTime(2)
"
 ::= { cps6000CntEntry  12 }

cps6000CntEntryRtm OBJECT-TYPE
SYNTAX      Integer32
UNITS       "Seconds"
MAX-ACCESS  read-only
STATUS      current
DESCRIPTION
"Reconnect Time Remaining (Seconds)"
 ::= { cps6000CntEntry  13 }

cps6000CntEntryCno OBJECT-TYPE
SYNTAX      DisplayString
MAX-ACCESS  read-only
STATUS      current
DESCRIPTION
"Contactor Open"
 ::= { cps6000CntEntry  14 }

cps6000CntEntryCnf OBJECT-TYPE
SYNTAX      DisplayString
MAX-ACCESS  read-only
STATUS      current
DESCRIPTION
"Contactor Failed"
 ::= { cps6000CntEntry  15 }



--
-- table DCN
--

cps6000DcnTable    OBJECT-TYPE
SYNTAX SEQUENCE OF Cps6000DcnEntry
MAX-ACCESS not-accessible
STATUS current
DESCRIPTION
        "Table of all Distribution Contactor Interface data"
 ::= { cps6000  14 }

cps6000DcnEntry OBJECT-TYPE
SYNTAX     Cps6000DcnEntry
MAX-ACCESS  not-accessible
STATUS      current
DESCRIPTION
       "Entry of information for one Distribution Contactor Interface"
INDEX { cps6000DcnEntryIndex }
 ::= { cps6000DcnTable  1 }

Cps6000DcnEntry ::= SEQUENCE {
cps6000DcnEntryIndex   INTEGER,
cps6000DcnEntryIde   DisplayString,
cps6000DcnEntryDes   DisplayString,
cps6000DcnEntryStt   DisplayString,
cps6000DcnEntryTyp   DisplayString,
cps6000DcnEntrySn   DisplayString,
cps6000DcnEntryBrc   DisplayString
}

cps6000DcnEntryIndex OBJECT-TYPE
SYNTAX      INTEGER (0..2147483647)
MAX-ACCESS  read-only
STATUS      current
DESCRIPTION
"Table Index"
 ::= { cps6000DcnEntry  1 }

cps6000DcnEntryIde OBJECT-TYPE
SYNTAX      DisplayString
MAX-ACCESS  read-only
STATUS      current
DESCRIPTION
"Identifier"
 ::= { cps6000DcnEntry  2 }

cps6000DcnEntryDes OBJECT-TYPE
SYNTAX      DisplayString
MAX-ACCESS  read-write
STATUS      current
DESCRIPTION
"Description"
 ::= { cps6000DcnEntry  3 }

cps6000DcnEntryStt OBJECT-TYPE
SYNTAX      DisplayString
MAX-ACCESS  read-only
STATUS      current
DESCRIPTION
"State
Values:
NONE,
MISSING,
PRESENT
"
 ::= { cps6000DcnEntry  4 }

cps6000DcnEntryTyp OBJECT-TYPE
SYNTAX      DisplayString
MAX-ACCESS  read-write
STATUS      current
DESCRIPTION
"Contactor Interface Type
Values:
NONE,
CN1,
CN2,
CN3,
CN4
"
 ::= { cps6000DcnEntry  5 }

cps6000DcnEntrySn OBJECT-TYPE
SYNTAX      DisplayString
MAX-ACCESS  read-only
STATUS      current
DESCRIPTION
"Serial Number"
 ::= { cps6000DcnEntry  6 }

cps6000DcnEntryBrc OBJECT-TYPE
SYNTAX      DisplayString
MAX-ACCESS  read-only
STATUS      current
DESCRIPTION
"Board Code"
 ::= { cps6000DcnEntry  7 }



--
-- table DCM
--

cps6000DcmTable    OBJECT-TYPE
SYNTAX SEQUENCE OF Cps6000DcmEntry
MAX-ACCESS not-accessible
STATUS current
DESCRIPTION
        "Table of all Distribution Current Monitor data"
 ::= { cps6000  15 }

cps6000DcmEntry OBJECT-TYPE
SYNTAX     Cps6000DcmEntry
MAX-ACCESS  not-accessible
STATUS      current
DESCRIPTION
       "Entry of information for one Distribution Current Monitor"
INDEX { cps6000DcmEntryIndex }
 ::= { cps6000DcmTable  1 }

Cps6000DcmEntry ::= SEQUENCE {
cps6000DcmEntryIndex   INTEGER,
cps6000DcmEntryIde   DisplayString,
cps6000DcmEntryDes   DisplayString,
cps6000DcmEntryStt   DisplayString,
cps6000DcmEntryTyp   DisplayString,
cps6000DcmEntryVal   Integer32,
cps6000DcmEntrySha   Integer32,
cps6000DcmEntrySn   DisplayString,
cps6000DcmEntryBrc   DisplayString
}

cps6000DcmEntryIndex OBJECT-TYPE
SYNTAX      INTEGER (0..2147483647)
MAX-ACCESS  read-only
STATUS      current
DESCRIPTION
"Table Index"
 ::= { cps6000DcmEntry  1 }

cps6000DcmEntryIde OBJECT-TYPE
SYNTAX      DisplayString
MAX-ACCESS  read-only
STATUS      current
DESCRIPTION
"Identifier"
 ::= { cps6000DcmEntry  2 }

cps6000DcmEntryDes OBJECT-TYPE
SYNTAX      DisplayString
MAX-ACCESS  read-write
STATUS      current
DESCRIPTION
"Description"
 ::= { cps6000DcmEntry  3 }

cps6000DcmEntryStt OBJECT-TYPE
SYNTAX      DisplayString
MAX-ACCESS  read-only
STATUS      current
DESCRIPTION
"State
Values:
NONE,
MISSING,
PRESENT
"
 ::= { cps6000DcmEntry  4 }

cps6000DcmEntryTyp OBJECT-TYPE
SYNTAX      DisplayString
MAX-ACCESS  read-write
STATUS      current
DESCRIPTION
"Shunt Type
Values:
NONE,
LOAD,
BATTERY
"
 ::= { cps6000DcmEntry  5 }

cps6000DcmEntryVal OBJECT-TYPE
SYNTAX      Integer32
UNITS       "Amps x 1000"
MAX-ACCESS  read-only
STATUS      current
DESCRIPTION
"Reading (Amps x 1000)"
 ::= { cps6000DcmEntry  6 }

cps6000DcmEntrySha OBJECT-TYPE
SYNTAX      Integer32
UNITS       "Amps"
MAX-ACCESS  read-write
STATUS      current
DESCRIPTION
"Shunt Rating (Amps)"
 ::= { cps6000DcmEntry  7 }

cps6000DcmEntrySn OBJECT-TYPE
SYNTAX      DisplayString
MAX-ACCESS  read-only
STATUS      current
DESCRIPTION
"Serial Number"
 ::= { cps6000DcmEntry  8 }

cps6000DcmEntryBrc OBJECT-TYPE
SYNTAX      DisplayString
MAX-ACCESS  read-only
STATUS      current
DESCRIPTION
"Board Code"
 ::= { cps6000DcmEntry  9 }



--
-- table UDE
--

cps6000UdeTable    OBJECT-TYPE
SYNTAX SEQUENCE OF Cps6000UdeEntry
MAX-ACCESS not-accessible
STATUS current
DESCRIPTION
        "Table of all User Defined Event data"
 ::= { cps6000  16 }

cps6000UdeEntry OBJECT-TYPE
SYNTAX     Cps6000UdeEntry
MAX-ACCESS  not-accessible
STATUS      current
DESCRIPTION
       "Entry of information for one User Defined Event"
INDEX { cps6000UdeEntryIndex }
 ::= { cps6000UdeTable  1 }

Cps6000UdeEntry ::= SEQUENCE {
cps6000UdeEntryIndex   INTEGER,
cps6000UdeEntryIde   DisplayString,
cps6000UdeEntryDes   DisplayString,
cps6000UdeEntryAst   DisplayString,
cps6000UdeEntrySev   DisplayString,
cps6000UdeEntryPrg   DisplayString,
cps6000UdeEntryDur   DisplayString,
cps6000UdeEntryLat   INTEGER,
cps6000UdeEntryAcc   DisplayString,
cps6000UdeEntryDly   Integer32,
cps6000UdeEntryNoo   INTEGER,
cps6000UdeEntryNor   INTEGER,
cps6000UdeEntryNag   INTEGER,
cps6000UdeEntryDst   DisplayString,
cps6000UdeEntryFds   DisplayString
}

cps6000UdeEntryIndex OBJECT-TYPE
SYNTAX      INTEGER (0..2147483647)
MAX-ACCESS  read-only
STATUS      current
DESCRIPTION
"Table Index"
 ::= { cps6000UdeEntry  1 }

cps6000UdeEntryIde OBJECT-TYPE
SYNTAX      DisplayString
MAX-ACCESS  read-only
STATUS      current
DESCRIPTION
"Identifier"
 ::= { cps6000UdeEntry  2 }

cps6000UdeEntryDes OBJECT-TYPE
SYNTAX      DisplayString
MAX-ACCESS  read-write
STATUS      current
DESCRIPTION
"Description"
 ::= { cps6000UdeEntry  3 }

cps6000UdeEntryAst OBJECT-TYPE
SYNTAX      DisplayString
MAX-ACCESS  read-only
STATUS      current
DESCRIPTION
"Alarm State"
 ::= { cps6000UdeEntry  4 }

cps6000UdeEntrySev OBJECT-TYPE
SYNTAX      DisplayString
MAX-ACCESS  read-write
STATUS      current
DESCRIPTION
"Severity
Values:
CRIT,
MAJ,
MIN,
WRN,
RO
"
 ::= { cps6000UdeEntry  5 }

cps6000UdeEntryPrg OBJECT-TYPE
SYNTAX      DisplayString
MAX-ACCESS  read-write
STATUS      current
DESCRIPTION
"Program Line"
 ::= { cps6000UdeEntry  6 }

cps6000UdeEntryDur OBJECT-TYPE
SYNTAX      DisplayString
UNITS       "Seconds"
MAX-ACCESS  read-write
STATUS      current
DESCRIPTION
"Minimum Duration (Seconds)"
 ::= { cps6000UdeEntry  7 }

cps6000UdeEntryLat OBJECT-TYPE
SYNTAX      INTEGER {
no(0),
yes(1)
}
MAX-ACCESS  read-write
STATUS      current
DESCRIPTION
"Latched
Values:
no(0),
yes(1)
"
 ::= { cps6000UdeEntry  8 }

cps6000UdeEntryAcc OBJECT-TYPE
SYNTAX      DisplayString
MAX-ACCESS  read-write
STATUS      current
DESCRIPTION
"Contact Closure
Values:
R1,
R2,
R3,
R4
"
 ::= { cps6000UdeEntry  9 }

cps6000UdeEntryDly OBJECT-TYPE
SYNTAX      Integer32(0..540)
UNITS       "Seconds"
MAX-ACCESS  read-write
STATUS      current
DESCRIPTION
"Notify Delay (Seconds)"
 ::= { cps6000UdeEntry  10 }

cps6000UdeEntryNoo OBJECT-TYPE
SYNTAX      INTEGER {
no(0),
yes(1)
}
MAX-ACCESS  read-write
STATUS      current
DESCRIPTION
"Notify on Occur
Values:
no(0),
yes(1)
"
 ::= { cps6000UdeEntry  11 }

cps6000UdeEntryNor OBJECT-TYPE
SYNTAX      INTEGER {
no(0),
yes(1)
}
MAX-ACCESS  read-write
STATUS      current
DESCRIPTION
"Notify on Retire
Values:
no(0),
yes(1)
"
 ::= { cps6000UdeEntry  12 }

cps6000UdeEntryNag OBJECT-TYPE
SYNTAX      INTEGER {
no(0),
yes(1)
}
MAX-ACCESS  read-write
STATUS      current
DESCRIPTION
"NAG on Occur
Values:
no(0),
yes(1)
"
 ::= { cps6000UdeEntry  13 }

cps6000UdeEntryDst OBJECT-TYPE
SYNTAX      DisplayString
MAX-ACCESS  read-write
STATUS      current
DESCRIPTION
"Notify Destination
Values:
P1,
P2,
P3,
P4
"
 ::= { cps6000UdeEntry  14 }

cps6000UdeEntryFds OBJECT-TYPE
SYNTAX      DisplayString
MAX-ACCESS  read-write
STATUS      current
DESCRIPTION
"Front Panel Description"
 ::= { cps6000UdeEntry  15 }



--
-- object cps6000Cm1
--

cps6000Cm1 OBJECT IDENTIFIER  ::= { cps6000  17 }

cps6000Cm1Ide OBJECT-TYPE
SYNTAX      DisplayString
MAX-ACCESS  read-only
STATUS      current
DESCRIPTION
"Identifier"
 ::= { cps6000Cm1  1 }

cps6000Cm1Des OBJECT-TYPE
SYNTAX      DisplayString
MAX-ACCESS  read-write
STATUS      current
DESCRIPTION
"Description"
 ::= { cps6000Cm1  2 }

cps6000Cm1Ngi OBJECT-TYPE
SYNTAX      Integer32(15..60)
UNITS       "Minutes"
MAX-ACCESS  read-write
STATUS      current
DESCRIPTION
"Nag Interval (Minutes)"
 ::= { cps6000Cm1  3 }

cps6000Cm1Cof OBJECT-TYPE
SYNTAX      DisplayString
MAX-ACCESS  read-only
STATUS      current
DESCRIPTION
"Queue Overflow
Value:
Alarm report from COF1
"
 ::= { cps6000Cm1  4 }

cps6000Cm1Cor OBJECT-TYPE
SYNTAX      DisplayString
MAX-ACCESS  read-only
STATUS      current
DESCRIPTION
"Number Did Not Respond
Value:
Alarm report from COR1
"
 ::= { cps6000Cm1  5 }

cps6000Cm1Nnc OBJECT-TYPE
SYNTAX      DisplayString
MAX-ACCESS  read-only
STATUS      current
DESCRIPTION
"Number Not Configured
Value:
Alarm report from NNC1
"
 ::= { cps6000Cm1  6 }


--
-- table COP
--

cps6000CopTable    OBJECT-TYPE
SYNTAX SEQUENCE OF Cps6000CopEntry
MAX-ACCESS not-accessible
STATUS current
DESCRIPTION
        "Table of all Call Out Phone Number data"
 ::= { cps6000  18 }

cps6000CopEntry OBJECT-TYPE
SYNTAX     Cps6000CopEntry
MAX-ACCESS  not-accessible
STATUS      current
DESCRIPTION
       "Entry of information for one Call Out Phone Number"
INDEX { cps6000CopEntryIndex }
 ::= { cps6000CopTable  1 }

Cps6000CopEntry ::= SEQUENCE {
cps6000CopEntryIndex   INTEGER,
cps6000CopEntryIde   DisplayString,
cps6000CopEntryDes   DisplayString,
cps6000CopEntryTyp   DisplayString,
cps6000CopEntryPhn   DisplayString,
cps6000CopEntryBdr   INTEGER,
cps6000CopEntryDbt   INTEGER,
cps6000CopEntryPry   DisplayString,
cps6000CopEntrySbt   INTEGER,
cps6000CopEntryDly   Integer32,
cps6000CopEntryPgr   DisplayString,
cps6000CopEntryMsg   DisplayString
}

cps6000CopEntryIndex OBJECT-TYPE
SYNTAX      INTEGER (0..2147483647)
MAX-ACCESS  read-only
STATUS      current
DESCRIPTION
"Table Index"
 ::= { cps6000CopEntry  1 }

cps6000CopEntryIde OBJECT-TYPE
SYNTAX      DisplayString
MAX-ACCESS  read-only
STATUS      current
DESCRIPTION
"Identifier"
 ::= { cps6000CopEntry  2 }

cps6000CopEntryDes OBJECT-TYPE
SYNTAX      DisplayString
MAX-ACCESS  read-write
STATUS      current
DESCRIPTION
"Description"
 ::= { cps6000CopEntry  3 }

cps6000CopEntryTyp OBJECT-TYPE
SYNTAX      DisplayString
MAX-ACCESS  read-write
STATUS      current
DESCRIPTION
"Type
Values:
DATA,
PAGER
"
 ::= { cps6000CopEntry  4 }

cps6000CopEntryPhn OBJECT-TYPE
SYNTAX      DisplayString
MAX-ACCESS  read-write
STATUS      current
DESCRIPTION
"Phone Number"
 ::= { cps6000CopEntry  5 }

cps6000CopEntryBdr OBJECT-TYPE
SYNTAX      INTEGER {
b300(300),
b1200(1200),
b2400(2400),
b4800(4800),
b9600(9600),
b19200(19200)
}
MAX-ACCESS  read-write
STATUS      current
DESCRIPTION
"Connect Baudrate
Values:
b300(300),
b1200(1200),
b2400(2400),
b4800(4800),
b9600(9600),
b19200(19200)
"
 ::= { cps6000CopEntry  6 }

cps6000CopEntryDbt OBJECT-TYPE
SYNTAX      INTEGER {
d7(7),
d8(8)
}
MAX-ACCESS  read-write
STATUS      current
DESCRIPTION
"Data Bits
Values:
d7(7),
d8(8)
"
 ::= { cps6000CopEntry  7 }

cps6000CopEntryPry OBJECT-TYPE
SYNTAX      DisplayString
MAX-ACCESS  read-write
STATUS      current
DESCRIPTION
"Parity
Values:
O,
E,
N
"
 ::= { cps6000CopEntry  8 }

cps6000CopEntrySbt OBJECT-TYPE
SYNTAX      INTEGER {
s1(1),
s2(2)
}
MAX-ACCESS  read-write
STATUS      current
DESCRIPTION
"Stop Bits
Values:
s1(1),
s2(2)
"
 ::= { cps6000CopEntry  9 }

cps6000CopEntryDly OBJECT-TYPE
SYNTAX      Integer32(0..9)
MAX-ACCESS  read-write
STATUS      current
DESCRIPTION
"Pager ID Delay"
 ::= { cps6000CopEntry  10 }

cps6000CopEntryPgr OBJECT-TYPE
SYNTAX      DisplayString
MAX-ACCESS  read-write
STATUS      current
DESCRIPTION
"Pager ID"
 ::= { cps6000CopEntry  11 }

cps6000CopEntryMsg OBJECT-TYPE
SYNTAX      DisplayString
MAX-ACCESS  read-write
STATUS      current
DESCRIPTION
"Pager Message"
 ::= { cps6000CopEntry  12 }



--
-- table COE
--

cps6000CoeTable    OBJECT-TYPE
SYNTAX SEQUENCE OF Cps6000CoeEntry
MAX-ACCESS not-accessible
STATUS current
DESCRIPTION
        "Table of all Email Address data"
 ::= { cps6000  19 }

cps6000CoeEntry OBJECT-TYPE
SYNTAX     Cps6000CoeEntry
MAX-ACCESS  not-accessible
STATUS      current
DESCRIPTION
       "Entry of information for one Email Address"
INDEX { cps6000CoeEntryIndex }
 ::= { cps6000CoeTable  1 }

Cps6000CoeEntry ::= SEQUENCE {
cps6000CoeEntryIndex   INTEGER,
cps6000CoeEntryIde   DisplayString,
cps6000CoeEntryDes   DisplayString,
cps6000CoeEntryAdr   DisplayString,
cps6000CoeEntryTyp   DisplayString
}

cps6000CoeEntryIndex OBJECT-TYPE
SYNTAX      INTEGER (0..2147483647)
MAX-ACCESS  read-only
STATUS      current
DESCRIPTION
"Table Index"
 ::= { cps6000CoeEntry  1 }

cps6000CoeEntryIde OBJECT-TYPE
SYNTAX      DisplayString
MAX-ACCESS  read-only
STATUS      current
DESCRIPTION
"Identifier"
 ::= { cps6000CoeEntry  2 }

cps6000CoeEntryDes OBJECT-TYPE
SYNTAX      DisplayString
MAX-ACCESS  read-write
STATUS      current
DESCRIPTION
"Description"
 ::= { cps6000CoeEntry  3 }

cps6000CoeEntryAdr OBJECT-TYPE
SYNTAX      DisplayString
MAX-ACCESS  read-write
STATUS      current
DESCRIPTION
"Email Address"
 ::= { cps6000CoeEntry  4 }

cps6000CoeEntryTyp OBJECT-TYPE
SYNTAX      DisplayString
MAX-ACCESS  read-write
STATUS      current
DESCRIPTION
"Address Type"
 ::= { cps6000CoeEntry  5 }



--
-- table SND
--

cps6000SndTable    OBJECT-TYPE
SYNTAX SEQUENCE OF Cps6000SndEntry
MAX-ACCESS not-accessible
STATUS current
DESCRIPTION
        "Table of all SNMP Trap Destination data"
 ::= { cps6000  20 }

cps6000SndEntry OBJECT-TYPE
SYNTAX     Cps6000SndEntry
MAX-ACCESS  not-accessible
STATUS      current
DESCRIPTION
       "Entry of information for one SNMP Trap Destination"
INDEX { cps6000SndEntryIndex }
 ::= { cps6000SndTable  1 }

Cps6000SndEntry ::= SEQUENCE {
cps6000SndEntryIndex   INTEGER,
cps6000SndEntryIde   DisplayString,
cps6000SndEntryDes   DisplayString,
cps6000SndEntryIp   DisplayString,
cps6000SndEntryCs   DisplayString
}

cps6000SndEntryIndex OBJECT-TYPE
SYNTAX      INTEGER (0..2147483647)
MAX-ACCESS  read-only
STATUS      current
DESCRIPTION
"Table Index"
 ::= { cps6000SndEntry  1 }

cps6000SndEntryIde OBJECT-TYPE
SYNTAX      DisplayString
MAX-ACCESS  read-only
STATUS      current
DESCRIPTION
"Identifier"
 ::= { cps6000SndEntry  2 }

cps6000SndEntryDes OBJECT-TYPE
SYNTAX      DisplayString
MAX-ACCESS  read-write
STATUS      current
DESCRIPTION
"Description"
 ::= { cps6000SndEntry  3 }

cps6000SndEntryIp OBJECT-TYPE
SYNTAX      DisplayString
MAX-ACCESS  read-write
STATUS      current
DESCRIPTION
"IP Address"
 ::= { cps6000SndEntry  4 }

cps6000SndEntryCs OBJECT-TYPE
SYNTAX      DisplayString
MAX-ACCESS  read-write
STATUS      current
DESCRIPTION
"Community String"
 ::= { cps6000SndEntry  5 }



--
-- object cps6000Po1
--

cps6000Po1 OBJECT IDENTIFIER  ::= { cps6000  21 }

cps6000Po1Ide OBJECT-TYPE
SYNTAX      DisplayString
MAX-ACCESS  read-only
STATUS      current
DESCRIPTION
"Identifier"
 ::= { cps6000Po1  1 }

cps6000Po1Des OBJECT-TYPE
SYNTAX      DisplayString
MAX-ACCESS  read-write
STATUS      current
DESCRIPTION
"Description"
 ::= { cps6000Po1  2 }

cps6000Po1Phn OBJECT-TYPE
SYNTAX      DisplayString
MAX-ACCESS  read-write
STATUS      current
DESCRIPTION
"Phone Number"
 ::= { cps6000Po1  3 }

cps6000Po1Bdr OBJECT-TYPE
SYNTAX      INTEGER {
b300(300),
b1200(1200),
b2400(2400),
b4800(4800),
b9600(9600),
b19200(19200)
}
MAX-ACCESS  read-write
STATUS      current
DESCRIPTION
"Connect Baudrate
Values:
b300(300),
b1200(1200),
b2400(2400),
b4800(4800),
b9600(9600),
b19200(19200)
"
 ::= { cps6000Po1  4 }

cps6000Po1Dbt OBJECT-TYPE
SYNTAX      INTEGER {
d7(7),
d8(8)
}
MAX-ACCESS  read-write
STATUS      current
DESCRIPTION
"Data Bits
Values:
d7(7),
d8(8)
"
 ::= { cps6000Po1  5 }

cps6000Po1Pry OBJECT-TYPE
SYNTAX      DisplayString
MAX-ACCESS  read-write
STATUS      current
DESCRIPTION
"Parity
Values:
O,
E,
N
"
 ::= { cps6000Po1  6 }

cps6000Po1Sbt OBJECT-TYPE
SYNTAX      INTEGER {
s1(1),
s2(2)
}
MAX-ACCESS  read-write
STATUS      current
DESCRIPTION
"Stop Bits
Values:
s1(1),
s2(2)
"
 ::= { cps6000Po1  7 }

cps6000Po1Int OBJECT-TYPE
SYNTAX      DisplayString
MAX-ACCESS  read-write
STATUS      current
DESCRIPTION
"Interval
Values:
Sunday,
Monday,
Tuesday,
Wednesday,
Thursday,
Friday,
Saturday,
Daily,
Monthly,
Quarterly,
Never
"
 ::= { cps6000Po1  8 }

cps6000Po1Tim OBJECT-TYPE
SYNTAX      DisplayString
MAX-ACCESS  read-write
STATUS      current
DESCRIPTION
"Time"
 ::= { cps6000Po1  9 }

cps6000Po1Cl01 OBJECT-TYPE
SYNTAX      DisplayString
MAX-ACCESS  read-write
STATUS      current
DESCRIPTION
"Command Line 1"
 ::= { cps6000Po1  10 }

cps6000Po1Cl02 OBJECT-TYPE
SYNTAX      DisplayString
MAX-ACCESS  read-write
STATUS      current
DESCRIPTION
"Command Line 2"
 ::= { cps6000Po1  11 }

cps6000Po1Cl03 OBJECT-TYPE
SYNTAX      DisplayString
MAX-ACCESS  read-write
STATUS      current
DESCRIPTION
"Command Line 3"
 ::= { cps6000Po1  12 }

cps6000Po1Cl04 OBJECT-TYPE
SYNTAX      DisplayString
MAX-ACCESS  read-write
STATUS      current
DESCRIPTION
"Command Line 4"
 ::= { cps6000Po1  13 }

cps6000Po1Cl05 OBJECT-TYPE
SYNTAX      DisplayString
MAX-ACCESS  read-write
STATUS      current
DESCRIPTION
"Command Line 5"
 ::= { cps6000Po1  14 }

cps6000Po1Cl06 OBJECT-TYPE
SYNTAX      DisplayString
MAX-ACCESS  read-write
STATUS      current
DESCRIPTION
"Command Line 6"
 ::= { cps6000Po1  15 }

cps6000Po1Cl07 OBJECT-TYPE
SYNTAX      DisplayString
MAX-ACCESS  read-write
STATUS      current
DESCRIPTION
"Command Line 7"
 ::= { cps6000Po1  16 }

cps6000Po1Cl08 OBJECT-TYPE
SYNTAX      DisplayString
MAX-ACCESS  read-write
STATUS      current
DESCRIPTION
"Command Line 8"
 ::= { cps6000Po1  17 }

cps6000Po1Cl09 OBJECT-TYPE
SYNTAX      DisplayString
MAX-ACCESS  read-write
STATUS      current
DESCRIPTION
"Command Line 9"
 ::= { cps6000Po1  18 }

cps6000Po1Cl10 OBJECT-TYPE
SYNTAX      DisplayString
MAX-ACCESS  read-write
STATUS      current
DESCRIPTION
"Command Line 10"
 ::= { cps6000Po1  19 }

cps6000Po1Por OBJECT-TYPE
SYNTAX      DisplayString
MAX-ACCESS  read-only
STATUS      current
DESCRIPTION
"Number Did Not Respond
Value:
Alarm report from POR1
"
 ::= { cps6000Po1  20 }


--
-- object cps6000Cb1
--

cps6000Cb1 OBJECT IDENTIFIER  ::= { cps6000  22 }

cps6000Cb1Ide OBJECT-TYPE
SYNTAX      DisplayString
MAX-ACCESS  read-only
STATUS      current
DESCRIPTION
"Identifier"
 ::= { cps6000Cb1  1 }

cps6000Cb1Des OBJECT-TYPE
SYNTAX      DisplayString
MAX-ACCESS  read-write
STATUS      current
DESCRIPTION
"Description"
 ::= { cps6000Cb1  2 }

cps6000Cb1Stt OBJECT-TYPE
SYNTAX      INTEGER {
off(0),
on(1)
}
MAX-ACCESS  read-write
STATUS      current
DESCRIPTION
"State
Values:
off(0),
on(1)
"
 ::= { cps6000Cb1  3 }

cps6000Cb1Ph1 OBJECT-TYPE
SYNTAX      DisplayString
MAX-ACCESS  read-write
STATUS      current
DESCRIPTION
"Call-Back Phone Number 1"
 ::= { cps6000Cb1  4 }

cps6000Cb1Br1 OBJECT-TYPE
SYNTAX      INTEGER {
b300(300),
b1200(1200),
b2400(2400),
b4800(4800),
b9600(9600),
b19200(19200)
}
MAX-ACCESS  read-write
STATUS      current
DESCRIPTION
"Connect Baudrate 1
Values:
b300(300),
b1200(1200),
b2400(2400),
b4800(4800),
b9600(9600),
b19200(19200)
"
 ::= { cps6000Cb1  5 }

cps6000Cb1Ph2 OBJECT-TYPE
SYNTAX      DisplayString
MAX-ACCESS  read-write
STATUS      current
DESCRIPTION
"Call-Back Phone Number 2"
 ::= { cps6000Cb1  6 }

cps6000Cb1Br2 OBJECT-TYPE
SYNTAX      INTEGER {
b300(300),
b1200(1200),
b2400(2400),
b4800(4800),
b9600(9600),
b19200(19200)
}
MAX-ACCESS  read-write
STATUS      current
DESCRIPTION
"Connect Baudrate 2
Values:
b300(300),
b1200(1200),
b2400(2400),
b4800(4800),
b9600(9600),
b19200(19200)
"
 ::= { cps6000Cb1  7 }

cps6000Cb1Ph3 OBJECT-TYPE
SYNTAX      DisplayString
MAX-ACCESS  read-write
STATUS      current
DESCRIPTION
"Call-Back Phone Number 3"
 ::= { cps6000Cb1  8 }

cps6000Cb1Br3 OBJECT-TYPE
SYNTAX      INTEGER {
b300(300),
b1200(1200),
b2400(2400),
b4800(4800),
b9600(9600),
b19200(19200)
}
MAX-ACCESS  read-write
STATUS      current
DESCRIPTION
"Connect Baudrate 3
Values:
b300(300),
b1200(1200),
b2400(2400),
b4800(4800),
b9600(9600),
b19200(19200)
"
 ::= { cps6000Cb1  9 }

cps6000Cb1Ph4 OBJECT-TYPE
SYNTAX      DisplayString
MAX-ACCESS  read-write
STATUS      current
DESCRIPTION
"Call-Back Phone Number 4"
 ::= { cps6000Cb1  10 }

cps6000Cb1Br4 OBJECT-TYPE
SYNTAX      INTEGER {
b300(300),
b1200(1200),
b2400(2400),
b4800(4800),
b9600(9600),
b19200(19200)
}
MAX-ACCESS  read-write
STATUS      current
DESCRIPTION
"Connect Baudrate 4
Values:
b300(300),
b1200(1200),
b2400(2400),
b4800(4800),
b9600(9600),
b19200(19200)
"
 ::= { cps6000Cb1  11 }

cps6000Cb1Ph5 OBJECT-TYPE
SYNTAX      DisplayString
MAX-ACCESS  read-write
STATUS      current
DESCRIPTION
"Call-Back Phone Number 5"
 ::= { cps6000Cb1  12 }

cps6000Cb1Br5 OBJECT-TYPE
SYNTAX      INTEGER {
b300(300),
b1200(1200),
b2400(2400),
b4800(4800),
b9600(9600),
b19200(19200)
}
MAX-ACCESS  read-write
STATUS      current
DESCRIPTION
"Connect Baudrate 5
Values:
b300(300),
b1200(1200),
b2400(2400),
b4800(4800),
b9600(9600),
b19200(19200)
"
 ::= { cps6000Cb1  13 }


--
-- object cps6000Mp1
--

cps6000Mp1 OBJECT IDENTIFIER  ::= { cps6000  23 }

cps6000Mp1Ide OBJECT-TYPE
SYNTAX      DisplayString
MAX-ACCESS  read-only
STATUS      current
DESCRIPTION
"Identifier"
 ::= { cps6000Mp1  1 }

cps6000Mp1Des OBJECT-TYPE
SYNTAX      DisplayString
MAX-ACCESS  read-write
STATUS      current
DESCRIPTION
"Description"
 ::= { cps6000Mp1  2 }

cps6000Mp1Stt OBJECT-TYPE
SYNTAX      DisplayString
MAX-ACCESS  read-only
STATUS      current
DESCRIPTION
"State"
 ::= { cps6000Mp1  3 }

cps6000Mp1Dbt OBJECT-TYPE
SYNTAX      INTEGER {
d7(7),
d8(8)
}
MAX-ACCESS  read-write
STATUS      current
DESCRIPTION
"Data Bits
Values:
d7(7),
d8(8)
"
 ::= { cps6000Mp1  4 }

cps6000Mp1Bdr OBJECT-TYPE
SYNTAX      INTEGER {
b300(300),
b1200(1200),
b2400(2400),
b4800(4800),
b9600(9600),
b19200(19200)
}
MAX-ACCESS  read-write
STATUS      current
DESCRIPTION
"Baudrate
Values:
b300(300),
b1200(1200),
b2400(2400),
b4800(4800),
b9600(9600),
b19200(19200)
"
 ::= { cps6000Mp1  5 }

cps6000Mp1Pry OBJECT-TYPE
SYNTAX      DisplayString
MAX-ACCESS  read-write
STATUS      current
DESCRIPTION
"Parity
Values:
O,
E,
N
"
 ::= { cps6000Mp1  6 }

cps6000Mp1Sbt OBJECT-TYPE
SYNTAX      INTEGER {
s1(1),
s2(2)
}
MAX-ACCESS  read-write
STATUS      current
DESCRIPTION
"Stop Bits
Values:
s1(1),
s2(2)
"
 ::= { cps6000Mp1  7 }

cps6000Mp1Tmo OBJECT-TYPE
SYNTAX      Integer32(0..45)
UNITS       "Minutes"
MAX-ACCESS  read-write
STATUS      current
DESCRIPTION
"Time-Out (Minutes)"
 ::= { cps6000Mp1  8 }

cps6000Mp1Hsh OBJECT-TYPE
SYNTAX      DisplayString
MAX-ACCESS  read-write
STATUS      current
DESCRIPTION
"Handshaking
Values:
NO,
SW
"
 ::= { cps6000Mp1  9 }

cps6000Mp1Nrg OBJECT-TYPE
SYNTAX      Integer32(2..15)
MAX-ACCESS  read-write
STATUS      current
DESCRIPTION
"Number of Rings Before Answer"
 ::= { cps6000Mp1  10 }

cps6000Mp1Wre OBJECT-TYPE
SYNTAX      INTEGER {
disable(0),
enable(1)
}
MAX-ACCESS  read-write
STATUS      current
DESCRIPTION
"Write Enable
Values:
disable(0),
enable(1)
"
 ::= { cps6000Mp1  11 }

cps6000Mp1Ins OBJECT-TYPE
SYNTAX      DisplayString
MAX-ACCESS  read-write
STATUS      current
DESCRIPTION
"Modem Init String"
 ::= { cps6000Mp1  12 }


--
-- object cps6000Lp1
--

cps6000Lp1 OBJECT IDENTIFIER  ::= { cps6000  24 }

cps6000Lp1Ide OBJECT-TYPE
SYNTAX      DisplayString
MAX-ACCESS  read-only
STATUS      current
DESCRIPTION
"Identifier"
 ::= { cps6000Lp1  1 }

cps6000Lp1Des OBJECT-TYPE
SYNTAX      DisplayString
MAX-ACCESS  read-write
STATUS      current
DESCRIPTION
"Description"
 ::= { cps6000Lp1  2 }

cps6000Lp1Stt OBJECT-TYPE
SYNTAX      DisplayString
MAX-ACCESS  read-only
STATUS      current
DESCRIPTION
"State"
 ::= { cps6000Lp1  3 }

cps6000Lp1Bdr OBJECT-TYPE
SYNTAX      DisplayString
MAX-ACCESS  read-write
STATUS      current
DESCRIPTION
"Baudrate
Values:
300,
1200,
2400,
4800,
9600,
19200,
AUTO
"
 ::= { cps6000Lp1  4 }

cps6000Lp1Dbt OBJECT-TYPE
SYNTAX      INTEGER {
d7(7),
d8(8)
}
MAX-ACCESS  read-write
STATUS      current
DESCRIPTION
"Data Bits
Values:
d7(7),
d8(8)
"
 ::= { cps6000Lp1  5 }

cps6000Lp1Pry OBJECT-TYPE
SYNTAX      DisplayString
MAX-ACCESS  read-write
STATUS      current
DESCRIPTION
"Parity
Values:
O,
E,
N
"
 ::= { cps6000Lp1  6 }

cps6000Lp1Sbt OBJECT-TYPE
SYNTAX      INTEGER {
s1(1),
s2(2)
}
MAX-ACCESS  read-write
STATUS      current
DESCRIPTION
"Stop Bits
Values:
s1(1),
s2(2)
"
 ::= { cps6000Lp1  7 }

cps6000Lp1Tmo OBJECT-TYPE
SYNTAX      Integer32(0..45)
UNITS       "Minutes"
MAX-ACCESS  read-write
STATUS      current
DESCRIPTION
"Time-Out (Minutes)"
 ::= { cps6000Lp1  8 }

cps6000Lp1Hsh OBJECT-TYPE
SYNTAX      DisplayString
MAX-ACCESS  read-write
STATUS      current
DESCRIPTION
"Handshaking
Values:
NO,
HW,
SW
"
 ::= { cps6000Lp1  9 }

cps6000Lp1App OBJECT-TYPE
SYNTAX      DisplayString
MAX-ACCESS  read-write
STATUS      current
DESCRIPTION
"Application
Values:
TERMINAL,
TL1,
EVENT LOG
"
 ::= { cps6000Lp1  10 }

cps6000Lp1Wre OBJECT-TYPE
SYNTAX      INTEGER {
disable(0),
enable(1)
}
MAX-ACCESS  read-write
STATUS      current
DESCRIPTION
"Write Enable
Values:
disable(0),
enable(1)
"
 ::= { cps6000Lp1  11 }


--
-- object cps6000Tlm1
--

cps6000Tlm1 OBJECT IDENTIFIER  ::= { cps6000  25 }

cps6000Tlm1Ide OBJECT-TYPE
SYNTAX      DisplayString
MAX-ACCESS  read-only
STATUS      current
DESCRIPTION
"Identifier"
 ::= { cps6000Tlm1  1 }

cps6000Tlm1Des OBJECT-TYPE
SYNTAX      DisplayString
MAX-ACCESS  read-write
STATUS      current
DESCRIPTION
"Description"
 ::= { cps6000Tlm1  2 }

cps6000Tlm1Aue OBJECT-TYPE
SYNTAX      INTEGER {
disable(0),
enable(1)
}
MAX-ACCESS  read-write
STATUS      current
DESCRIPTION
"Activate-User Enable
Values:
disable(0),
enable(1)
"
 ::= { cps6000Tlm1  3 }

cps6000Tlm1Cts OBJECT-TYPE
SYNTAX      INTEGER {
disable(0),
enable(1)
}
MAX-ACCESS  read-write
STATUS      current
DESCRIPTION
"CTS Connect Detection
Values:
disable(0),
enable(1)
"
 ::= { cps6000Tlm1  4 }

cps6000Tlm1Dsr OBJECT-TYPE
SYNTAX      INTEGER {
disable(0),
enable(1)
}
MAX-ACCESS  read-write
STATUS      current
DESCRIPTION
"DSR Connect Detection
Values:
disable(0),
enable(1)
"
 ::= { cps6000Tlm1  5 }

cps6000Tlm1Prt OBJECT-TYPE
SYNTAX      Integer32
MAX-ACCESS  read-write
STATUS      current
DESCRIPTION
"TCP/IP Port"
 ::= { cps6000Tlm1  6 }


--
-- table TL1
--

cps6000Tl1Table    OBJECT-TYPE
SYNTAX SEQUENCE OF Cps6000Tl1Entry
MAX-ACCESS not-accessible
STATUS current
DESCRIPTION
        "Table of all TL1 Object data"
 ::= { cps6000  26 }

cps6000Tl1Entry OBJECT-TYPE
SYNTAX     Cps6000Tl1Entry
MAX-ACCESS  not-accessible
STATUS      current
DESCRIPTION
       "Entry of information for one TL1 Object"
INDEX { cps6000Tl1EntryIndex }
 ::= { cps6000Tl1Table  1 }

Cps6000Tl1Entry ::= SEQUENCE {
cps6000Tl1EntryIndex   INTEGER,
cps6000Tl1EntryIde   DisplayString,
cps6000Tl1EntryDes   DisplayString,
cps6000Tl1EntryCds   DisplayString,
cps6000Tl1EntryAid   DisplayString,
cps6000Tl1EntryCnd   DisplayString,
cps6000Tl1EntrySaf   INTEGER,
cps6000Tl1EntryRpt   DisplayString
}

cps6000Tl1EntryIndex OBJECT-TYPE
SYNTAX      INTEGER (0..2147483647)
MAX-ACCESS  read-only
STATUS      current
DESCRIPTION
"Table Index"
 ::= { cps6000Tl1Entry  1 }

cps6000Tl1EntryIde OBJECT-TYPE
SYNTAX      DisplayString
MAX-ACCESS  read-only
STATUS      current
DESCRIPTION
"Identifier"
 ::= { cps6000Tl1Entry  2 }

cps6000Tl1EntryDes OBJECT-TYPE
SYNTAX      DisplayString
MAX-ACCESS  read-write
STATUS      current
DESCRIPTION
"Description"
 ::= { cps6000Tl1Entry  3 }

cps6000Tl1EntryCds OBJECT-TYPE
SYNTAX      DisplayString
MAX-ACCESS  read-write
STATUS      current
DESCRIPTION
"Condition Description"
 ::= { cps6000Tl1Entry  4 }

cps6000Tl1EntryAid OBJECT-TYPE
SYNTAX      DisplayString
MAX-ACCESS  read-write
STATUS      current
DESCRIPTION
"Aid"
 ::= { cps6000Tl1Entry  5 }

cps6000Tl1EntryCnd OBJECT-TYPE
SYNTAX      DisplayString
MAX-ACCESS  read-write
STATUS      current
DESCRIPTION
"Condition Type"
 ::= { cps6000Tl1Entry  6 }

cps6000Tl1EntrySaf OBJECT-TYPE
SYNTAX      INTEGER {
no(0),
yes(1)
}
MAX-ACCESS  read-write
STATUS      current
DESCRIPTION
"Service Affecting
Values:
no(0),
yes(1)
"
 ::= { cps6000Tl1Entry  7 }

cps6000Tl1EntryRpt OBJECT-TYPE
SYNTAX      DisplayString
MAX-ACCESS  read-write
STATUS      current
DESCRIPTION
"Reporting
Values:
EQUIPMENT,
ENVIRONMENT,
PRESENCE
"
 ::= { cps6000Tl1Entry  8 }



--
-- object cps6000Net1
--

cps6000Net1 OBJECT IDENTIFIER  ::= { cps6000  27 }

cps6000Net1Ide OBJECT-TYPE
SYNTAX      DisplayString
MAX-ACCESS  read-only
STATUS      current
DESCRIPTION
"Identifier"
 ::= { cps6000Net1  1 }

cps6000Net1Des OBJECT-TYPE
SYNTAX      DisplayString
MAX-ACCESS  read-write
STATUS      current
DESCRIPTION
"Description"
 ::= { cps6000Net1  2 }

cps6000Net1Ead OBJECT-TYPE
SYNTAX      DisplayString
MAX-ACCESS  read-only
STATUS      current
DESCRIPTION
"Ethernet Address"
 ::= { cps6000Net1  3 }

cps6000Net1Dhcp OBJECT-TYPE
SYNTAX      INTEGER {
disable(0),
enable(1)
}
MAX-ACCESS  read-write
STATUS      current
DESCRIPTION
"DHCP
Values:
disable(0),
enable(1)
"
 ::= { cps6000Net1  4 }

cps6000Net1Ip OBJECT-TYPE
SYNTAX      DisplayString
MAX-ACCESS  read-write
STATUS      current
DESCRIPTION
"Static IP Address"
 ::= { cps6000Net1  5 }

cps6000Net1Wip OBJECT-TYPE
SYNTAX      DisplayString
MAX-ACCESS  read-only
STATUS      current
DESCRIPTION
"Working IP Address"
 ::= { cps6000Net1  6 }

cps6000Net1Sub OBJECT-TYPE
SYNTAX      DisplayString
MAX-ACCESS  read-write
STATUS      current
DESCRIPTION
"Subnet Mask"
 ::= { cps6000Net1  7 }

cps6000Net1Gtwy OBJECT-TYPE
SYNTAX      DisplayString
MAX-ACCESS  read-write
STATUS      current
DESCRIPTION
"Default Gateway"
 ::= { cps6000Net1  8 }

cps6000Net1Host OBJECT-TYPE
SYNTAX      DisplayString
MAX-ACCESS  read-write
STATUS      current
DESCRIPTION
"Host Name"
 ::= { cps6000Net1  9 }

cps6000Net1Dom OBJECT-TYPE
SYNTAX      DisplayString
MAX-ACCESS  read-write
STATUS      current
DESCRIPTION
"Domain Name"
 ::= { cps6000Net1  10 }

cps6000Net1Dns OBJECT-TYPE
SYNTAX      DisplayString
MAX-ACCESS  read-write
STATUS      current
DESCRIPTION
"DNS Server Address"
 ::= { cps6000Net1  11 }

cps6000Net1Wre OBJECT-TYPE
SYNTAX      INTEGER {
disable(0),
enable(1)
}
MAX-ACCESS  read-write
STATUS      current
DESCRIPTION
"Write Enable
Values:
disable(0),
enable(1)
"
 ::= { cps6000Net1  12 }

cps6000Net1Tmo OBJECT-TYPE
SYNTAX      Integer32
UNITS       "Minutes"
MAX-ACCESS  read-write
STATUS      current
DESCRIPTION
"Timeout (Minutes)"
 ::= { cps6000Net1  13 }

cps6000Net1Msrv OBJECT-TYPE
SYNTAX      DisplayString
MAX-ACCESS  read-write
STATUS      current
DESCRIPTION
"Mail Server Address"
 ::= { cps6000Net1  14 }


--
-- table DRC
--

cps6000DrcTable    OBJECT-TYPE
SYNTAX SEQUENCE OF Cps6000DrcEntry
MAX-ACCESS not-accessible
STATUS current
DESCRIPTION
        "Table of all Derived Channel data"
 ::= { cps6000  28 }

cps6000DrcEntry OBJECT-TYPE
SYNTAX     Cps6000DrcEntry
MAX-ACCESS  not-accessible
STATUS      current
DESCRIPTION
       "Entry of information for one Derived Channel"
INDEX { cps6000DrcEntryIndex }
 ::= { cps6000DrcTable  1 }

Cps6000DrcEntry ::= SEQUENCE {
cps6000DrcEntryIndex   INTEGER,
cps6000DrcEntryIde   DisplayString,
cps6000DrcEntryDes   DisplayString,
cps6000DrcEntryVal   DisplayString,
cps6000DrcEntryPrg   DisplayString,
cps6000DrcEntryUni   DisplayString
}

cps6000DrcEntryIndex OBJECT-TYPE
SYNTAX      INTEGER (0..2147483647)
MAX-ACCESS  read-only
STATUS      current
DESCRIPTION
"Table Index"
 ::= { cps6000DrcEntry  1 }

cps6000DrcEntryIde OBJECT-TYPE
SYNTAX      DisplayString
MAX-ACCESS  read-only
STATUS      current
DESCRIPTION
"Identifier"
 ::= { cps6000DrcEntry  2 }

cps6000DrcEntryDes OBJECT-TYPE
SYNTAX      DisplayString
MAX-ACCESS  read-write
STATUS      current
DESCRIPTION
"Description"
 ::= { cps6000DrcEntry  3 }

cps6000DrcEntryVal OBJECT-TYPE
SYNTAX      DisplayString
MAX-ACCESS  read-only
STATUS      current
DESCRIPTION
"Value"
 ::= { cps6000DrcEntry  4 }

cps6000DrcEntryPrg OBJECT-TYPE
SYNTAX      DisplayString
MAX-ACCESS  read-write
STATUS      current
DESCRIPTION
"Program Line"
 ::= { cps6000DrcEntry  5 }

cps6000DrcEntryUni OBJECT-TYPE
SYNTAX      DisplayString
MAX-ACCESS  read-write
STATUS      current
DESCRIPTION
"Unit"
 ::= { cps6000DrcEntry  6 }



--
-- table INP
--

cps6000InpTable    OBJECT-TYPE
SYNTAX SEQUENCE OF Cps6000InpEntry
MAX-ACCESS not-accessible
STATUS current
DESCRIPTION
        "Table of all Input Management data"
 ::= { cps6000  29 }

cps6000InpEntry OBJECT-TYPE
SYNTAX     Cps6000InpEntry
MAX-ACCESS  not-accessible
STATUS      current
DESCRIPTION
       "Entry of information for one Input Management"
INDEX { cps6000InpEntryIndex }
 ::= { cps6000InpTable  1 }

Cps6000InpEntry ::= SEQUENCE {
cps6000InpEntryIndex   INTEGER,
cps6000InpEntryIde   DisplayString,
cps6000InpEntryDes   DisplayString,
cps6000InpEntryStt   INTEGER,
cps6000InpEntryTyp   DisplayString,
cps6000InpEntryPol   DisplayString,
cps6000InpEntrySn   DisplayString,
cps6000InpEntryBrc   DisplayString
}

cps6000InpEntryIndex OBJECT-TYPE
SYNTAX      INTEGER (0..2147483647)
MAX-ACCESS  read-only
STATUS      current
DESCRIPTION
"Table Index"
 ::= { cps6000InpEntry  1 }

cps6000InpEntryIde OBJECT-TYPE
SYNTAX      DisplayString
MAX-ACCESS  read-only
STATUS      current
DESCRIPTION
"Identifier"
 ::= { cps6000InpEntry  2 }

cps6000InpEntryDes OBJECT-TYPE
SYNTAX      DisplayString
MAX-ACCESS  read-write
STATUS      current
DESCRIPTION
"Description"
 ::= { cps6000InpEntry  3 }

cps6000InpEntryStt OBJECT-TYPE
SYNTAX      INTEGER {
alarming(1),
nonAlarming(0)
}
MAX-ACCESS  read-only
STATUS      current
DESCRIPTION
"Input State
Values:
alarming(1),
nonAlarming(0)
"
 ::= { cps6000InpEntry  4 }

cps6000InpEntryTyp OBJECT-TYPE
SYNTAX      DisplayString
MAX-ACCESS  read-write
STATUS      current
DESCRIPTION
"Type Alarm Object ID or, REMLVD for Remote LVD"
 ::= { cps6000InpEntry  5 }

cps6000InpEntryPol OBJECT-TYPE
SYNTAX      DisplayString
MAX-ACCESS  read-write
STATUS      current
DESCRIPTION
"Input Alarming Polarity
Values:
OPEN,
CLOSED
"
 ::= { cps6000InpEntry  6 }

cps6000InpEntrySn OBJECT-TYPE
SYNTAX      DisplayString
MAX-ACCESS  read-only
STATUS      current
DESCRIPTION
"Serial Number"
 ::= { cps6000InpEntry  7 }

cps6000InpEntryBrc OBJECT-TYPE
SYNTAX      DisplayString
MAX-ACCESS  read-only
STATUS      current
DESCRIPTION
"Board Code"
 ::= { cps6000InpEntry  8 }



--
-- object cps6000Rp1
--

cps6000Rp1 OBJECT IDENTIFIER  ::= { cps6000  30 }

cps6000Rp1Ide OBJECT-TYPE
SYNTAX      DisplayString
MAX-ACCESS  read-only
STATUS      current
DESCRIPTION
"Identifier"
 ::= { cps6000Rp1  1 }

cps6000Rp1Des OBJECT-TYPE
SYNTAX      DisplayString
MAX-ACCESS  read-write
STATUS      current
DESCRIPTION
"Description"
 ::= { cps6000Rp1  2 }

cps6000Rp1Frq OBJECT-TYPE
SYNTAX      Integer32(15..50)
UNITS       "Hz"
MAX-ACCESS  read-write
STATUS      current
DESCRIPTION
"Frequency (Hz)"
 ::= { cps6000Rp1  3 }

cps6000Rp1Vsp OBJECT-TYPE
SYNTAX      Integer32(65..100)
UNITS       "Volts"
MAX-ACCESS  read-write
STATUS      current
DESCRIPTION
"Voltage Set-point (Volts)"
 ::= { cps6000Rp1  4 }

cps6000Rp1Ofe OBJECT-TYPE
SYNTAX      INTEGER {
disable(0),
enable(1)
}
MAX-ACCESS  read-write
STATUS      current
DESCRIPTION
"Offset
Values:
disable(0),
enable(1)
"
 ::= { cps6000Rp1  5 }

cps6000Rp1Rme OBJECT-TYPE
SYNTAX      INTEGER {
disable(0),
enable(1)
}
MAX-ACCESS  read-write
STATUS      current
DESCRIPTION
"Redundancy Monitor
Values:
disable(0),
enable(1)
"
 ::= { cps6000Rp1  6 }

cps6000Rp1Rss OBJECT-TYPE
SYNTAX      INTEGER {
restart(1)
}
MAX-ACCESS  read-write
STATUS      current
DESCRIPTION
"Restart
Values:
restart(1)
"
 ::= { cps6000Rp1  7 }

cps6000Rp1Rf OBJECT-TYPE
SYNTAX      DisplayString
MAX-ACCESS  read-only
STATUS      current
DESCRIPTION
"Ringer Minor Fail"
 ::= { cps6000Rp1  8 }

cps6000Rp1Rpff OBJECT-TYPE
SYNTAX      DisplayString
MAX-ACCESS  read-only
STATUS      current
DESCRIPTION
"Ringer Fan Fail"
 ::= { cps6000Rp1  9 }

cps6000Rp1Rpxj OBJECT-TYPE
SYNTAX      DisplayString
MAX-ACCESS  read-only
STATUS      current
DESCRIPTION
"Ringer Major External Fault"
 ::= { cps6000Rp1  10 }

cps6000Rp1Rpxn OBJECT-TYPE
SYNTAX      DisplayString
MAX-ACCESS  read-only
STATUS      current
DESCRIPTION
"Ringer Minor External Fault"
 ::= { cps6000Rp1  11 }

cps6000Rp1Rprl OBJECT-TYPE
SYNTAX      DisplayString
MAX-ACCESS  read-only
STATUS      current
DESCRIPTION
"Ringer Redundency Loss"
 ::= { cps6000Rp1  12 }

cps6000Rp1Rpfj OBJECT-TYPE
SYNTAX      DisplayString
MAX-ACCESS  read-only
STATUS      current
DESCRIPTION
"Ringer Major Fail"
 ::= { cps6000Rp1  13 }

cps6000Rp1Rcdp OBJECT-TYPE
SYNTAX      DisplayString
MAX-ACCESS  read-only
STATUS      current
DESCRIPTION
"Ringer ID Conflict
Value:
Alarm report from RCDP1
"
 ::= { cps6000Rp1  14 }


--
-- table RCH
--

cps6000RchTable    OBJECT-TYPE
SYNTAX SEQUENCE OF Cps6000RchEntry
MAX-ACCESS not-accessible
STATUS current
DESCRIPTION
        "Table of all Ringer Chassis data"
 ::= { cps6000  31 }

cps6000RchEntry OBJECT-TYPE
SYNTAX     Cps6000RchEntry
MAX-ACCESS  not-accessible
STATUS      current
DESCRIPTION
       "Entry of information for one Ringer Chassis"
INDEX { cps6000RchEntryIndex }
 ::= { cps6000RchTable  1 }

Cps6000RchEntry ::= SEQUENCE {
cps6000RchEntryIndex   INTEGER,
cps6000RchEntryIde   DisplayString,
cps6000RchEntryDes   DisplayString,
cps6000RchEntryStt   DisplayString,
cps6000RchEntryVa   Integer32,
cps6000RchEntryPri   DisplayString,
cps6000RchEntrySec   DisplayString,
cps6000RchEntryRf   INTEGER,
cps6000RchEntryRpff   INTEGER,
cps6000RchEntryRpxj   INTEGER,
cps6000RchEntryRpxn   INTEGER,
cps6000RchEntryRprl   INTEGER,
cps6000RchEntryRpfj   INTEGER,
cps6000RchEntryRcdp   INTEGER
}

cps6000RchEntryIndex OBJECT-TYPE
SYNTAX      INTEGER (0..2147483647)
MAX-ACCESS  read-only
STATUS      current
DESCRIPTION
"Table Index"
 ::= { cps6000RchEntry  1 }

cps6000RchEntryIde OBJECT-TYPE
SYNTAX      DisplayString
MAX-ACCESS  read-only
STATUS      current
DESCRIPTION
"Identifier"
 ::= { cps6000RchEntry  2 }

cps6000RchEntryDes OBJECT-TYPE
SYNTAX      DisplayString
MAX-ACCESS  read-write
STATUS      current
DESCRIPTION
"Description"
 ::= { cps6000RchEntry  3 }

cps6000RchEntryStt OBJECT-TYPE
SYNTAX      DisplayString
MAX-ACCESS  read-write
STATUS      current
DESCRIPTION
"Ringer Group State"
 ::= { cps6000RchEntry  4 }

cps6000RchEntryVa OBJECT-TYPE
SYNTAX      Integer32
MAX-ACCESS  read-only
STATUS      current
DESCRIPTION
"Ringer Output VA"
 ::= { cps6000RchEntry  5 }

cps6000RchEntryPri OBJECT-TYPE
SYNTAX      DisplayString
MAX-ACCESS  read-only
STATUS      current
DESCRIPTION
"Primary Ringer"
 ::= { cps6000RchEntry  6 }

cps6000RchEntrySec OBJECT-TYPE
SYNTAX      DisplayString
MAX-ACCESS  read-only
STATUS      current
DESCRIPTION
"Secondary Ringer"
 ::= { cps6000RchEntry  7 }

cps6000RchEntryRf OBJECT-TYPE
SYNTAX      INTEGER {
inactive(0),
active(1)
}
MAX-ACCESS  read-only
STATUS      current
DESCRIPTION
"Ringer Minor Fail
Values:
inactive(0),
active(1)
"
 ::= { cps6000RchEntry  8 }

cps6000RchEntryRpff OBJECT-TYPE
SYNTAX      INTEGER {
inactive(0),
active(1)
}
MAX-ACCESS  read-only
STATUS      current
DESCRIPTION
"Ringer Fan Fail
Values:
inactive(0),
active(1)
"
 ::= { cps6000RchEntry  9 }

cps6000RchEntryRpxj OBJECT-TYPE
SYNTAX      INTEGER {
inactive(0),
active(1)
}
MAX-ACCESS  read-only
STATUS      current
DESCRIPTION
"Ringer Major External Fault
Values:
inactive(0),
active(1)
"
 ::= { cps6000RchEntry  10 }

cps6000RchEntryRpxn OBJECT-TYPE
SYNTAX      INTEGER {
inactive(0),
active(1)
}
MAX-ACCESS  read-only
STATUS      current
DESCRIPTION
"Ringer Minor External Fault
Values:
inactive(0),
active(1)
"
 ::= { cps6000RchEntry  11 }

cps6000RchEntryRprl OBJECT-TYPE
SYNTAX      INTEGER {
inactive(0),
active(1)
}
MAX-ACCESS  read-only
STATUS      current
DESCRIPTION
"Ringer Redundency Loss
Values:
inactive(0),
active(1)
"
 ::= { cps6000RchEntry  12 }

cps6000RchEntryRpfj OBJECT-TYPE
SYNTAX      INTEGER {
inactive(0),
active(1)
}
MAX-ACCESS  read-only
STATUS      current
DESCRIPTION
"Ringer Major Fail
Values:
inactive(0),
active(1)
"
 ::= { cps6000RchEntry  13 }

cps6000RchEntryRcdp OBJECT-TYPE
SYNTAX      INTEGER {
inactive(0),
active(1)
}
MAX-ACCESS  read-only
STATUS      current
DESCRIPTION
"Ringer ID Conflict
Values:
inactive(0),
active(1)
"
 ::= { cps6000RchEntry  14 }



--
-- table ALARM
--

cps6000AlarmTable    OBJECT-TYPE
SYNTAX SEQUENCE OF Cps6000AlarmEntry
MAX-ACCESS not-accessible
STATUS current
DESCRIPTION
        "Table of all Alarm data"
 ::= { cps6000  32 }

cps6000AlarmEntry OBJECT-TYPE
SYNTAX     Cps6000AlarmEntry
MAX-ACCESS  not-accessible
STATUS      current
DESCRIPTION
       "Entry of information for one Alarm"
INDEX { cps6000AlarmEntryIndex }
 ::= { cps6000AlarmTable  1 }

Cps6000AlarmEntry ::= SEQUENCE {
cps6000AlarmEntryIndex   INTEGER,
cps6000AlarmEntryDes   DisplayString,
cps6000AlarmEntryAst   INTEGER,
cps6000AlarmEntrySev   DisplayString,
cps6000AlarmEntryAcc   DisplayString,
cps6000AlarmEntryThr   DisplayString,
cps6000AlarmEntryFth   DisplayString,
cps6000AlarmEntryBth   DisplayString,
cps6000AlarmEntryDly   Integer32,
cps6000AlarmEntryNoo   INTEGER,
cps6000AlarmEntryNor   INTEGER,
cps6000AlarmEntryNag   INTEGER,
cps6000AlarmEntryDst   DisplayString,
cps6000AlarmEntryFds   DisplayString
}

cps6000AlarmEntryIndex OBJECT-TYPE
SYNTAX      INTEGER (0..2147483647)
MAX-ACCESS  read-only
STATUS      current
DESCRIPTION
"Table Index"
 ::= { cps6000AlarmEntry  1 }

cps6000AlarmEntryDes OBJECT-TYPE
SYNTAX      DisplayString
MAX-ACCESS  read-write
STATUS      current
DESCRIPTION
"Description"
 ::= { cps6000AlarmEntry  2 }

cps6000AlarmEntryAst OBJECT-TYPE
SYNTAX      INTEGER {
inactive(0),
active(1)
}
MAX-ACCESS  read-only
STATUS      current
DESCRIPTION
"State
Values:
inactive(0),
active(1)
"
 ::= { cps6000AlarmEntry  3 }

cps6000AlarmEntrySev OBJECT-TYPE
SYNTAX      DisplayString
MAX-ACCESS  read-write
STATUS      current
DESCRIPTION
"Severity"
 ::= { cps6000AlarmEntry  4 }

cps6000AlarmEntryAcc OBJECT-TYPE
SYNTAX      DisplayString
MAX-ACCESS  read-write
STATUS      current
DESCRIPTION
"Contact Closure
Values:
R1,
R2,
R3,
R4
"
 ::= { cps6000AlarmEntry  5 }

cps6000AlarmEntryThr OBJECT-TYPE
SYNTAX      DisplayString
MAX-ACCESS  read-write
STATUS      current
DESCRIPTION
"Threshold"
 ::= { cps6000AlarmEntry  6 }

cps6000AlarmEntryFth OBJECT-TYPE
SYNTAX      DisplayString
MAX-ACCESS  read-write
STATUS      current
DESCRIPTION
"Float Threshold"
 ::= { cps6000AlarmEntry  7 }

cps6000AlarmEntryBth OBJECT-TYPE
SYNTAX      DisplayString
MAX-ACCESS  read-write
STATUS      current
DESCRIPTION
"Boost Threshold"
 ::= { cps6000AlarmEntry  8 }

cps6000AlarmEntryDly OBJECT-TYPE
SYNTAX      Integer32(0..540)
MAX-ACCESS  read-write
STATUS      current
DESCRIPTION
"Notify Delay"
 ::= { cps6000AlarmEntry  9 }

cps6000AlarmEntryNoo OBJECT-TYPE
SYNTAX      INTEGER {
no(0),
yes(1)
}
MAX-ACCESS  read-write
STATUS      current
DESCRIPTION
"Notify On Occur
Values:
no(0),
yes(1)
"
 ::= { cps6000AlarmEntry  10 }

cps6000AlarmEntryNor OBJECT-TYPE
SYNTAX      INTEGER {
no(0),
yes(1)
}
MAX-ACCESS  read-write
STATUS      current
DESCRIPTION
"Notify On Retire
Values:
no(0),
yes(1)
"
 ::= { cps6000AlarmEntry  11 }

cps6000AlarmEntryNag OBJECT-TYPE
SYNTAX      INTEGER {
no(0),
yes(1)
}
MAX-ACCESS  read-write
STATUS      current
DESCRIPTION
"Nag on Occur
Values:
no(0),
yes(1)
"
 ::= { cps6000AlarmEntry  12 }

cps6000AlarmEntryDst OBJECT-TYPE
SYNTAX      DisplayString
MAX-ACCESS  read-write
STATUS      current
DESCRIPTION
"Notify Destination"
 ::= { cps6000AlarmEntry  13 }

cps6000AlarmEntryFds OBJECT-TYPE
SYNTAX      DisplayString
MAX-ACCESS  read-write
STATUS      current
DESCRIPTION
"Front Panel Description"
 ::= { cps6000AlarmEntry  14 }



--
-- object cps6000Trap
--

cps6000Trap OBJECT IDENTIFIER  ::= { cps6000  33 }

cps6000TrapDc1Amj   NOTIFICATION-TYPE
OBJECTS     { trapInfo }
STATUS      current
DESCRIPTION
        "Auxiliary Fuse Major"
 ::= { cps6000Trap  1 }

cps6000TrapDc1Epo   NOTIFICATION-TYPE
OBJECTS     { trapInfo }
STATUS      current
DESCRIPTION
        "Emergency Power Off"
 ::= { cps6000Trap  2 }

cps6000TrapDc1Faj   NOTIFICATION-TYPE
OBJECTS     { trapInfo }
STATUS      current
DESCRIPTION
        "External Fuse Major"
 ::= { cps6000Trap  3 }

cps6000TrapDc1Fan   NOTIFICATION-TYPE
OBJECTS     { trapInfo }
STATUS      current
DESCRIPTION
        "External Fuse Minor"
 ::= { cps6000Trap  4 }

cps6000TrapDc1Vsf   NOTIFICATION-TYPE
OBJECTS     { trapInfo }
STATUS      current
DESCRIPTION
        "Sense/Control Fuse"
 ::= { cps6000Trap  5 }

cps6000TrapDc1Osa   NOTIFICATION-TYPE
OBJECTS     { trapInfo }
STATUS      current
DESCRIPTION
        "Open String"
 ::= { cps6000Trap  6 }

cps6000TrapDc1Zid   NOTIFICATION-TYPE
OBJECTS     { trapInfo }
STATUS      current
DESCRIPTION
        "ID Not Configured"
 ::= { cps6000Trap  7 }

cps6000TrapDc1Tpa   NOTIFICATION-TYPE
OBJECTS     { trapInfo }
STATUS      current
DESCRIPTION
        "Thermal Probe Alarm"
 ::= { cps6000Trap  8 }

cps6000TrapDc1Vmf   NOTIFICATION-TYPE
OBJECTS     { trapInfo }
STATUS      current
DESCRIPTION
        "Voltage Module Fail"
 ::= { cps6000Trap  9 }

cps6000TrapDc1Cma   NOTIFICATION-TYPE
OBJECTS     { trapInfo }
STATUS      current
DESCRIPTION
        "Minor Communication Failure"
 ::= { cps6000Trap  10 }

cps6000TrapDc1Macf   NOTIFICATION-TYPE
OBJECTS     { trapInfo }
STATUS      current
DESCRIPTION
        "Multiple AC Failure"
 ::= { cps6000Trap  11 }

cps6000TrapDc1Mcm   NOTIFICATION-TYPE
OBJECTS     { trapInfo }
STATUS      current
DESCRIPTION
        "Major Communication Failure"
 ::= { cps6000Trap  12 }

cps6000TrapDc1Rfa   NOTIFICATION-TYPE
OBJECTS     { trapInfo }
STATUS      current
DESCRIPTION
        "Rectifier Fail"
 ::= { cps6000Trap  13 }

cps6000TrapDc1Did   NOTIFICATION-TYPE
OBJECTS     { trapInfo }
STATUS      current
DESCRIPTION
        "ID Conflict"
 ::= { cps6000Trap  14 }

cps6000TrapDc1Clm   NOTIFICATION-TYPE
OBJECTS     { trapInfo }
STATUS      current
DESCRIPTION
        "Rectifier Current Limit"
 ::= { cps6000Trap  15 }

cps6000TrapDc1Vla   NOTIFICATION-TYPE
OBJECTS     { trapInfo }
STATUS      current
DESCRIPTION
        "Very Low Voltage"
 ::= { cps6000Trap  16 }

cps6000TrapDc1Acf   NOTIFICATION-TYPE
OBJECTS     { trapInfo }
STATUS      current
DESCRIPTION
        "AC Fail"
 ::= { cps6000Trap  17 }

cps6000TrapDc1Man   NOTIFICATION-TYPE
OBJECTS     { trapInfo }
STATUS      current
DESCRIPTION
        "Manual Off"
 ::= { cps6000Trap  18 }

cps6000TrapDc1Mman   NOTIFICATION-TYPE
OBJECTS     { trapInfo }
STATUS      current
DESCRIPTION
        "Multiple Manual Off"
 ::= { cps6000Trap  19 }

cps6000TrapDc1Mfa   NOTIFICATION-TYPE
OBJECTS     { trapInfo }
STATUS      current
DESCRIPTION
        "Multiple Rectifier Fail"
 ::= { cps6000Trap  20 }

cps6000TrapDc1Rtl   NOTIFICATION-TYPE
OBJECTS     { trapInfo }
STATUS      current
DESCRIPTION
        "Reserve Time Low"
 ::= { cps6000Trap  21 }

cps6000TrapDc1Rrtl   NOTIFICATION-TYPE
OBJECTS     { trapInfo }
STATUS      current
DESCRIPTION
        "Real-time Reserve Time Low"
 ::= { cps6000Trap  22 }

cps6000TrapDc1Rls   NOTIFICATION-TYPE
OBJECTS     { trapInfo }
STATUS      current
DESCRIPTION
        "Redundancy Loss"
 ::= { cps6000Trap  23 }

cps6000TrapDc1Bda   NOTIFICATION-TYPE
OBJECTS     { trapInfo }
STATUS      current
DESCRIPTION
        "Battery On Discharge"
 ::= { cps6000Trap  24 }

cps6000TrapDc1Hva   NOTIFICATION-TYPE
OBJECTS     { trapInfo }
STATUS      current
DESCRIPTION
        "High Voltage"
 ::= { cps6000Trap  25 }

cps6000TrapDc1Hfv   NOTIFICATION-TYPE
OBJECTS     { trapInfo }
STATUS      current
DESCRIPTION
        "High Float Voltage"
 ::= { cps6000Trap  26 }

cps6000TrapPs1Amth   NOTIFICATION-TYPE
OBJECTS     { trapInfo }
STATUS      current
DESCRIPTION
        "High Ambient Temperature"
 ::= { cps6000Trap  27 }

cps6000TrapPs1Amtl   NOTIFICATION-TYPE
OBJECTS     { trapInfo }
STATUS      current
DESCRIPTION
        "Low Ambient Temperature"
 ::= { cps6000Trap  28 }

cps6000TrapPs1Bbl   NOTIFICATION-TYPE
OBJECTS     { trapInfo }
STATUS      current
DESCRIPTION
        "Memory Backup Battery Low"
 ::= { cps6000Trap  29 }

cps6000TrapPs1Cch   NOTIFICATION-TYPE
OBJECTS     { trapInfo }
STATUS      current
DESCRIPTION
        "Configuration Changed"
 ::= { cps6000Trap  30 }

cps6000TrapPs1Clc   NOTIFICATION-TYPE
OBJECTS     { trapInfo }
STATUS      current
DESCRIPTION
        "Clock Changed"
 ::= { cps6000Trap  31 }

cps6000TrapPs1Epr   NOTIFICATION-TYPE
OBJECTS     { trapInfo }
STATUS      current
DESCRIPTION
        "External Password Reset"
 ::= { cps6000Trap  32 }

cps6000TrapPs1Exl   NOTIFICATION-TYPE
OBJECTS     { trapInfo }
STATUS      current
DESCRIPTION
        "Excessive Login Attempts"
 ::= { cps6000Trap  33 }

cps6000TrapPs1Hcl   NOTIFICATION-TYPE
OBJECTS     { trapInfo }
STATUS      current
DESCRIPTION
        "History Cleared"
 ::= { cps6000Trap  34 }

cps6000TrapPs1Pfd   NOTIFICATION-TYPE
OBJECTS     { trapInfo }
STATUS      current
DESCRIPTION
        "Passwords At Default"
 ::= { cps6000Trap  35 }

cps6000TrapPs1Pht   NOTIFICATION-TYPE
OBJECTS     { trapInfo }
STATUS      current
DESCRIPTION
        "Processor Halt"
 ::= { cps6000Trap  36 }

cps6000TrapPs1Stf   NOTIFICATION-TYPE
OBJECTS     { trapInfo }
STATUS      current
DESCRIPTION
        "Self Test Failed"
 ::= { cps6000Trap  37 }

cps6000TrapPs1Pgi   NOTIFICATION-TYPE
OBJECTS     { trapInfo }
STATUS      current
DESCRIPTION
        "Program Line Invalid"
 ::= { cps6000Trap  38 }

cps6000TrapPs1Ax1   NOTIFICATION-TYPE
OBJECTS     { trapInfo }
STATUS      current
DESCRIPTION
        "Auxilliary Event 1"
 ::= { cps6000Trap  39 }

cps6000TrapPs1Ax2   NOTIFICATION-TYPE
OBJECTS     { trapInfo }
STATUS      current
DESCRIPTION
        "Auxilliary Event 1"
 ::= { cps6000Trap  40 }

cps6000TrapPs1Ax3   NOTIFICATION-TYPE
OBJECTS     { trapInfo }
STATUS      current
DESCRIPTION
        "Auxilliary Event 1"
 ::= { cps6000Trap  41 }

cps6000TrapPs1Ax4   NOTIFICATION-TYPE
OBJECTS     { trapInfo }
STATUS      current
DESCRIPTION
        "Auxilliary Event 1"
 ::= { cps6000Trap  42 }

cps6000TrapPs1Ax5   NOTIFICATION-TYPE
OBJECTS     { trapInfo }
STATUS      current
DESCRIPTION
        "Auxilliary Event 1"
 ::= { cps6000Trap  43 }

cps6000TrapPs1Ax6   NOTIFICATION-TYPE
OBJECTS     { trapInfo }
STATUS      current
DESCRIPTION
        "Auxilliary Event 1"
 ::= { cps6000Trap  44 }

cps6000TrapAt1Ata   NOTIFICATION-TYPE
OBJECTS     { trapInfo }
STATUS      current
DESCRIPTION
        "Alarm Test Active"
 ::= { cps6000Trap  45 }

cps6000TrapAt1Atb   NOTIFICATION-TYPE
OBJECTS     { trapInfo }
STATUS      current
DESCRIPTION
        "Alarm Test Aborted"
 ::= { cps6000Trap  46 }

cps6000TrapCp1Cfa   NOTIFICATION-TYPE
OBJECTS     { trapInfo }
STATUS      current
DESCRIPTION
        "Converter Fail"
 ::= { cps6000Trap  47 }

cps6000TrapCp1Dfa   NOTIFICATION-TYPE
OBJECTS     { trapInfo }
STATUS      current
DESCRIPTION
        "Distribution Fail"
 ::= { cps6000Trap  48 }

cps6000TrapCp1Did   NOTIFICATION-TYPE
OBJECTS     { trapInfo }
STATUS      current
DESCRIPTION
        "ID Conflict"
 ::= { cps6000Trap  49 }

cps6000TrapCp1Mfa   NOTIFICATION-TYPE
OBJECTS     { trapInfo }
STATUS      current
DESCRIPTION
        "Multiple Converter Fail"
 ::= { cps6000Trap  50 }

cps6000TrapBs1Bsa   NOTIFICATION-TYPE
OBJECTS     { trapInfo }
STATUS      current
DESCRIPTION
        "Boost State Alarm"
 ::= { cps6000Trap  51 }

cps6000TrapBr1Bta   NOTIFICATION-TYPE
OBJECTS     { trapInfo }
STATUS      current
DESCRIPTION
        "Battery Test Active"
 ::= { cps6000Trap  52 }

cps6000TrapBr1Bfa   NOTIFICATION-TYPE
OBJECTS     { trapInfo }
STATUS      current
DESCRIPTION
        "Battery Test Failed"
 ::= { cps6000Trap  53 }

cps6000TrapBr1Btha   NOTIFICATION-TYPE
OBJECTS     { trapInfo }
STATUS      current
DESCRIPTION
        "High Battery Temperature"
 ::= { cps6000Trap  54 }

cps6000TrapBr1Isda   NOTIFICATION-TYPE
OBJECTS     { trapInfo }
STATUS      current
DESCRIPTION
        "Imminent Shutdown"
 ::= { cps6000Trap  55 }

cps6000TrapCn1Cno   NOTIFICATION-TYPE
OBJECTS     { trapInfo }
STATUS      current
DESCRIPTION
        "Contactor Open"
 ::= { cps6000Trap  56 }

cps6000TrapCn1Cnf   NOTIFICATION-TYPE
OBJECTS     { trapInfo }
STATUS      current
DESCRIPTION
        "Contactor Failed"
 ::= { cps6000Trap  57 }

cps6000TrapCn2Cno   NOTIFICATION-TYPE
OBJECTS     { trapInfo }
STATUS      current
DESCRIPTION
        "Contactor Open"
 ::= { cps6000Trap  58 }

cps6000TrapCn2Cnf   NOTIFICATION-TYPE
OBJECTS     { trapInfo }
STATUS      current
DESCRIPTION
        "Contactor Failed"
 ::= { cps6000Trap  59 }

cps6000TrapCn3Cno   NOTIFICATION-TYPE
OBJECTS     { trapInfo }
STATUS      current
DESCRIPTION
        "Contactor Open"
 ::= { cps6000Trap  60 }

cps6000TrapCn3Cnf   NOTIFICATION-TYPE
OBJECTS     { trapInfo }
STATUS      current
DESCRIPTION
        "Contactor Failed"
 ::= { cps6000Trap  61 }

cps6000TrapCn4Cno   NOTIFICATION-TYPE
OBJECTS     { trapInfo }
STATUS      current
DESCRIPTION
        "Contactor Open"
 ::= { cps6000Trap  62 }

cps6000TrapCn4Cnf   NOTIFICATION-TYPE
OBJECTS     { trapInfo }
STATUS      current
DESCRIPTION
        "Contactor Failed"
 ::= { cps6000Trap  63 }

cps6000TrapCm1Cof   NOTIFICATION-TYPE
OBJECTS     { trapInfo }
STATUS      current
DESCRIPTION
        "Queue Overflow"
 ::= { cps6000Trap  64 }

cps6000TrapCm1Cor   NOTIFICATION-TYPE
OBJECTS     { trapInfo }
STATUS      current
DESCRIPTION
        "Number Did Not Respond"
 ::= { cps6000Trap  65 }

cps6000TrapCm1Nnc   NOTIFICATION-TYPE
OBJECTS     { trapInfo }
STATUS      current
DESCRIPTION
        "Number Not Configured"
 ::= { cps6000Trap  66 }

cps6000TrapPo1Por   NOTIFICATION-TYPE
OBJECTS     { trapInfo }
STATUS      current
DESCRIPTION
        "Number Did Not Respond"
 ::= { cps6000Trap  67 }

cps6000TrapRp1Rf   NOTIFICATION-TYPE
OBJECTS     { trapInfo }
STATUS      current
DESCRIPTION
        "Ringer Minor Fail"
 ::= { cps6000Trap  68 }

cps6000TrapRp1Rpff   NOTIFICATION-TYPE
OBJECTS     { trapInfo }
STATUS      current
DESCRIPTION
        "Ringer Fan Fail"
 ::= { cps6000Trap  69 }

cps6000TrapRp1Rpxj   NOTIFICATION-TYPE
OBJECTS     { trapInfo }
STATUS      current
DESCRIPTION
        "Ringer Major External Fault"
 ::= { cps6000Trap  70 }

cps6000TrapRp1Rpxn   NOTIFICATION-TYPE
OBJECTS     { trapInfo }
STATUS      current
DESCRIPTION
        "Ringer Minor External Fault"
 ::= { cps6000Trap  71 }

cps6000TrapRp1Rprl   NOTIFICATION-TYPE
OBJECTS     { trapInfo }
STATUS      current
DESCRIPTION
        "Ringer Redundency Loss"
 ::= { cps6000Trap  72 }

cps6000TrapRp1Rpfj   NOTIFICATION-TYPE
OBJECTS     { trapInfo }
STATUS      current
DESCRIPTION
        "Ringer Major Fail"
 ::= { cps6000Trap  73 }

cps6000TrapUserDefined   NOTIFICATION-TYPE
OBJECTS     { trapInfo }
STATUS      current
DESCRIPTION
        "This may be a user defined event, or a new controller event."
 ::= { cps6000Trap  74 }

cps6000TrapDc1Icr   NOTIFICATION-TYPE
OBJECTS     { trapInfo }
STATUS      current
DESCRIPTION
        "Incompatible Rectifier"
 ::= { cps6000Trap  75 }

cps6000TrapDc1Rfn   NOTIFICATION-TYPE
OBJECTS     { trapInfo }
STATUS      current
DESCRIPTION
        "Rectifier Fan Fail"
 ::= { cps6000Trap  76 }

cps6000TrapDc1Emd   NOTIFICATION-TYPE
OBJECTS     { trapInfo }
STATUS      current
DESCRIPTION
        "Energy Management Disabled"
 ::= { cps6000Trap  77 }

cps6000TrapCp1Cfn   NOTIFICATION-TYPE
OBJECTS     { trapInfo }
STATUS      current
DESCRIPTION
        "Converter Fan Minor"
 ::= { cps6000Trap  78 }

cps6000TrapCp1Cfj   NOTIFICATION-TYPE
OBJECTS     { trapInfo }
STATUS      current
DESCRIPTION
        "Converter Fan Major"
 ::= { cps6000Trap  79 }

cps6000TrapCp1Icc   NOTIFICATION-TYPE
OBJECTS     { trapInfo }
STATUS      current
DESCRIPTION
        "Incompatible Converter Alarm"
 ::= { cps6000Trap  80 }

cps6000TrapCp1Hva   NOTIFICATION-TYPE
OBJECTS     { trapInfo }
STATUS      current
DESCRIPTION
        "Converter High Voltage Major"
 ::= { cps6000Trap  81 }

cps6000TrapCp1Hfv   NOTIFICATION-TYPE
OBJECTS     { trapInfo }
STATUS      current
DESCRIPTION
        "Converter High Voltage Minor"
 ::= { cps6000Trap  82 }

cps6000TrapCp1Vla   NOTIFICATION-TYPE
OBJECTS     { trapInfo }
STATUS      current
DESCRIPTION
        "Converter Very Low Voltage"
 ::= { cps6000Trap  83 }

cps6000TrapCp1Rl   NOTIFICATION-TYPE
OBJECTS     { trapInfo }
STATUS      current
DESCRIPTION
        "Converter Redundancy Loss"
 ::= { cps6000Trap  84 }

cps6000TrapBr1Mdp   NOTIFICATION-TYPE
OBJECTS     { trapInfo }
STATUS      current
DESCRIPTION
        "Voltage Duplicate ID"
 ::= { cps6000Trap  85 }

cps6000TrapBr1Mzd   NOTIFICATION-TYPE
OBJECTS     { trapInfo }
STATUS      current
DESCRIPTION
        "Voltage ID Not Configured"
 ::= { cps6000Trap  86 }

cps6000TrapBr1Scda   NOTIFICATION-TYPE
OBJECTS     { trapInfo }
STATUS      current
DESCRIPTION
        "Shorted Cell Detected"
 ::= { cps6000Trap  87 }

cps6000TrapRp1Rcdp   NOTIFICATION-TYPE
OBJECTS     { trapInfo }
STATUS      current
DESCRIPTION
        "Ringer ID Conflict"
 ::= { cps6000Trap  88 }

cps6000TrapFt1Fmi   NOTIFICATION-TYPE
OBJECTS     { trapInfo }
STATUS      current
DESCRIPTION
        "Fan Fail Minor"
 ::= { cps6000Trap  89 }

cps6000TrapFt1Fmj   NOTIFICATION-TYPE
OBJECTS     { trapInfo }
STATUS      current
DESCRIPTION
        "Fan Fail Major"
 ::= { cps6000Trap  90 }

cps6000TrapFt1Ipi   NOTIFICATION-TYPE
OBJECTS     { trapInfo }
STATUS      current
DESCRIPTION
        "Input Power Minor"
 ::= { cps6000Trap  91 }

cps6000TrapFt1Ipj   NOTIFICATION-TYPE
OBJECTS     { trapInfo }
STATUS      current
DESCRIPTION
        "Input Power Major"
 ::= { cps6000Trap  92 }

cps6000TrapFt1Cbt   NOTIFICATION-TYPE
OBJECTS     { trapInfo }
STATUS      current
DESCRIPTION
        "Circuit Breaker Trip"
 ::= { cps6000Trap  93 }

cps6000TrapFt1Ctf   NOTIFICATION-TYPE
OBJECTS     { trapInfo }
STATUS      current
DESCRIPTION
        "Circuit Fail"
 ::= { cps6000Trap  94 }

cps6000TrapFt1Mctf   NOTIFICATION-TYPE
OBJECTS     { trapInfo }
STATUS      current
DESCRIPTION
        "Multiple Circuit Fail"
 ::= { cps6000Trap  95 }

cps6000TrapFt1Lor   NOTIFICATION-TYPE
OBJECTS     { trapInfo }
STATUS      current
DESCRIPTION
        "Loss of Redundancy"
 ::= { cps6000Trap  96 }

cps6000TrapFt1Lda   NOTIFICATION-TYPE
OBJECTS     { trapInfo }
STATUS      current
DESCRIPTION
        "Load Drop Alarm"
 ::= { cps6000Trap  97 }

cps6000TrapFt1Lsa   NOTIFICATION-TYPE
OBJECTS     { trapInfo }
STATUS      current
DESCRIPTION
        "Load Share Alarm"
 ::= { cps6000Trap  98 }

cps6000TrapFt1Lta   NOTIFICATION-TYPE
OBJECTS     { trapInfo }
STATUS      current
DESCRIPTION
        "Line Test Failed Alarm"
 ::= { cps6000Trap  99 }

cps6000TrapDc1Lsf   NOTIFICATION-TYPE
OBJECTS     { trapInfo }
STATUS      current
DESCRIPTION
        "Loadshare Fail"
 ::= { cps6000Trap  100 }


trapInfo OBJECT-TYPE
SYNTAX      DisplayString
MAX-ACCESS  accessible-for-notify
STATUS      current
DESCRIPTION
        "Supplemental alarm information"
 ::= { cps6000  34 }
--
-- object cps6000Retire
--

cps6000Retire OBJECT IDENTIFIER  ::= { cps6000  35 }

cps6000RetireDc1Amj   NOTIFICATION-TYPE
OBJECTS     { trapInfo }
STATUS      current
DESCRIPTION
        "Auxiliary Fuse Major"
 ::= { cps6000Retire  1 }

cps6000RetireDc1Epo   NOTIFICATION-TYPE
OBJECTS     { trapInfo }
STATUS      current
DESCRIPTION
        "Emergency Power Off"
 ::= { cps6000Retire  2 }

cps6000RetireDc1Faj   NOTIFICATION-TYPE
OBJECTS     { trapInfo }
STATUS      current
DESCRIPTION
        "External Fuse Major"
 ::= { cps6000Retire  3 }

cps6000RetireDc1Fan   NOTIFICATION-TYPE
OBJECTS     { trapInfo }
STATUS      current
DESCRIPTION
        "External Fuse Minor"
 ::= { cps6000Retire  4 }

cps6000RetireDc1Vsf   NOTIFICATION-TYPE
OBJECTS     { trapInfo }
STATUS      current
DESCRIPTION
        "Sense/Control Fuse"
 ::= { cps6000Retire  5 }

cps6000RetireDc1Osa   NOTIFICATION-TYPE
OBJECTS     { trapInfo }
STATUS      current
DESCRIPTION
        "Open String"
 ::= { cps6000Retire  6 }

cps6000RetireDc1Zid   NOTIFICATION-TYPE
OBJECTS     { trapInfo }
STATUS      current
DESCRIPTION
        "ID Not Configured"
 ::= { cps6000Retire  7 }

cps6000RetireDc1Tpa   NOTIFICATION-TYPE
OBJECTS     { trapInfo }
STATUS      current
DESCRIPTION
        "Thermal Probe Alarm"
 ::= { cps6000Retire  8 }

cps6000RetireDc1Vmf   NOTIFICATION-TYPE
OBJECTS     { trapInfo }
STATUS      current
DESCRIPTION
        "Voltage Module Fail"
 ::= { cps6000Retire  9 }

cps6000RetireDc1Cma   NOTIFICATION-TYPE
OBJECTS     { trapInfo }
STATUS      current
DESCRIPTION
        "Minor Communication Failure"
 ::= { cps6000Retire  10 }

cps6000RetireDc1Macf   NOTIFICATION-TYPE
OBJECTS     { trapInfo }
STATUS      current
DESCRIPTION
        "Multiple AC Failure"
 ::= { cps6000Retire  11 }

cps6000RetireDc1Mcm   NOTIFICATION-TYPE
OBJECTS     { trapInfo }
STATUS      current
DESCRIPTION
        "Major Communication Failure"
 ::= { cps6000Retire  12 }

cps6000RetireDc1Rfa   NOTIFICATION-TYPE
OBJECTS     { trapInfo }
STATUS      current
DESCRIPTION
        "Rectifier Fail"
 ::= { cps6000Retire  13 }

cps6000RetireDc1Did   NOTIFICATION-TYPE
OBJECTS     { trapInfo }
STATUS      current
DESCRIPTION
        "ID Conflict"
 ::= { cps6000Retire  14 }

cps6000RetireDc1Clm   NOTIFICATION-TYPE
OBJECTS     { trapInfo }
STATUS      current
DESCRIPTION
        "Rectifier Current Limit"
 ::= { cps6000Retire  15 }

cps6000RetireDc1Vla   NOTIFICATION-TYPE
OBJECTS     { trapInfo }
STATUS      current
DESCRIPTION
        "Very Low Voltage"
 ::= { cps6000Retire  16 }

cps6000RetireDc1Acf   NOTIFICATION-TYPE
OBJECTS     { trapInfo }
STATUS      current
DESCRIPTION
        "AC Fail"
 ::= { cps6000Retire  17 }

cps6000RetireDc1Man   NOTIFICATION-TYPE
OBJECTS     { trapInfo }
STATUS      current
DESCRIPTION
        "Manual Off"
 ::= { cps6000Retire  18 }

cps6000RetireDc1Mman   NOTIFICATION-TYPE
OBJECTS     { trapInfo }
STATUS      current
DESCRIPTION
        "Multiple Manual Off"
 ::= { cps6000Retire  19 }

cps6000RetireDc1Mfa   NOTIFICATION-TYPE
OBJECTS     { trapInfo }
STATUS      current
DESCRIPTION
        "Multiple Rectifier Fail"
 ::= { cps6000Retire  20 }

cps6000RetireDc1Rtl   NOTIFICATION-TYPE
OBJECTS     { trapInfo }
STATUS      current
DESCRIPTION
        "Reserve Time Low"
 ::= { cps6000Retire  21 }

cps6000RetireDc1Rrtl   NOTIFICATION-TYPE
OBJECTS     { trapInfo }
STATUS      current
DESCRIPTION
        "Real-time Reserve Time Low"
 ::= { cps6000Retire  22 }

cps6000RetireDc1Rls   NOTIFICATION-TYPE
OBJECTS     { trapInfo }
STATUS      current
DESCRIPTION
        "Redundancy Loss"
 ::= { cps6000Retire  23 }

cps6000RetireDc1Bda   NOTIFICATION-TYPE
OBJECTS     { trapInfo }
STATUS      current
DESCRIPTION
        "Battery On Discharge"
 ::= { cps6000Retire  24 }

cps6000RetireDc1Hva   NOTIFICATION-TYPE
OBJECTS     { trapInfo }
STATUS      current
DESCRIPTION
        "High Voltage"
 ::= { cps6000Retire  25 }

cps6000RetireDc1Hfv   NOTIFICATION-TYPE
OBJECTS     { trapInfo }
STATUS      current
DESCRIPTION
        "High Float Voltage"
 ::= { cps6000Retire  26 }

cps6000RetirePs1Amth   NOTIFICATION-TYPE
OBJECTS     { trapInfo }
STATUS      current
DESCRIPTION
        "High Ambient Temperature"
 ::= { cps6000Retire  27 }

cps6000RetirePs1Amtl   NOTIFICATION-TYPE
OBJECTS     { trapInfo }
STATUS      current
DESCRIPTION
        "Low Ambient Temperature"
 ::= { cps6000Retire  28 }

cps6000RetirePs1Bbl   NOTIFICATION-TYPE
OBJECTS     { trapInfo }
STATUS      current
DESCRIPTION
        "Memory Backup Battery Low"
 ::= { cps6000Retire  29 }

cps6000RetirePs1Cch   NOTIFICATION-TYPE
OBJECTS     { trapInfo }
STATUS      current
DESCRIPTION
        "Configuration Changed"
 ::= { cps6000Retire  30 }

cps6000RetirePs1Clc   NOTIFICATION-TYPE
OBJECTS     { trapInfo }
STATUS      current
DESCRIPTION
        "Clock Changed"
 ::= { cps6000Retire  31 }

cps6000RetirePs1Epr   NOTIFICATION-TYPE
OBJECTS     { trapInfo }
STATUS      current
DESCRIPTION
        "External Password Reset"
 ::= { cps6000Retire  32 }

cps6000RetirePs1Exl   NOTIFICATION-TYPE
OBJECTS     { trapInfo }
STATUS      current
DESCRIPTION
        "Excessive Login Attempts"
 ::= { cps6000Retire  33 }

cps6000RetirePs1Hcl   NOTIFICATION-TYPE
OBJECTS     { trapInfo }
STATUS      current
DESCRIPTION
        "History Cleared"
 ::= { cps6000Retire  34 }

cps6000RetirePs1Pfd   NOTIFICATION-TYPE
OBJECTS     { trapInfo }
STATUS      current
DESCRIPTION
        "Passwords At Default"
 ::= { cps6000Retire  35 }

cps6000RetirePs1Pht   NOTIFICATION-TYPE
OBJECTS     { trapInfo }
STATUS      current
DESCRIPTION
        "Processor Halt"
 ::= { cps6000Retire  36 }

cps6000RetirePs1Stf   NOTIFICATION-TYPE
OBJECTS     { trapInfo }
STATUS      current
DESCRIPTION
        "Self Test Failed"
 ::= { cps6000Retire  37 }

cps6000RetirePs1Pgi   NOTIFICATION-TYPE
OBJECTS     { trapInfo }
STATUS      current
DESCRIPTION
        "Program Line Invalid"
 ::= { cps6000Retire  38 }

cps6000RetirePs1Ax1   NOTIFICATION-TYPE
OBJECTS     { trapInfo }
STATUS      current
DESCRIPTION
        "Auxilliary Event 1"
 ::= { cps6000Retire  39 }

cps6000RetirePs1Ax2   NOTIFICATION-TYPE
OBJECTS     { trapInfo }
STATUS      current
DESCRIPTION
        "Auxilliary Event 1"
 ::= { cps6000Retire  40 }

cps6000RetirePs1Ax3   NOTIFICATION-TYPE
OBJECTS     { trapInfo }
STATUS      current
DESCRIPTION
        "Auxilliary Event 1"
 ::= { cps6000Retire  41 }

cps6000RetirePs1Ax4   NOTIFICATION-TYPE
OBJECTS     { trapInfo }
STATUS      current
DESCRIPTION
        "Auxilliary Event 1"
 ::= { cps6000Retire  42 }

cps6000RetirePs1Ax5   NOTIFICATION-TYPE
OBJECTS     { trapInfo }
STATUS      current
DESCRIPTION
        "Auxilliary Event 1"
 ::= { cps6000Retire  43 }

cps6000RetirePs1Ax6   NOTIFICATION-TYPE
OBJECTS     { trapInfo }
STATUS      current
DESCRIPTION
        "Auxilliary Event 1"
 ::= { cps6000Retire  44 }

cps6000RetireAt1Ata   NOTIFICATION-TYPE
OBJECTS     { trapInfo }
STATUS      current
DESCRIPTION
        "Alarm Test Active"
 ::= { cps6000Retire  45 }

cps6000RetireAt1Atb   NOTIFICATION-TYPE
OBJECTS     { trapInfo }
STATUS      current
DESCRIPTION
        "Alarm Test Aborted"
 ::= { cps6000Retire  46 }

cps6000RetireCp1Cfa   NOTIFICATION-TYPE
OBJECTS     { trapInfo }
STATUS      current
DESCRIPTION
        "Converter Fail"
 ::= { cps6000Retire  47 }

cps6000RetireCp1Dfa   NOTIFICATION-TYPE
OBJECTS     { trapInfo }
STATUS      current
DESCRIPTION
        "Distribution Fail"
 ::= { cps6000Retire  48 }

cps6000RetireCp1Did   NOTIFICATION-TYPE
OBJECTS     { trapInfo }
STATUS      current
DESCRIPTION
        "ID Conflict"
 ::= { cps6000Retire  49 }

cps6000RetireCp1Mfa   NOTIFICATION-TYPE
OBJECTS     { trapInfo }
STATUS      current
DESCRIPTION
        "Multiple Converter Fail"
 ::= { cps6000Retire  50 }

cps6000RetireBs1Bsa   NOTIFICATION-TYPE
OBJECTS     { trapInfo }
STATUS      current
DESCRIPTION
        "Boost State Alarm"
 ::= { cps6000Retire  51 }

cps6000RetireBr1Bta   NOTIFICATION-TYPE
OBJECTS     { trapInfo }
STATUS      current
DESCRIPTION
        "Battery Test Active"
 ::= { cps6000Retire  52 }

cps6000RetireBr1Bfa   NOTIFICATION-TYPE
OBJECTS     { trapInfo }
STATUS      current
DESCRIPTION
        "Battery Test Failed"
 ::= { cps6000Retire  53 }

cps6000RetireBr1Btha   NOTIFICATION-TYPE
OBJECTS     { trapInfo }
STATUS      current
DESCRIPTION
        "High Battery Temperature"
 ::= { cps6000Retire  54 }

cps6000RetireBr1Isda   NOTIFICATION-TYPE
OBJECTS     { trapInfo }
STATUS      current
DESCRIPTION
        "Imminent Shutdown"
 ::= { cps6000Retire  55 }

cps6000RetireCn1Cno   NOTIFICATION-TYPE
OBJECTS     { trapInfo }
STATUS      current
DESCRIPTION
        "Contactor Open"
 ::= { cps6000Retire  56 }

cps6000RetireCn1Cnf   NOTIFICATION-TYPE
OBJECTS     { trapInfo }
STATUS      current
DESCRIPTION
        "Contactor Failed"
 ::= { cps6000Retire  57 }

cps6000RetireCn2Cno   NOTIFICATION-TYPE
OBJECTS     { trapInfo }
STATUS      current
DESCRIPTION
        "Contactor Open"
 ::= { cps6000Retire  58 }

cps6000RetireCn2Cnf   NOTIFICATION-TYPE
OBJECTS     { trapInfo }
STATUS      current
DESCRIPTION
        "Contactor Failed"
 ::= { cps6000Retire  59 }

cps6000RetireCn3Cno   NOTIFICATION-TYPE
OBJECTS     { trapInfo }
STATUS      current
DESCRIPTION
        "Contactor Open"
 ::= { cps6000Retire  60 }

cps6000RetireCn3Cnf   NOTIFICATION-TYPE
OBJECTS     { trapInfo }
STATUS      current
DESCRIPTION
        "Contactor Failed"
 ::= { cps6000Retire  61 }

cps6000RetireCn4Cno   NOTIFICATION-TYPE
OBJECTS     { trapInfo }
STATUS      current
DESCRIPTION
        "Contactor Open"
 ::= { cps6000Retire  62 }

cps6000RetireCn4Cnf   NOTIFICATION-TYPE
OBJECTS     { trapInfo }
STATUS      current
DESCRIPTION
        "Contactor Failed"
 ::= { cps6000Retire  63 }

cps6000RetireCm1Cof   NOTIFICATION-TYPE
OBJECTS     { trapInfo }
STATUS      current
DESCRIPTION
        "Queue Overflow"
 ::= { cps6000Retire  64 }

cps6000RetireCm1Cor   NOTIFICATION-TYPE
OBJECTS     { trapInfo }
STATUS      current
DESCRIPTION
        "Number Did Not Respond"
 ::= { cps6000Retire  65 }

cps6000RetireCm1Nnc   NOTIFICATION-TYPE
OBJECTS     { trapInfo }
STATUS      current
DESCRIPTION
        "Number Not Configured"
 ::= { cps6000Retire  66 }

cps6000RetirePo1Por   NOTIFICATION-TYPE
OBJECTS     { trapInfo }
STATUS      current
DESCRIPTION
        "Number Did Not Respond"
 ::= { cps6000Retire  67 }

cps6000RetireRp1Rf   NOTIFICATION-TYPE
OBJECTS     { trapInfo }
STATUS      current
DESCRIPTION
        "Ringer Minor Fail"
 ::= { cps6000Retire  68 }

cps6000RetireRp1Rpff   NOTIFICATION-TYPE
OBJECTS     { trapInfo }
STATUS      current
DESCRIPTION
        "Ringer Fan Fail"
 ::= { cps6000Retire  69 }

cps6000RetireRp1Rpxj   NOTIFICATION-TYPE
OBJECTS     { trapInfo }
STATUS      current
DESCRIPTION
        "Ringer Major External Fault"
 ::= { cps6000Retire  70 }

cps6000RetireRp1Rpxn   NOTIFICATION-TYPE
OBJECTS     { trapInfo }
STATUS      current
DESCRIPTION
        "Ringer Minor External Fault"
 ::= { cps6000Retire  71 }

cps6000RetireRp1Rprl   NOTIFICATION-TYPE
OBJECTS     { trapInfo }
STATUS      current
DESCRIPTION
        "Ringer Redundency Loss"
 ::= { cps6000Retire  72 }

cps6000RetireRp1Rpfj   NOTIFICATION-TYPE
OBJECTS     { trapInfo }
STATUS      current
DESCRIPTION
        "Ringer Major Fail"
 ::= { cps6000Retire  73 }

cps6000RetireUserDefined   NOTIFICATION-TYPE
OBJECTS     { trapInfo }
STATUS      current
DESCRIPTION
        "This may be a user defined event, or a new controller event."
 ::= { cps6000Retire  74 }

cps6000RetireDc1Icr   NOTIFICATION-TYPE
OBJECTS     { trapInfo }
STATUS      current
DESCRIPTION
        "Incompatible Rectifier"
 ::= { cps6000Retire  75 }

cps6000RetireDc1Rfn   NOTIFICATION-TYPE
OBJECTS     { trapInfo }
STATUS      current
DESCRIPTION
        "Rectifier Fan Fail"
 ::= { cps6000Retire  76 }

cps6000RetireDc1Emd   NOTIFICATION-TYPE
OBJECTS     { trapInfo }
STATUS      current
DESCRIPTION
        "Energy Management Disabled"
 ::= { cps6000Retire  77 }

cps6000RetireCp1Cfn   NOTIFICATION-TYPE
OBJECTS     { trapInfo }
STATUS      current
DESCRIPTION
        "Converter Fan Minor"
 ::= { cps6000Retire  78 }

cps6000RetireCp1Cfj   NOTIFICATION-TYPE
OBJECTS     { trapInfo }
STATUS      current
DESCRIPTION
        "Converter Fan Major"
 ::= { cps6000Retire  79 }

cps6000RetireCp1Icc   NOTIFICATION-TYPE
OBJECTS     { trapInfo }
STATUS      current
DESCRIPTION
        "Incompatible Converter Alarm"
 ::= { cps6000Retire  80 }

cps6000RetireCp1Hva   NOTIFICATION-TYPE
OBJECTS     { trapInfo }
STATUS      current
DESCRIPTION
        "Converter High Voltage Major"
 ::= { cps6000Retire  81 }

cps6000RetireCp1Hfv   NOTIFICATION-TYPE
OBJECTS     { trapInfo }
STATUS      current
DESCRIPTION
        "Converter High Voltage Minor"
 ::= { cps6000Retire  82 }

cps6000RetireCp1Vla   NOTIFICATION-TYPE
OBJECTS     { trapInfo }
STATUS      current
DESCRIPTION
        "Converter Very Low Voltage"
 ::= { cps6000Retire  83 }

cps6000RetireCp1Rl   NOTIFICATION-TYPE
OBJECTS     { trapInfo }
STATUS      current
DESCRIPTION
        "Converter Redundancy Loss"
 ::= { cps6000Retire  84 }

cps6000RetireBr1Mdp   NOTIFICATION-TYPE
OBJECTS     { trapInfo }
STATUS      current
DESCRIPTION
        "Voltage Duplicate ID"
 ::= { cps6000Retire  85 }

cps6000RetireBr1Mzd   NOTIFICATION-TYPE
OBJECTS     { trapInfo }
STATUS      current
DESCRIPTION
        "Voltage ID Not Configured"
 ::= { cps6000Retire  86 }

cps6000RetireBr1Scda   NOTIFICATION-TYPE
OBJECTS     { trapInfo }
STATUS      current
DESCRIPTION
        "Shorted Cell Detected"
 ::= { cps6000Retire  87 }

cps6000RetireRp1Rcdp   NOTIFICATION-TYPE
OBJECTS     { trapInfo }
STATUS      current
DESCRIPTION
        "Ringer ID Conflict"
 ::= { cps6000Retire  88 }

cps6000RetireFt1Fmi   NOTIFICATION-TYPE
OBJECTS     { trapInfo }
STATUS      current
DESCRIPTION
        "Fan Fail Minor"
 ::= { cps6000Retire  89 }

cps6000RetireFt1Fmj   NOTIFICATION-TYPE
OBJECTS     { trapInfo }
STATUS      current
DESCRIPTION
        "Fan Fail Major"
 ::= { cps6000Retire  90 }

cps6000RetireFt1Ipi   NOTIFICATION-TYPE
OBJECTS     { trapInfo }
STATUS      current
DESCRIPTION
        "Input Power Minor"
 ::= { cps6000Retire  91 }

cps6000RetireFt1Ipj   NOTIFICATION-TYPE
OBJECTS     { trapInfo }
STATUS      current
DESCRIPTION
        "Input Power Major"
 ::= { cps6000Retire  92 }

cps6000RetireFt1Cbt   NOTIFICATION-TYPE
OBJECTS     { trapInfo }
STATUS      current
DESCRIPTION
        "Circuit Breaker Trip"
 ::= { cps6000Retire  93 }

cps6000RetireFt1Ctf   NOTIFICATION-TYPE
OBJECTS     { trapInfo }
STATUS      current
DESCRIPTION
        "Circuit Fail"
 ::= { cps6000Retire  94 }

cps6000RetireFt1Mctf   NOTIFICATION-TYPE
OBJECTS     { trapInfo }
STATUS      current
DESCRIPTION
        "Multiple Circuit Fail"
 ::= { cps6000Retire  95 }

cps6000RetireFt1Lor   NOTIFICATION-TYPE
OBJECTS     { trapInfo }
STATUS      current
DESCRIPTION
        "Loss of Redundancy"
 ::= { cps6000Retire  96 }

cps6000RetireFt1Lda   NOTIFICATION-TYPE
OBJECTS     { trapInfo }
STATUS      current
DESCRIPTION
        "Load Drop Alarm"
 ::= { cps6000Retire  97 }

cps6000RetireFt1Lsa   NOTIFICATION-TYPE
OBJECTS     { trapInfo }
STATUS      current
DESCRIPTION
        "Load Share Alarm"
 ::= { cps6000Retire  98 }

cps6000RetireFt1Lta   NOTIFICATION-TYPE
OBJECTS     { trapInfo }
STATUS      current
DESCRIPTION
        "Line Test Failed Alarm"
 ::= { cps6000Retire  99 }

cps6000RetireDc1Lsf   NOTIFICATION-TYPE
OBJECTS     { trapInfo }
STATUS      current
DESCRIPTION
        "Loadshare Fail"
 ::= { cps6000Retire  100 }


--
-- table MSV
--

cps6000MsvTable    OBJECT-TYPE
SYNTAX SEQUENCE OF Cps6000MsvEntry
MAX-ACCESS not-accessible
STATUS current
DESCRIPTION
        "Table of all Midstring Voltage Monitor data"
 ::= { cps6000  36 }

cps6000MsvEntry OBJECT-TYPE
SYNTAX     Cps6000MsvEntry
MAX-ACCESS  not-accessible
STATUS      current
DESCRIPTION
       "Entry of information for one Midstring Voltage Monitor"
INDEX { cps6000MsvEntryIndex }
 ::= { cps6000MsvTable  1 }

Cps6000MsvEntry ::= SEQUENCE {
cps6000MsvEntryIndex   INTEGER,
cps6000MsvEntryIde   DisplayString,
cps6000MsvEntryDes   DisplayString,
cps6000MsvEntryStt   DisplayString,
cps6000MsvEntryVal   DisplayString,
cps6000MsvEntryDid   DisplayString
}

cps6000MsvEntryIndex OBJECT-TYPE
SYNTAX      INTEGER (0..2147483647)
MAX-ACCESS  read-only
STATUS      current
DESCRIPTION
"Table Index"
 ::= { cps6000MsvEntry  1 }

cps6000MsvEntryIde OBJECT-TYPE
SYNTAX      DisplayString
MAX-ACCESS  read-only
STATUS      current
DESCRIPTION
"Identifier"
 ::= { cps6000MsvEntry  2 }

cps6000MsvEntryDes OBJECT-TYPE
SYNTAX      DisplayString
MAX-ACCESS  read-write
STATUS      current
DESCRIPTION
"Description"
 ::= { cps6000MsvEntry  3 }

cps6000MsvEntryStt OBJECT-TYPE
SYNTAX      DisplayString
MAX-ACCESS  read-only
STATUS      current
DESCRIPTION
"State"
 ::= { cps6000MsvEntry  4 }

cps6000MsvEntryVal OBJECT-TYPE
SYNTAX      DisplayString
UNITS       "Volts"
MAX-ACCESS  read-only
STATUS      current
DESCRIPTION
"Value (Volts)"
 ::= { cps6000MsvEntry  5 }

cps6000MsvEntryDid OBJECT-TYPE
SYNTAX      DisplayString
MAX-ACCESS  read-only
STATUS      current
DESCRIPTION
"ID Conflict"
 ::= { cps6000MsvEntry  6 }



--
-- object cps6000Ft1
--

cps6000Ft1 OBJECT IDENTIFIER  ::= { cps6000  37 }

cps6000Ft1Ide OBJECT-TYPE
SYNTAX      DisplayString
MAX-ACCESS  read-only
STATUS      current
DESCRIPTION
"Identifier"
 ::= { cps6000Ft1  1 }

cps6000Ft1Des OBJECT-TYPE
SYNTAX      DisplayString
MAX-ACCESS  read-only
STATUS      current
DESCRIPTION
"Description"
 ::= { cps6000Ft1  2 }

cps6000Ft1Stt OBJECT-TYPE
SYNTAX      DisplayString
MAX-ACCESS  read-only
STATUS      current
DESCRIPTION
"State
Values:
PRESENT,
NONE
"
 ::= { cps6000Ft1  3 }

cps6000Ft1Iadc OBJECT-TYPE
SYNTAX      DisplayString
UNITS       "Amps"
MAX-ACCESS  read-only
STATUS      current
DESCRIPTION
"Input Current (Amps)"
 ::= { cps6000Ft1  4 }

cps6000Ft1Lte OBJECT-TYPE
SYNTAX      INTEGER {
disable(0),
enable(1)
}
MAX-ACCESS  read-only
STATUS      current
DESCRIPTION
"Line Test Enable
Values:
disable(0),
enable(1)
"
 ::= { cps6000Ft1  5 }

cps6000Ft1Ltf OBJECT-TYPE
SYNTAX      DisplayString
UNITS       "Days"
MAX-ACCESS  read-only
STATUS      current
DESCRIPTION
"Line Test Frequency (Days)"
 ::= { cps6000Ft1  6 }

cps6000Ft1Fmi OBJECT-TYPE
SYNTAX      DisplayString
MAX-ACCESS  read-only
STATUS      current
DESCRIPTION
"Fan Fail Minor"
 ::= { cps6000Ft1  7 }

cps6000Ft1Fmj OBJECT-TYPE
SYNTAX      DisplayString
MAX-ACCESS  read-only
STATUS      current
DESCRIPTION
"Fan Fail Major"
 ::= { cps6000Ft1  8 }

cps6000Ft1Ipi OBJECT-TYPE
SYNTAX      DisplayString
MAX-ACCESS  read-only
STATUS      current
DESCRIPTION
"Input Power Minor"
 ::= { cps6000Ft1  9 }

cps6000Ft1Ipj OBJECT-TYPE
SYNTAX      DisplayString
MAX-ACCESS  read-only
STATUS      current
DESCRIPTION
"Input Power Major"
 ::= { cps6000Ft1  10 }

cps6000Ft1Cbt OBJECT-TYPE
SYNTAX      DisplayString
MAX-ACCESS  read-only
STATUS      current
DESCRIPTION
"Circuit Breaker Trip"
 ::= { cps6000Ft1  11 }

cps6000Ft1Ctf OBJECT-TYPE
SYNTAX      DisplayString
MAX-ACCESS  read-only
STATUS      current
DESCRIPTION
"Circuit Fail"
 ::= { cps6000Ft1  12 }

cps6000Ft1Mctf OBJECT-TYPE
SYNTAX      DisplayString
MAX-ACCESS  read-only
STATUS      current
DESCRIPTION
"Multiple Circuit Fail"
 ::= { cps6000Ft1  13 }

cps6000Ft1Lor OBJECT-TYPE
SYNTAX      DisplayString
MAX-ACCESS  read-only
STATUS      current
DESCRIPTION
"Loss of Redundancy"
 ::= { cps6000Ft1  14 }

cps6000Ft1Lda OBJECT-TYPE
SYNTAX      DisplayString
MAX-ACCESS  read-only
STATUS      current
DESCRIPTION
"Load Drop Alarm"
 ::= { cps6000Ft1  15 }

cps6000Ft1Lsa OBJECT-TYPE
SYNTAX      DisplayString
MAX-ACCESS  read-only
STATUS      current
DESCRIPTION
"Load Share Alarm"
 ::= { cps6000Ft1  16 }

cps6000Ft1Lta OBJECT-TYPE
SYNTAX      DisplayString
MAX-ACCESS  read-only
STATUS      current
DESCRIPTION
"Line Test Failed Alarm"
 ::= { cps6000Ft1  17 }

cps6000Ft1Rem OBJECT-TYPE
SYNTAX      INTEGER {
disable(0),
enable(1)
}
MAX-ACCESS  read-write
STATUS      current
DESCRIPTION
"Restart Faulted Circuits
Values:
disable(0),
enable(1)
"
 ::= { cps6000Ft1  18 }

cps6000Ft1Tof OBJECT-TYPE
SYNTAX      INTEGER {
disabled(0),
faulted(1),
faultedAndNoLoad(2)
}
MAX-ACCESS  read-write
STATUS      current
DESCRIPTION
"Turn Off Circuits
Values:
disabled(0),
faulted(1),
faultedAndNoLoad(2)
"
 ::= { cps6000Ft1  19 }


--
-- table GRP
--

cps6000GrpTable    OBJECT-TYPE
SYNTAX SEQUENCE OF Cps6000GrpEntry
MAX-ACCESS not-accessible
STATUS current
DESCRIPTION
        "Table of all Circuit Group data"
 ::= { cps6000  38 }

cps6000GrpEntry OBJECT-TYPE
SYNTAX     Cps6000GrpEntry
MAX-ACCESS  not-accessible
STATUS      current
DESCRIPTION
       "Entry of information for one Circuit Group"
INDEX { cps6000GrpEntryIndex }
 ::= { cps6000GrpTable  1 }

Cps6000GrpEntry ::= SEQUENCE {
cps6000GrpEntryIndex   INTEGER,
cps6000GrpEntryIde   DisplayString,
cps6000GrpEntryDes   DisplayString,
cps6000GrpEntryCct   DisplayString,
cps6000GrpEntryTadc   DisplayString,
cps6000GrpEntryAadc   DisplayString,
cps6000GrpEntryCap   DisplayString,
cps6000GrpEntryLrs   DisplayString,
cps6000GrpEntryOlcap   DisplayString
}

cps6000GrpEntryIndex OBJECT-TYPE
SYNTAX      INTEGER (0..2147483647)
MAX-ACCESS  read-only
STATUS      current
DESCRIPTION
"Table Index"
 ::= { cps6000GrpEntry  1 }

cps6000GrpEntryIde OBJECT-TYPE
SYNTAX      DisplayString
MAX-ACCESS  read-only
STATUS      current
DESCRIPTION
"Identifier"
 ::= { cps6000GrpEntry  2 }

cps6000GrpEntryDes OBJECT-TYPE
SYNTAX      DisplayString
MAX-ACCESS  read-write
STATUS      current
DESCRIPTION
"Description"
 ::= { cps6000GrpEntry  3 }

cps6000GrpEntryCct OBJECT-TYPE
SYNTAX      DisplayString
MAX-ACCESS  read-only
STATUS      current
DESCRIPTION
"Circuits"
 ::= { cps6000GrpEntry  4 }

cps6000GrpEntryTadc OBJECT-TYPE
SYNTAX      DisplayString
UNITS       "mA"
MAX-ACCESS  read-only
STATUS      current
DESCRIPTION
"Total Current (mA)"
 ::= { cps6000GrpEntry  5 }

cps6000GrpEntryAadc OBJECT-TYPE
SYNTAX      DisplayString
UNITS       "mA"
MAX-ACCESS  read-only
STATUS      current
DESCRIPTION
"Average Current (mA)"
 ::= { cps6000GrpEntry  6 }

cps6000GrpEntryCap OBJECT-TYPE
SYNTAX      DisplayString
UNITS       "mA"
MAX-ACCESS  read-only
STATUS      current
DESCRIPTION
"Capacity (mA)"
 ::= { cps6000GrpEntry  7 }

cps6000GrpEntryLrs OBJECT-TYPE
SYNTAX      DisplayString
MAX-ACCESS  read-only
STATUS      current
DESCRIPTION
"Loss of Redundancy Status"
 ::= { cps6000GrpEntry  8 }

cps6000GrpEntryOlcap OBJECT-TYPE
SYNTAX      DisplayString
UNITS       "mA"
MAX-ACCESS  read-only
STATUS      current
DESCRIPTION
"Online Capacity (mA)"
 ::= { cps6000GrpEntry  9 }



--
-- table SHF
--

cps6000ShfTable    OBJECT-TYPE
SYNTAX SEQUENCE OF Cps6000ShfEntry
MAX-ACCESS not-accessible
STATUS current
DESCRIPTION
        "Table of all Converter Shelf data"
 ::= { cps6000  39 }

cps6000ShfEntry OBJECT-TYPE
SYNTAX     Cps6000ShfEntry
MAX-ACCESS  not-accessible
STATUS      current
DESCRIPTION
       "Entry of information for one Converter Shelf"
INDEX { cps6000ShfEntryIndex }
 ::= { cps6000ShfTable  1 }

Cps6000ShfEntry ::= SEQUENCE {
cps6000ShfEntryIndex   INTEGER,
cps6000ShfEntryIde   DisplayString,
cps6000ShfEntryDes   DisplayString,
cps6000ShfEntryStt   DisplayString,
cps6000ShfEntryIadc   DisplayString,
cps6000ShfEntryIa1   INTEGER,
cps6000ShfEntryIa2   INTEGER,
cps6000ShfEntryIb1   INTEGER,
cps6000ShfEntryIb2   INTEGER,
cps6000ShfEntryUfn   INTEGER,
cps6000ShfEntryLfn   INTEGER,
cps6000ShfEntryCba   INTEGER,
cps6000ShfEntryCbb   INTEGER,
cps6000ShfEntryCvj   INTEGER,
cps6000ShfEntryCvi   INTEGER,
cps6000ShfEntryNoc   Integer32
}

cps6000ShfEntryIndex OBJECT-TYPE
SYNTAX      INTEGER (0..2147483647)
MAX-ACCESS  read-only
STATUS      current
DESCRIPTION
"Table Index"
 ::= { cps6000ShfEntry  1 }

cps6000ShfEntryIde OBJECT-TYPE
SYNTAX      DisplayString
MAX-ACCESS  read-only
STATUS      current
DESCRIPTION
"Identifier"
 ::= { cps6000ShfEntry  2 }

cps6000ShfEntryDes OBJECT-TYPE
SYNTAX      DisplayString
MAX-ACCESS  read-only
STATUS      current
DESCRIPTION
"Description"
 ::= { cps6000ShfEntry  3 }

cps6000ShfEntryStt OBJECT-TYPE
SYNTAX      DisplayString
MAX-ACCESS  read-only
STATUS      current
DESCRIPTION
"State
Values:
PRESENT,
MISSING
"
 ::= { cps6000ShfEntry  4 }

cps6000ShfEntryIadc OBJECT-TYPE
SYNTAX      DisplayString
UNITS       "Amps"
MAX-ACCESS  read-only
STATUS      current
DESCRIPTION
"Input Current (Amps)"
 ::= { cps6000ShfEntry  5 }

cps6000ShfEntryIa1 OBJECT-TYPE
SYNTAX      INTEGER {
inactive(0),
active(1)
}
MAX-ACCESS  read-only
STATUS      current
DESCRIPTION
"Input Voltage A1 Fail
Values:
inactive(0),
active(1)
"
 ::= { cps6000ShfEntry  6 }

cps6000ShfEntryIa2 OBJECT-TYPE
SYNTAX      INTEGER {
inactive(0),
active(1)
}
MAX-ACCESS  read-only
STATUS      current
DESCRIPTION
"Input Voltage A2 Fail
Values:
inactive(0),
active(1)
"
 ::= { cps6000ShfEntry  7 }

cps6000ShfEntryIb1 OBJECT-TYPE
SYNTAX      INTEGER {
inactive(0),
active(1)
}
MAX-ACCESS  read-only
STATUS      current
DESCRIPTION
"Input Voltage B1 Fail
Values:
inactive(0),
active(1)
"
 ::= { cps6000ShfEntry  8 }

cps6000ShfEntryIb2 OBJECT-TYPE
SYNTAX      INTEGER {
inactive(0),
active(1)
}
MAX-ACCESS  read-only
STATUS      current
DESCRIPTION
"Input Voltage B2 Fail
Values:
inactive(0),
active(1)
"
 ::= { cps6000ShfEntry  9 }

cps6000ShfEntryUfn OBJECT-TYPE
SYNTAX      INTEGER {
inactive(0),
active(1)
}
MAX-ACCESS  read-only
STATUS      current
DESCRIPTION
"Upper Fan Fail
Values:
inactive(0),
active(1)
"
 ::= { cps6000ShfEntry  10 }

cps6000ShfEntryLfn OBJECT-TYPE
SYNTAX      INTEGER {
inactive(0),
active(1)
}
MAX-ACCESS  read-only
STATUS      current
DESCRIPTION
"Lower Fan Fail
Values:
inactive(0),
active(1)
"
 ::= { cps6000ShfEntry  11 }

cps6000ShfEntryCba OBJECT-TYPE
SYNTAX      INTEGER {
inactive(0),
active(1)
}
MAX-ACCESS  read-only
STATUS      current
DESCRIPTION
"Circuit Breaker A Trip
Values:
inactive(0),
active(1)
"
 ::= { cps6000ShfEntry  12 }

cps6000ShfEntryCbb OBJECT-TYPE
SYNTAX      INTEGER {
inactive(0),
active(1)
}
MAX-ACCESS  read-only
STATUS      current
DESCRIPTION
"Circuit Breaker B Trip
Values:
inactive(0),
active(1)
"
 ::= { cps6000ShfEntry  13 }

cps6000ShfEntryCvj OBJECT-TYPE
SYNTAX      INTEGER {
inactive(0),
active(1)
}
MAX-ACCESS  read-only
STATUS      current
DESCRIPTION
"Converter Major
Values:
inactive(0),
active(1)
"
 ::= { cps6000ShfEntry  14 }

cps6000ShfEntryCvi OBJECT-TYPE
SYNTAX      INTEGER {
inactive(0),
active(1)
}
MAX-ACCESS  read-only
STATUS      current
DESCRIPTION
"Converter Minor
Values:
inactive(0),
active(1)
"
 ::= { cps6000ShfEntry  15 }

cps6000ShfEntryNoc OBJECT-TYPE
SYNTAX      Integer32
MAX-ACCESS  read-only
STATUS      current
DESCRIPTION
"Number of Converters in Shelf"
 ::= { cps6000ShfEntry  16 }



--
-- table CCT
--

cps6000CctTable    OBJECT-TYPE
SYNTAX SEQUENCE OF Cps6000CctEntry
MAX-ACCESS not-accessible
STATUS current
DESCRIPTION
        "Table of all Circuit data"
 ::= { cps6000  40 }

cps6000CctEntry OBJECT-TYPE
SYNTAX     Cps6000CctEntry
MAX-ACCESS  not-accessible
STATUS      current
DESCRIPTION
       "Entry of information for one Circuit"
INDEX { cps6000CctEntryIndex }
 ::= { cps6000CctTable  1 }

Cps6000CctEntry ::= SEQUENCE {
cps6000CctEntryIndex   INTEGER,
cps6000CctEntryIde   DisplayString,
cps6000CctEntryDes   DisplayString,
cps6000CctEntryVdc   DisplayString,
cps6000CctEntryAdc   DisplayString,
cps6000CctEntryStt   DisplayString,
cps6000CctEntryTmp   DisplayString,
cps6000CctEntryCap   DisplayString,
cps6000CctEntryCli   DisplayString,
cps6000CctEntrySnm   DisplayString,
cps6000CctEntryMdl   DisplayString,
cps6000CctEntryCcd   DisplayString,
cps6000CctEntryCfl   INTEGER,
cps6000CctEntryOv   INTEGER,
cps6000CctEntryCl   INTEGER,
cps6000CctEntryGf   INTEGER,
cps6000CctEntryUv   INTEGER,
cps6000CctEntryOt   INTEGER,
cps6000CctEntryLds   INTEGER,
cps6000CctEntryLss   INTEGER,
cps6000CctEntryLts   INTEGER,
cps6000CctEntryIlr   DisplayString,
cps6000CctEntryAlr   DisplayString
}

cps6000CctEntryIndex OBJECT-TYPE
SYNTAX      INTEGER (0..2147483647)
MAX-ACCESS  read-only
STATUS      current
DESCRIPTION
"Table Index"
 ::= { cps6000CctEntry  1 }

cps6000CctEntryIde OBJECT-TYPE
SYNTAX      DisplayString
MAX-ACCESS  read-only
STATUS      current
DESCRIPTION
"Identifier"
 ::= { cps6000CctEntry  2 }

cps6000CctEntryDes OBJECT-TYPE
SYNTAX      DisplayString
MAX-ACCESS  read-write
STATUS      current
DESCRIPTION
"Description"
 ::= { cps6000CctEntry  3 }

cps6000CctEntryVdc OBJECT-TYPE
SYNTAX      DisplayString
UNITS       "Volts"
MAX-ACCESS  read-only
STATUS      current
DESCRIPTION
"Voltage (Volts)"
 ::= { cps6000CctEntry  4 }

cps6000CctEntryAdc OBJECT-TYPE
SYNTAX      DisplayString
UNITS       "mA"
MAX-ACCESS  read-only
STATUS      current
DESCRIPTION
"Current (mA)"
 ::= { cps6000CctEntry  5 }

cps6000CctEntryStt OBJECT-TYPE
SYNTAX      DisplayString
MAX-ACCESS  read-write
STATUS      current
DESCRIPTION
"State
Values:
ON,
STANDBY,
MISSING,
VACANT
"
 ::= { cps6000CctEntry  6 }

cps6000CctEntryTmp OBJECT-TYPE
SYNTAX      DisplayString
UNITS       "C"
MAX-ACCESS  read-only
STATUS      current
DESCRIPTION
"Temperature (C)"
 ::= { cps6000CctEntry  7 }

cps6000CctEntryCap OBJECT-TYPE
SYNTAX      DisplayString
UNITS       "mA"
MAX-ACCESS  read-only
STATUS      current
DESCRIPTION
"Capacity (mA)"
 ::= { cps6000CctEntry  8 }

cps6000CctEntryCli OBJECT-TYPE
SYNTAX      DisplayString
MAX-ACCESS  read-only
STATUS      current
DESCRIPTION
"CLEI Code"
 ::= { cps6000CctEntry  9 }

cps6000CctEntrySnm OBJECT-TYPE
SYNTAX      DisplayString
MAX-ACCESS  read-only
STATUS      current
DESCRIPTION
"Serial Number"
 ::= { cps6000CctEntry  10 }

cps6000CctEntryMdl OBJECT-TYPE
SYNTAX      DisplayString
MAX-ACCESS  read-only
STATUS      current
DESCRIPTION
"Model"
 ::= { cps6000CctEntry  11 }

cps6000CctEntryCcd OBJECT-TYPE
SYNTAX      DisplayString
MAX-ACCESS  read-only
STATUS      current
DESCRIPTION
"Comcode"
 ::= { cps6000CctEntry  12 }

cps6000CctEntryCfl OBJECT-TYPE
SYNTAX      INTEGER {
inactive(0),
active(1)
}
MAX-ACCESS  read-only
STATUS      current
DESCRIPTION
"Fail
Values:
inactive(0),
active(1)
"
 ::= { cps6000CctEntry  13 }

cps6000CctEntryOv OBJECT-TYPE
SYNTAX      INTEGER {
inactive(0),
active(1)
}
MAX-ACCESS  read-only
STATUS      current
DESCRIPTION
"Over Voltage
Values:
inactive(0),
active(1)
"
 ::= { cps6000CctEntry  14 }

cps6000CctEntryCl OBJECT-TYPE
SYNTAX      INTEGER {
inactive(0),
active(1)
}
MAX-ACCESS  read-only
STATUS      current
DESCRIPTION
"Current Limit
Values:
inactive(0),
active(1)
"
 ::= { cps6000CctEntry  15 }

cps6000CctEntryGf OBJECT-TYPE
SYNTAX      INTEGER {
inactive(0),
active(1)
}
MAX-ACCESS  read-only
STATUS      current
DESCRIPTION
"Ground Fault
Values:
inactive(0),
active(1)
"
 ::= { cps6000CctEntry  16 }

cps6000CctEntryUv OBJECT-TYPE
SYNTAX      INTEGER {
inactive(0),
active(1)
}
MAX-ACCESS  read-only
STATUS      current
DESCRIPTION
"Under Voltage
Values:
inactive(0),
active(1)
"
 ::= { cps6000CctEntry  17 }

cps6000CctEntryOt OBJECT-TYPE
SYNTAX      INTEGER {
inactive(0),
active(1)
}
MAX-ACCESS  read-only
STATUS      current
DESCRIPTION
"Over Temperature
Values:
inactive(0),
active(1)
"
 ::= { cps6000CctEntry  18 }

cps6000CctEntryLds OBJECT-TYPE
SYNTAX      INTEGER {
inactive(0),
active(1)
}
MAX-ACCESS  read-only
STATUS      current
DESCRIPTION
"Load Drop Status
Values:
inactive(0),
active(1)
"
 ::= { cps6000CctEntry  19 }

cps6000CctEntryLss OBJECT-TYPE
SYNTAX      INTEGER {
inactive(0),
active(1)
}
MAX-ACCESS  read-only
STATUS      current
DESCRIPTION
"Load Share Status
Values:
inactive(0),
active(1)
"
 ::= { cps6000CctEntry  20 }

cps6000CctEntryLts OBJECT-TYPE
SYNTAX      INTEGER {
inactive(0),
active(1)
}
MAX-ACCESS  read-only
STATUS      current
DESCRIPTION
"Line Test Status
Values:
inactive(0),
active(1)
"
 ::= { cps6000CctEntry  21 }

cps6000CctEntryIlr OBJECT-TYPE
SYNTAX      DisplayString
UNITS       "Ohms"
MAX-ACCESS  read-only
STATUS      current
DESCRIPTION
"Initial Line Resistance (Ohms)"
 ::= { cps6000CctEntry  22 }

cps6000CctEntryAlr OBJECT-TYPE
SYNTAX      DisplayString
UNITS       "Ohms"
MAX-ACCESS  read-only
STATUS      current
DESCRIPTION
"Actual Line Resistance (Ohms)"
 ::= { cps6000CctEntry  23 }



END
