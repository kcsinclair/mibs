-- *****************************************************************
-- CISCO-CALLHOME-CAPABILITY.my:
-- Cisco CISCO-CALLHOME-MIB AGENT-CAPABILITIES
--   
-- March 2004, Dipesh Gorashia
-- Sept  2004, Arul Mozhi
--   
-- Copyright (c) 2004, 2006-2011 by Cisco Systems Inc.
-- All rights reserved.
-- ****************************************************************

CISCO-CALLHOME-CAPABILITY DEFINITIONS ::= BEGIN

IMPORTS
    MODULE-IDENTITY,
    Unsigned32
        FROM SNMPv2-SMI
    AGENT-CAPABILITIES
        FROM SNMPv2-CONF
    SnmpAdminString
        FROM SNMP-FRAMEWORK-MIB
    RowStatus
        FROM SNMPv2-TC
    CiscoURLString
        FROM CISCO-TC
    CallHomeTransportMethod
        FROM CISCO-CALLHOME-MIB
    ciscoAgentCapability
        FROM CISCO-SMI;


ciscoCallHomeCapability MODULE-IDENTITY
    LAST-UPDATED    "201104140000Z"
    ORGANIZATION    "Cisco Systems, Inc."
    CONTACT-INFO
            "Cisco Systems
            Customer Service

            Postal: 170 West Tasman Drive
            San Jose, CA  95134
            USA

            Tel: +1 800 553-NETS

            E-mail: cs-san@cisco.com,
            cs-lan-switch-snmp@cisco.com"
    DESCRIPTION
        "The capabilities description of
        CISCO-CALLHOME-MIB."
    REVISION        "201104140000Z"
    DESCRIPTION
        "Add the agent capabilities statement
        cCallHomeCapV15R0002SGPCat4K.

        Updated VARIATION of ccmAlertRateLimit for the following
        agent capabilities statements:
            cCallHomeCapV12R0233SXHPCat6k
            cCallHomeCapV12R0233SXIPCat6k
            cCallHomeCapV12R0233SXI2PCat6k
            cCallHomeCapV12R0250SYPCat6k
            cCallHomeCapV12R0252SGPCat4k"
    REVISION        "201011100000Z"
    DESCRIPTION
        "Add the agent capabilities statement
        cCallHomeCapV12R0250SYPCat6k."
    REVISION        "200907100000Z"
    DESCRIPTION
        "Added the agent capabilities statement
        cCallHomeCapV12R0233SXI2PCat6k."
    REVISION        "200906170000Z"
    DESCRIPTION
        "Updated the PRODUCT-RELEASE on agent capabilities statement
        cCallHomeCapV12R0252SGPCat4k."
    REVISION        "200905070000Z"
    DESCRIPTION
        "Added the agent capabilities statement
        cCallHomeCapV12R0252SGPCat4k.

        Added VARIATION statements of ccmPeriodicAlertGroupEnable and
        ccmEventAlertGroupEnable to cCallHomeCapV12R0233SXHPCat6k and
        cCallHomeCapV12R0233SXIPCat6k."
    REVISION        "200810270000Z"
    DESCRIPTION
        "Added the agent capabilities statement
        cCallHomeCapV12R0233SXIPCat6k."
    REVISION        "200707300000Z"
    DESCRIPTION
        "Added the agent capabilities statement
        cCallHomeCapV12R0233SXHPCat6k."
    REVISION        "200605100000Z"
    DESCRIPTION
        "Added the agent capabilities
        'cCallHomeCapSanOSV30R1MDS9000' for SanOS 3.0(1)  
        on Cisco MDS 9000 series devices.
        Added ccmSmtpServerFailNotif to 
        cCallHomeCapSanOSV20R1MDS9000."
    REVISION        "200409200000Z"
    DESCRIPTION
        "Added the agent capabilities
        'cCallHomeCapSanOSV20R1MDS9000' for SanOS 2.0(1)  
        on Cisco MDS 9000 series devices."
    REVISION        "200403300000Z"
    DESCRIPTION
        "Initial version of this MIB module."
    ::= { ciscoAgentCapability 355 }



cCallHomeCapCatOSV08R0101Cat6k AGENT-CAPABILITIES
    PRODUCT-RELEASE "Cisco CatOS 8.1(1) on Catalyst 6000/6500
                          and Cisco 7600 series devices."
    STATUS          current
    DESCRIPTION
        "CISCO-CALLHOME-MIB capabilities."

    SUPPORTS        CISCO-CALLHOME-MIB
    INCLUDES        {
                        chConfigurationGroup,
                        chMultipleSmtpServersGroup,
                        chStatisticsGroup,
                        ccmSysLogSeverityGroup,
                        ccmMIBNotificationsConfigGroup,
                        ccmMIBNotificationsGroup
                    }
    VARIATION       callHomeAlertAction
    SYNTAX          INTEGER  {
                        noOp(1),
                        test(2)
                    }
    DESCRIPTION
        "Only noOp (1) and test (2) enumerations
        are supported."

    VARIATION       callHomeDestProfileName
    SYNTAX          SnmpAdminString (SIZE (1..11))
    DESCRIPTION
        "Implementation supports a profile name of
        size 1 to 11 octets."

    VARIATION       callHomeDestProfileMsgFormat
    SYNTAX          INTEGER  {
                        shortText(3)
                    }
    ACCESS          read-only
    DESCRIPTION
        "Implementation supports read-only access
        for this object. Only shortText (3) is
        supported."

    VARIATION       callHomeDestProfileMaxMsgSize
    SYNTAX          Unsigned32 (0..159)
    DESCRIPTION
        "Message size in the range 0 to 159 is
        supported."

    VARIATION       callHomeDestProfileTrnsprtMthd
    SYNTAX          INTEGER  {
                        email(1)
                    }
    ACCESS          read-only
    DESCRIPTION
        "Implementation supports read-only access
        for this object. Only email (1) enumeration
        is supported."

    VARIATION       callHomeDestProfileStatus
    SYNTAX          INTEGER  {
                        active(1)
                    }
    ACCESS          read-only
    DESCRIPTION
        "Implementation supports read-only access
        for this object. Only active (1) enumeration
        is supported."

    VARIATION       callHomeDestEmailAddressEntry
    CREATION-REQUIRES { callHomeDestEmailAddress }
    DESCRIPTION
        "For callHomeDestEmailAddressStatus object
        for instance to be set to active (1),
        a valid value for corresponding
        callHomeDestEmailAddress is required."

    VARIATION       callHomeDestEmailAddressStatus
    SYNTAX          INTEGER  {
                        active(1),
                        createAndGo(4),
                        destroy(6)
                    }
    DESCRIPTION
        "Only active (1), createAndGo (4) and
        destroy (6) are supported."

    VARIATION       callHomeEmailFrom
    SYNTAX          SnmpAdminString (SIZE (0..63))
    DESCRIPTION
        "Implementation only supports an address of
        size 0 to 63 octets."

    VARIATION       callHomeEmailReplyTo
    SYNTAX          SnmpAdminString (SIZE (0..63))
    DESCRIPTION
        "Implementation only supports an address of
        size 0 to 63 octets."

    VARIATION       ccmSmtpServersAddrType
    SYNTAX          INTEGER  {
                        ipv4(1)
                    }
    DESCRIPTION
        "Implementation only supports IPv4 addresses."

    VARIATION       ccmSmtpServersPort
    ACCESS          read-only
    DESCRIPTION
        "Implementation supports read-only access
        for this object."

    VARIATION       ccmSmtpServersStatus
    SYNTAX          INTEGER  {
                        active(1),
                        createAndGo(4),
                        destroy(6)
                    }
    DESCRIPTION
        "Only active (1), createAndGo (4) and
        destroy (6) are supported."

    ::= { ciscoCallHomeCapability 1 }

cCallHomeCapSanOSV20R1MDS9000 AGENT-CAPABILITIES
    PRODUCT-RELEASE "Cisco SanOS 2.0(1) on Cisco MDS 9000 series 
                     devices."
    STATUS          current
    DESCRIPTION
        "Cisco CallHome MIB capabilities"

    SUPPORTS        CISCO-CALLHOME-MIB
    INCLUDES        {
                        chConfigurationGroup2,
                        chStatisticsGroup,
                        chEmailMsgDispGroup,
                        chSingleSmtpServerGroup,
                        ccmMIBNotificationsGroup1,
                        chPeriodicSwInventoryInfoGroup
                    }
    VARIATION       callHomeDestProfileTrnsprtMthd
    SYNTAX          INTEGER  {
                        email(1)
                    }
    ACCESS          read-only
    DESCRIPTION
        "Implementation supports read-only access
        for this object. Only email (1) enumeration
        is supported."

    VARIATION       callHomeDestProfileStatus
    SYNTAX          INTEGER  {
                        active(1),
                        createAndGo(4),
                        destroy(6)
                    }
    DESCRIPTION
        "Only a limited set of values is supported."

    VARIATION       callHomeDestEmailAddressStatus
    SYNTAX          INTEGER  {
                        active(1),
                        createAndGo(4),
                        destroy(6)
                    }
    DESCRIPTION
        "Only a limited set of values is supported."

    VARIATION       ccmSmtpServerFailNotif
    ACCESS          not-implemented
    DESCRIPTION
        "Not Supported."

    ::= { ciscoCallHomeCapability 2 }

cCallHomeCapSanOSV30R1MDS9000 AGENT-CAPABILITIES
    PRODUCT-RELEASE "Cisco SanOS 3.0(1) on Cisco MDS 9000 series 
                     devices."
    STATUS          current
    DESCRIPTION
        "Cisco CallHome MIB capabilities"

    SUPPORTS        CISCO-CALLHOME-MIB
    INCLUDES        {
                        chConfigurationGroup2,
                        chStatisticsGroup,
                        chEmailMsgDispGroup,
                        chSingleSmtpServerGroup,
                        ccmMIBNotificationsGroup1,
                        chPeriodicSwInventoryInfoGroup,
                        ccmUserDefCmdGroup
                    }
    VARIATION       callHomeDestProfileTrnsprtMthd
    SYNTAX          INTEGER  {
                        email(1)
                    }
    ACCESS          read-only
    DESCRIPTION
        "Implementation supports read-only access
        for this object. Only email (1) enumeration
        is supported."

    VARIATION       callHomeDestProfileStatus
    SYNTAX          INTEGER  {
                        active(1),
                        createAndGo(4),
                        destroy(6)
                    }
    DESCRIPTION
        "Only a limited set of values is supported."

    VARIATION       callHomeDestEmailAddressStatus
    SYNTAX          INTEGER  {
                        active(1),
                        createAndGo(4),
                        destroy(6)
                    }
    DESCRIPTION
        "Only a limited set of values is supported."

    VARIATION       ccmSmtpServerFailNotif
    ACCESS          not-implemented
    DESCRIPTION
        "Not Supported."

    ::= { ciscoCallHomeCapability 3 }

cCallHomeCapV12R0233SXHPCat6k AGENT-CAPABILITIES
    PRODUCT-RELEASE "Cisco IOS 12.2(33)SXH on Catalyst 6000/6500
                         series devices."
    STATUS          current
    DESCRIPTION
        "CISCO-CALLHOME-MIB capabilities."

    SUPPORTS        CISCO-CALLHOME-MIB
    INCLUDES        {
                        chSystemInformationGroup1,
                        ccmConfigurationGroup3,
                        chMultipleSmtpServersGroup,
                        chStatisticsGroup,
                        ccmMIBNotificationsConfigGroup,
                        ccmMIBNotificationsGroup1,
                        ccmProfileActivationGroup,
                        ccmProfileTestGroup,
                        ccmProfileAlertGroupsGroup,
                        ccmProfileAlertGroupControlGroup,
                        ccmSmtpServersPriorityGroup,
                        ccmAlertGroupCapabilityGroup,
                        ccmHttpCfgGroup,
                        ccmSeverityAlertGroupCfgGroup,
                        ccmPeriodicAlertGroupCfgGroup,
                        ccmPatternAlertGroupCfgGroup,
                        ccmEventAlertGroupCfgGroup,
                        ccmSmtpMsgSendFailNotifCtrlGroup,
                        ccmSmtpMsgSendFailNotifGroup,
                        ccmAlertHCStatisticsGroup,
                        ccmAlertRateLimitGroup,
                        ccmSmtpServerStatusGroup,
                        ccmProfileHiMessageSizeGroup
                    }
    VARIATION       sysContactEmailAddress
    SYNTAX          SnmpAdminString (SIZE (0..200))
    DESCRIPTION
        "Implementation only supports an address of
        size 0 to 200 octets."

    VARIATION       callHomeCustomerId
    SYNTAX          SnmpAdminString (SIZE (0..64))
    DESCRIPTION
        "Implementation only supports string of up to
        64 characters."

    VARIATION       callHomeContractId
    SYNTAX          SnmpAdminString (SIZE (0..64))
    DESCRIPTION
        "Implementation only supports string of up to
        64 characters."

    VARIATION       callHomeSiteId
    SYNTAX          SnmpAdminString (SIZE (0..200))
    DESCRIPTION
        "Implementation only supports string of up to
        200 octets."

    VARIATION       callHomeEmailFrom
    SYNTAX          SnmpAdminString (SIZE (0..200))
    DESCRIPTION
        "Implementation only supports an address of
        size 0 to 200 octets."

    VARIATION       callHomeEmailReplyTo
    SYNTAX          SnmpAdminString (SIZE (0..200))
    DESCRIPTION
        "Implementation only supports an address of
        size 0 to 200 octets."

    VARIATION       callHomeDestProfileMaxMsgSize
    SYNTAX          Unsigned32 (50..1000000)
    DESCRIPTION
        "Only a limited set of values is supported."

    VARIATION       callHomeDestProfileTrnsprtMthd
    SYNTAX          CallHomeTransportMethod {
                        email(1),
                        http(3),
                        emailAndHttp(4)
                    }
    DESCRIPTION
        "Only a limited set of enumerated values is
        supported."

    VARIATION       callHomeDestProfileStatus
    SYNTAX          RowStatus {
                        active(1),
                        createAndGo(4),
                        destroy(6)
                    }
    DESCRIPTION
        "Only a limited set of enumerated values is
        supported.
        For the system created profile with
        callHomeDestProfileName as 'CiscoTAC-1',
        the only enumeration supported is 'active'."

    VARIATION       callHomeDestProfileHiMaxMsgSize
    SYNTAX          Unsigned32 (50..3145728)
    DESCRIPTION
        "The object supports only the values in the
        range of 50 to 3145728."

    VARIATION       callHomeDestEmailAddress
    SYNTAX          SnmpAdminString (SIZE (0..200))
    DESCRIPTION
        "Implementation only supports an address of
        size 0 to 200 octets."

    VARIATION       callHomeDestEmailAddressStatus
    SYNTAX          RowStatus {
                        active(1),
                        createAndGo(4),
                        destroy(6)
                    }
    DESCRIPTION
        "Only a limited set of enumerated values is
        supported.
        For the system created profile with
        callHomeDestProfileName as 'CiscoTAC-1',
        the only enumeration supported is 'active'."

    VARIATION       callHomeDestHttpUrl
    SYNTAX          CiscoURLString (SIZE (1..200))
    DESCRIPTION
        "Implementation only supports an address of
        size 1 to 200 octets."

    VARIATION       ccmSmtpServersAddrType
    SYNTAX          INTEGER  {
                        ipv4(1),
                        dns(16)
                    }
    DESCRIPTION
        "Implementation only supports IPv4 and DNS
        addresses."

    VARIATION       callHomeSmtpServerPort
    ACCESS          read-only
    DESCRIPTION
        "Unable to set this object on Catalyst 6500
        devices running IOS."

    VARIATION       ccmSmtpServersStatus
    SYNTAX          RowStatus {
                        active(1),
                        createAndGo(4),
                        destroy(6)
                    }
    DESCRIPTION
        "Only a limited set of enumerated values is
        supported."

    VARIATION       ccmAlertGroupTypeAddedNotif
    ACCESS          not-implemented
    DESCRIPTION
        "Object not implemented."

    VARIATION       ccmAlertGroupTypeDeletedNotif
    ACCESS          not-implemented
    DESCRIPTION
        "Object not implemented."

    VARIATION       ccmDestProfileTestMessage
    SYNTAX          SnmpAdminString (SIZE (0..128))
    DESCRIPTION
        "Implementation supports test message of
        only up to 128 octets."

    VARIATION       ccmPeriodicAlertGroupEnable
    DESCRIPTION
        "Setting the object to 'false' will cause the
        profile to unsubscribe the alert group if
        ccmEventAlertGroupEnable for the profile is
        also 'false'."

    VARIATION       ccmPatternAlertGroupStorage
    ACCESS          read-only
    DESCRIPTION
        "Unable to set this object on Catalyst 6500
        devices running IOS."

    VARIATION       ccmPatternAlertGroupStatus
    SYNTAX          RowStatus {
                        active(1),
                        createAndGo(4),
                        destroy(6)
                    }
    DESCRIPTION
        "Only a limited set of enumerated values is
        supported."

    VARIATION       ccmEventAlertGroupEnable
    DESCRIPTION
        "Setting the object to 'false' will cause the
        profile to unsubscribe the alert group if
        ccmPeriodicAlertGroupEnable for the profile is
        also 'false'."

    VARIATION       ccmAlertRateLimit
    SYNTAX          Unsigned32 (1..60)
    DESCRIPTION
        "Only a limited set of values is supported."

    ::= { ciscoCallHomeCapability 4 }

cCallHomeCapV12R0233SXIPCat6k AGENT-CAPABILITIES
    PRODUCT-RELEASE "Cisco IOS 12.2(33)SXI on Catalyst 6000/6500
                     series devices."
    STATUS          current
    DESCRIPTION
        "CISCO-CALLHOME-MIB capabilities."

    SUPPORTS        CISCO-CALLHOME-MIB
    INCLUDES        {
                        chSystemInformationGroup1,
                        ccmConfigurationGroup3,
                        chMultipleSmtpServersGroup,
                        chStatisticsGroup,
                        ccmMIBNotificationsConfigGroup,
                        ccmMIBNotificationsGroup1,
                        ccmProfileActivationGroup,
                        ccmProfileTestGroup,
                        ccmProfileAlertGroupsGroup,
                        ccmProfileAlertGroupControlGroup,
                        ccmSmtpServersPriorityGroup,
                        ccmAlertGroupCapabilityGroup,
                        ccmHttpCfgGroup,
                        ccmSeverityAlertGroupCfgGroup,
                        ccmPeriodicAlertGroupCfgGroup,
                        ccmPatternAlertGroupCfgGroup,
                        ccmEventAlertGroupCfgGroup,
                        ccmSmtpMsgSendFailNotifCtrlGroup,
                        ccmSmtpMsgSendFailNotifGroup,
                        ccmAlertHCStatisticsGroup,
                        ccmAlertRateLimitGroup,
                        ccmSmtpServerStatusGroup,
                        ccmProfileHiMessageSizeGroup,
                        ccmOnDemandMsgSendControlGroup,
                        ccmOnDemandMsgStatusGroup,
                        ccmSmartCallHomeGroup,
                        ccmEventStatsGroup
                    }
    VARIATION       sysContactEmailAddress
    SYNTAX          SnmpAdminString (SIZE (0..200))
    DESCRIPTION
        "Only a limited set of values is supported."

    VARIATION       callHomeCustomerId
    SYNTAX          SnmpAdminString (SIZE (0..64))
    DESCRIPTION
        "Only a limited set of values is supported."

    VARIATION       callHomeContractId
    SYNTAX          SnmpAdminString (SIZE (0..64))
    DESCRIPTION
        "Only a limited set of values is supported."

    VARIATION       callHomeSiteId
    SYNTAX          SnmpAdminString (SIZE (0..200))
    DESCRIPTION
        "Only a limited set of values is supported."

    VARIATION       callHomeEmailFrom
    SYNTAX          SnmpAdminString (SIZE (0..200))
    DESCRIPTION
        "Only a limited set of values is supported."

    VARIATION       callHomeEmailReplyTo
    SYNTAX          SnmpAdminString (SIZE (0..200))
    DESCRIPTION
        "Only a limited set of values is supported."

    VARIATION       callHomeDestProfileMaxMsgSize
    SYNTAX          Unsigned32 (50..1000000)
    DESCRIPTION
        "Only a limited set of values is supported."

    VARIATION       callHomeDestProfileTrnsprtMthd
    SYNTAX          CallHomeTransportMethod {
                        email(1),
                        http(3),
                        emailAndHttp(4)
                    }
    DESCRIPTION
        "Only a limited set of enumerated values is
        supported."

    VARIATION       callHomeDestProfileStatus
    SYNTAX          RowStatus {
                        active(1),
                        createAndGo(4),
                        destroy(6)
                    }
    DESCRIPTION
        "Only a limited set of enumerated values is
        supported.
        For the system created profile with
        callHomeDestProfileName as 'CiscoTAC-1',
        the only enumeration supported is 'active'."

    VARIATION       callHomeDestProfileHiMaxMsgSize
    SYNTAX          Unsigned32 (50..3145728)
    DESCRIPTION
        "Only a limited set of values is supported."

    VARIATION       callHomeDestEmailAddress
    SYNTAX          SnmpAdminString (SIZE (0..200))
    DESCRIPTION
        "Only a limited set of values is supported."

    VARIATION       callHomeDestEmailAddressStatus
    SYNTAX          RowStatus {
                        active(1),
                        createAndGo(4),
                        destroy(6)
                    }
    DESCRIPTION
        "Only a limited set of enumerated values is
        supported.
        For the system created profile with
        callHomeDestProfileName as 'CiscoTAC-1',
        the only enumeration supported is 'active'."

    VARIATION       callHomeDestHttpUrl
    SYNTAX          CiscoURLString (SIZE (1..200))
    DESCRIPTION
        "Only a limited set of values is supported."

    VARIATION       ccmSmtpServersAddrType
    SYNTAX          INTEGER  {
                        ipv4(1),
                        dns(16)
                    }
    DESCRIPTION
        "Implementation only supports IPv4 and DNS
        addresses."

    VARIATION       callHomeSmtpServerPort
    ACCESS          read-only
    DESCRIPTION
        "Unable to set this object on Catalyst 6500
        devices running IOS."

    VARIATION       ccmSmtpServersStatus
    SYNTAX          RowStatus {
                        active(1),
                        createAndGo(4),
                        destroy(6)
                    }
    DESCRIPTION
        "Only a limited set of enumerated values is
        supported."

    VARIATION       ccmAlertGroupTypeAddedNotif
    ACCESS          not-implemented
    DESCRIPTION
        "Object not implemented."

    VARIATION       ccmAlertGroupTypeDeletedNotif
    ACCESS          not-implemented
    DESCRIPTION
        "Object not implemented."

    VARIATION       ccmDestProfileTestMessage
    SYNTAX          SnmpAdminString (SIZE (0..128))
    DESCRIPTION
        "Only a limited set of values is supported."

    VARIATION       ccmPeriodicAlertGroupEnable
    DESCRIPTION
        "Setting the object to 'false' will cause the
        profile to unsubscribe the alert group if
        ccmEventAlertGroupEnable for the profile is
        also 'false'."

    VARIATION       ccmPatternAlertGroupStorage
    ACCESS          read-only
    DESCRIPTION
        "Unable to set this object on Catalyst 6500
        devices running IOS."

    VARIATION       ccmPatternAlertGroupStatus
    SYNTAX          RowStatus {
                        active(1),
                        createAndGo(4),
                        destroy(6)
                    }
    DESCRIPTION
        "Only a limited set of enumerated values is
        supported."

    VARIATION       ccmEventAlertGroupEnable
    DESCRIPTION
        "Setting the object to 'false' will cause the
        profile to unsubscribe the alert group if
        ccmPeriodicAlertGroupEnable for the profile is
        also 'false'."

    VARIATION       ccmAlertRateLimit
    SYNTAX          Unsigned32 (1..60)
    DESCRIPTION
        "Only a limited set of values is supported."

    VARIATION       ccmSmartCallHomeAnalysisCmd
    SYNTAX          SnmpAdminString (SIZE (0..200))
    DESCRIPTION
        "Only a limited set of values is supported."

    VARIATION       ccmOnDemandMsgSendEntPhyIndex
    DESCRIPTION
        "Only entPhysicalIndex of Supervisor and Line Card
        modules are supported."

    VARIATION       ccmSmartCallHomeCcoId
    SYNTAX          SnmpAdminString (SIZE (0..200))
    DESCRIPTION
        "Only a limited set of values is supported."

    ::= { ciscoCallHomeCapability 5 }

cCallHomeCapV12R0252SGPCat4k AGENT-CAPABILITIES
    PRODUCT-RELEASE "Cisco IOS 12.2(52)SG on Catalyst 4000 family
                    switches, except LAN Base images."
    STATUS          current
    DESCRIPTION
        "CISCO-CALLHOME-MIB capabilities."

    SUPPORTS        CISCO-CALLHOME-MIB
    INCLUDES        {
                        chSystemInformationGroup1,
                        ccmConfigurationGroup3,
                        chMultipleSmtpServersGroup,
                        chStatisticsGroup,
                        ccmMIBNotificationsConfigGroup,
                        ccmMIBNotificationsGroup1,
                        ccmProfileActivationGroup,
                        ccmProfileTestGroup,
                        ccmProfileAlertGroupsGroup,
                        ccmProfileAlertGroupControlGroup,
                        ccmSmtpServersPriorityGroup,
                        ccmAlertGroupCapabilityGroup,
                        ccmHttpCfgGroup,
                        ccmSeverityAlertGroupCfgGroup,
                        ccmPeriodicAlertGroupCfgGroup,
                        ccmPatternAlertGroupCfgGroup,
                        ccmEventAlertGroupCfgGroup,
                        ccmSmtpMsgSendFailNotifCtrlGroup,
                        ccmSmtpMsgSendFailNotifGroup,
                        ccmAlertHCStatisticsGroup,
                        ccmAlertRateLimitGroup,
                        ccmSmtpServerStatusGroup,
                        ccmProfileHiMessageSizeGroup,
                        ccmOnDemandMsgSendControlGroup,
                        ccmOnDemandMsgStatusGroup,
                        ccmSmartCallHomeGroup,
                        ccmEventStatsGroup,
                        ccmCallHomeVrfGroup
                    }
    VARIATION       sysContactEmailAddress
    SYNTAX          SnmpAdminString (SIZE (0..200))
    DESCRIPTION
        "Only a limited set of values is supported."

    VARIATION       callHomeCustomerId
    SYNTAX          SnmpAdminString (SIZE (0..64))
    DESCRIPTION
        "Only a limited set of values is supported."

    VARIATION       callHomeContractId
    SYNTAX          SnmpAdminString (SIZE (0..64))
    DESCRIPTION
        "Only a limited set of values is supported."

    VARIATION       callHomeSiteId
    SYNTAX          SnmpAdminString (SIZE (0..200))
    DESCRIPTION
        "Only a limited set of values is supported."

    VARIATION       callHomeEmailFrom
    SYNTAX          SnmpAdminString (SIZE (0..200))
    DESCRIPTION
        "Only a limited set of values is supported."

    VARIATION       callHomeEmailReplyTo
    SYNTAX          SnmpAdminString (SIZE (0..200))
    DESCRIPTION
        "Only a limited set of values is supported."

    VARIATION       callHomeDestProfileMaxMsgSize
    SYNTAX          Unsigned32 (50..1000000)
    DESCRIPTION
        "Only a limited set of values is supported."

    VARIATION       callHomeDestProfileTrnsprtMthd
    SYNTAX          CallHomeTransportMethod {
                        email(1),
                        http(3),
                        emailAndHttp(4)
                    }
    DESCRIPTION
        "Only a limited set of enumerated values is
        supported."

    VARIATION       callHomeDestProfileStatus
    SYNTAX          RowStatus {
                        active(1),
                        createAndGo(4),
                        destroy(6)
                    }
    DESCRIPTION
        "Only a limited set of enumerated values is
        supported.
        For the system created profile with
        callHomeDestProfileName as 'CiscoTAC-1',
        the only enumeration supported is 'active'."

    VARIATION       callHomeDestProfileHiMaxMsgSize
    SYNTAX          Unsigned32 (50..3145728)
    DESCRIPTION
        "Only a limited set of values is supported."

    VARIATION       callHomeDestEmailAddress
    SYNTAX          SnmpAdminString (SIZE (0..200))
    DESCRIPTION
        "Only a limited set of values is supported."

    VARIATION       callHomeDestEmailAddressStatus
    SYNTAX          RowStatus {
                        active(1),
                        createAndGo(4),
                        destroy(6)
                    }
    DESCRIPTION
        "Only a limited set of enumerated values is
        supported.
        For the system created profile with
        callHomeDestProfileName as 'CiscoTAC-1',
        the only enumeration supported is 'active'."

    VARIATION       callHomeDestHttpUrl
    SYNTAX          CiscoURLString (SIZE (1..200))
    DESCRIPTION
        "Only a limited set of values is supported."

    VARIATION       ccmSmtpServersAddrType
    SYNTAX          INTEGER  {
                        ipv4(1),
                        dns(16)
                    }
    DESCRIPTION
        "Implementation only supports IPv4 and DNS
        addresses."

    VARIATION       callHomeSmtpServerPort
    ACCESS          read-only
    DESCRIPTION
        "Unable to set this object."

    VARIATION       ccmSmtpServersStatus
    SYNTAX          RowStatus {
                        active(1),
                        createAndGo(4),
                        destroy(6)
                    }
    DESCRIPTION
        "Only a limited set of enumerated values is
        supported."

    VARIATION       ccmAlertGroupTypeAddedNotif
    ACCESS          not-implemented
    DESCRIPTION
        "Object not implemented."

    VARIATION       ccmAlertGroupTypeDeletedNotif
    ACCESS          not-implemented
    DESCRIPTION
        "Object not implemented."

    VARIATION       ccmDestProfileTestMessage
    SYNTAX          SnmpAdminString (SIZE (0..128))
    DESCRIPTION
        "Only a limited set of values is supported."

    VARIATION       ccmPeriodicAlertGroupEnable
    DESCRIPTION
        "Setting the object to 'false' will cause the
        profile to unsubscribe the alert group if
        ccmEventAlertGroupEnable for the profile is
        also 'false'."

    VARIATION       ccmPatternAlertGroupStorage
    ACCESS          read-only
    DESCRIPTION
        "Unable to set this object."

    VARIATION       ccmPatternAlertGroupStatus
    SYNTAX          RowStatus {
                        active(1),
                        createAndGo(4),
                        destroy(6)
                    }
    DESCRIPTION
        "Only a limited set of enumerated values is
        supported."

    VARIATION       ccmEventAlertGroupEnable
    DESCRIPTION
        "Setting the object to 'false' will cause the
        profile to unsubscribe the alert group if
        ccmPeriodicAlertGroupEnable for the profile is
        also 'false'."

    VARIATION       ccmAlertRateLimit
    SYNTAX          Unsigned32 (1..60)
    DESCRIPTION
        "Only a limited set of values is supported."

    VARIATION       ccmSmartCallHomeAnalysisCmd
    SYNTAX          SnmpAdminString (SIZE (0..200))
    DESCRIPTION
        "Only a limited set of values is supported."

    VARIATION       ccmOnDemandMsgSendEntPhyIndex
    DESCRIPTION
        "Only entPhysicalIndex of Supervisor and Line Card
        modules are supported."

    VARIATION       ccmSmartCallHomeCcoId
    SYNTAX          SnmpAdminString (SIZE (0..200))
    DESCRIPTION
        "Only a limited set of values is supported."

    ::= { ciscoCallHomeCapability 6 }

cCallHomeCapV12R0233SXI2PCat6k AGENT-CAPABILITIES
    PRODUCT-RELEASE "Cisco IOS 12.2(33)SXI2 on Catalyst 6000/6500
                     series devices."
    STATUS          current
    DESCRIPTION
        "CISCO-CALLHOME-MIB capabilities."

    SUPPORTS        CISCO-CALLHOME-MIB
    INCLUDES        {
                        chSystemInformationGroup1,
                        ccmConfigurationGroup3,
                        chMultipleSmtpServersGroup,
                        chStatisticsGroup,
                        ccmMIBNotificationsConfigGroup,
                        ccmMIBNotificationsGroup1,
                        ccmProfileActivationGroup,
                        ccmProfileTestGroup,
                        ccmProfileAlertGroupsGroup,
                        ccmProfileAlertGroupControlGroup,
                        ccmSmtpServersPriorityGroup,
                        ccmAlertGroupCapabilityGroup,
                        ccmHttpCfgGroup,
                        ccmSeverityAlertGroupCfgGroup,
                        ccmPeriodicAlertGroupCfgGroup,
                        ccmPatternAlertGroupCfgGroup,
                        ccmEventAlertGroupCfgGroup,
                        ccmSmtpMsgSendFailNotifCtrlGroup,
                        ccmSmtpMsgSendFailNotifGroup,
                        ccmAlertHCStatisticsGroup,
                        ccmAlertRateLimitGroup,
                        ccmSmtpServerStatusGroup,
                        ccmProfileHiMessageSizeGroup,
                        ccmOnDemandMsgSendControlGroup,
                        ccmOnDemandMsgStatusGroup,
                        ccmSmartCallHomeGroup,
                        ccmEventStatsGroup,
                        ccmCallHomeVrfGroup
                    }
    VARIATION       sysContactEmailAddress
    SYNTAX          SnmpAdminString (SIZE (0..200))
    DESCRIPTION
        "Only a limited set of values is supported."

    VARIATION       callHomeCustomerId
    SYNTAX          SnmpAdminString (SIZE (0..64))
    DESCRIPTION
        "Only a limited set of values is supported."

    VARIATION       callHomeContractId
    SYNTAX          SnmpAdminString (SIZE (0..64))
    DESCRIPTION
        "Only a limited set of values is supported."

    VARIATION       callHomeSiteId
    SYNTAX          SnmpAdminString (SIZE (0..200))
    DESCRIPTION
        "Only a limited set of values is supported."

    VARIATION       callHomeEmailFrom
    SYNTAX          SnmpAdminString (SIZE (0..200))
    DESCRIPTION
        "Only a limited set of values is supported."

    VARIATION       callHomeEmailReplyTo
    SYNTAX          SnmpAdminString (SIZE (0..200))
    DESCRIPTION
        "Only a limited set of values is supported."

    VARIATION       callHomeDestProfileMaxMsgSize
    SYNTAX          Unsigned32 (50..1000000)
    DESCRIPTION
        "Only a limited set of values is supported."

    VARIATION       callHomeDestProfileTrnsprtMthd
    SYNTAX          CallHomeTransportMethod {
                        email(1),
                        http(3),
                        emailAndHttp(4)
                    }
    DESCRIPTION
        "Only a limited set of enumerated values is
        supported."

    VARIATION       callHomeDestProfileStatus
    SYNTAX          RowStatus {
                        active(1),
                        createAndGo(4),
                        destroy(6)
                    }
    DESCRIPTION
        "Only a limited set of enumerated values is
        supported.
        For the system created profile with
        callHomeDestProfileName as 'CiscoTAC-1',
        the only enumeration supported is 'active'."

    VARIATION       callHomeDestProfileHiMaxMsgSize
    SYNTAX          Unsigned32 (50..3145728)
    DESCRIPTION
        "Only a limited set of values is supported."

    VARIATION       callHomeDestEmailAddress
    SYNTAX          SnmpAdminString (SIZE (0..200))
    DESCRIPTION
        "Only a limited set of values is supported."

    VARIATION       callHomeDestEmailAddressStatus
    SYNTAX          RowStatus {
                        active(1),
                        createAndGo(4),
                        destroy(6)
                    }
    DESCRIPTION
        "Only a limited set of enumerated values is
        supported.
        For the system created profile with
        callHomeDestProfileName as 'CiscoTAC-1',
        the only enumeration supported is 'active'."

    VARIATION       callHomeDestHttpUrl
    SYNTAX          CiscoURLString (SIZE (1..200))
    DESCRIPTION
        "Only a limited set of values is supported."

    VARIATION       ccmSmtpServersAddrType
    SYNTAX          INTEGER  {
                        ipv4(1),
                        dns(16)
                    }
    DESCRIPTION
        "Implementation only supports IPv4 and DNS
        addresses."

    VARIATION       callHomeSmtpServerPort
    ACCESS          read-only
    DESCRIPTION
        "Write access is not supported."

    VARIATION       ccmSmtpServersStatus
    SYNTAX          RowStatus {
                        active(1),
                        createAndGo(4),
                        destroy(6)
                    }
    DESCRIPTION
        "Only a limited set of enumerated values is
        supported."

    VARIATION       ccmAlertGroupTypeAddedNotif
    ACCESS          not-implemented
    DESCRIPTION
        "Object not implemented."

    VARIATION       ccmAlertGroupTypeDeletedNotif
    ACCESS          not-implemented
    DESCRIPTION
        "Object not implemented."

    VARIATION       ccmDestProfileTestMessage
    SYNTAX          SnmpAdminString (SIZE (0..128))
    DESCRIPTION
        "Only a limited set of values is supported."

    VARIATION       ccmPeriodicAlertGroupEnable
    DESCRIPTION
        "Setting the object to 'false' will cause the
        profile to unsubscribe the alert group if
        ccmEventAlertGroupEnable for the profile is
        also 'false'."

    VARIATION       ccmPatternAlertGroupStorage
    ACCESS          read-only
    DESCRIPTION
        "Write access is not supported."

    VARIATION       ccmPatternAlertGroupStatus
    SYNTAX          RowStatus {
                        active(1),
                        createAndGo(4),
                        destroy(6)
                    }
    DESCRIPTION
        "Only a limited set of enumerated values is
        supported."

    VARIATION       ccmEventAlertGroupEnable
    DESCRIPTION
        "Setting the object to 'false' will cause the
        profile to unsubscribe the alert group if
        ccmPeriodicAlertGroupEnable for the profile is
        also 'false'."

    VARIATION       ccmAlertRateLimit
    SYNTAX          Unsigned32 (1..60)
    DESCRIPTION
        "Only a limited set of values is supported."

    VARIATION       ccmSmartCallHomeAnalysisCmd
    SYNTAX          SnmpAdminString (SIZE (0..200))
    DESCRIPTION
        "Only a limited set of values is supported."

    VARIATION       ccmOnDemandMsgSendEntPhyIndex
    DESCRIPTION
        "Only entPhysicalIndex of Supervisor and Line Card
        modules are supported."

    VARIATION       ccmSmartCallHomeCcoId
    SYNTAX          SnmpAdminString (SIZE (0..200))
    DESCRIPTION
        "Only a limited set of values is supported."

    ::= { ciscoCallHomeCapability 7 }

cCallHomeCapV12R0250SYPCat6k AGENT-CAPABILITIES
    PRODUCT-RELEASE "Cisco IOS 12.2(50)SY on Catalyst 6000/6500
                     series devices."
    STATUS          current
    DESCRIPTION
        "CISCO-CALLHOME-MIB capabilities."

    SUPPORTS        CISCO-CALLHOME-MIB
    INCLUDES        {
                        chSystemInformationGroup1,
                        ccmConfigurationGroup3,
                        chMultipleSmtpServersGroup,
                        chStatisticsGroup,
                        ccmMIBNotificationsConfigGroup,
                        ccmMIBNotificationsGroup1,
                        ccmProfileActivationGroup,
                        ccmProfileTestGroup,
                        ccmProfileAlertGroupsGroup,
                        ccmProfileAlertGroupControlGroup,
                        ccmSmtpServersPriorityGroup,
                        ccmAlertGroupCapabilityGroup,
                        ccmHttpCfgGroup,
                        ccmSeverityAlertGroupCfgGroup,
                        ccmPeriodicAlertGroupCfgGroup,
                        ccmPatternAlertGroupCfgGroup,
                        ccmEventAlertGroupCfgGroup,
                        ccmSmtpMsgSendFailNotifCtrlGroup,
                        ccmSmtpMsgSendFailNotifGroup,
                        ccmAlertHCStatisticsGroup,
                        ccmAlertRateLimitGroup,
                        ccmSmtpServerStatusGroup,
                        ccmProfileHiMessageSizeGroup,
                        ccmOnDemandMsgSendControlGroup,
                        ccmOnDemandMsgStatusGroup,
                        ccmSmartCallHomeGroup,
                        ccmEventStatsGroup,
                        ccmCallHomeVrfGroup,
                        ccmMessageSourceGroup
                    }
    VARIATION       sysContactEmailAddress
    SYNTAX          SnmpAdminString (SIZE (0..200))
    DESCRIPTION
        "Only a limited set of values is supported."

    VARIATION       callHomeCustomerId
    SYNTAX          SnmpAdminString (SIZE (0..64))
    DESCRIPTION
        "Only a limited set of values is supported."

    VARIATION       callHomeContractId
    SYNTAX          SnmpAdminString (SIZE (0..64))
    DESCRIPTION
        "Only a limited set of values is supported."

    VARIATION       callHomeSiteId
    SYNTAX          SnmpAdminString (SIZE (0..200))
    DESCRIPTION
        "Only a limited set of values is supported."

    VARIATION       callHomeEmailFrom
    SYNTAX          SnmpAdminString (SIZE (0..200))
    DESCRIPTION
        "Only a limited set of values is supported."

    VARIATION       callHomeEmailReplyTo
    SYNTAX          SnmpAdminString (SIZE (0..200))
    DESCRIPTION
        "Only a limited set of values is supported."

    VARIATION       callHomeDestProfileMaxMsgSize
    SYNTAX          Unsigned32 (50..1000000)
    DESCRIPTION
        "Only a limited set of values is supported."

    VARIATION       callHomeDestProfileTrnsprtMthd
    SYNTAX          CallHomeTransportMethod {
                        email(1),
                        http(3),
                        emailAndHttp(4)
                    }
    DESCRIPTION
        "Only a limited set of enumerated values is
        supported."

    VARIATION       callHomeDestProfileStatus
    SYNTAX          RowStatus {
                        active(1),
                        createAndGo(4),
                        destroy(6)
                    }
    DESCRIPTION
        "Only a limited set of enumerated values is
        supported.
        For the system created profile with
        callHomeDestProfileName as 'CiscoTAC-1',
        the only enumeration supported is 'active'."

    VARIATION       callHomeDestProfileHiMaxMsgSize
    SYNTAX          Unsigned32 (50..3145728)
    DESCRIPTION
        "Only a limited set of values is supported."

    VARIATION       callHomeDestEmailAddress
    SYNTAX          SnmpAdminString (SIZE (0..200))
    DESCRIPTION
        "Only a limited set of values is supported."

    VARIATION       callHomeDestEmailAddressStatus
    SYNTAX          RowStatus {
                        active(1),
                        createAndGo(4),
                        destroy(6)
                    }
    DESCRIPTION
        "Only a limited set of enumerated values is
        supported.
        For the system created profile with
        callHomeDestProfileName as 'CiscoTAC-1',
        the only enumeration supported is 'active'."

    VARIATION       callHomeDestHttpUrl
    SYNTAX          CiscoURLString (SIZE (1..200))
    DESCRIPTION
        "Only a limited set of values is supported."

    VARIATION       ccmSmtpServersAddrType
    SYNTAX          INTEGER  {
                        ipv4(1),
                        dns(16)
                    }
    DESCRIPTION
        "Implementation only supports IPv4 and DNS
        addresses."

    VARIATION       callHomeSmtpServerPort
    ACCESS          read-only
    DESCRIPTION
        "Write access is not supported."

    VARIATION       ccmSmtpServersStatus
    SYNTAX          RowStatus {
                        active(1),
                        createAndGo(4),
                        destroy(6)
                    }
    DESCRIPTION
        "Only a limited set of enumerated values is
        supported."

    VARIATION       ccmAlertGroupTypeAddedNotif
    ACCESS          not-implemented
    DESCRIPTION
        "Object not implemented."

    VARIATION       ccmAlertGroupTypeDeletedNotif
    ACCESS          not-implemented
    DESCRIPTION
        "Object not implemented."

    VARIATION       ccmDestProfileTestMessage
    SYNTAX          SnmpAdminString (SIZE (0..128))
    DESCRIPTION
        "Only a limited set of values is supported."

    VARIATION       ccmPeriodicAlertGroupEnable
    DESCRIPTION
        "Setting the object to 'false' will cause the
        profile to unsubscribe the alert group if
        ccmEventAlertGroupEnable for the profile is
        also 'false'."

    VARIATION       ccmPatternAlertGroupStorage
    ACCESS          read-only
    DESCRIPTION
        "Write access is not supported."

    VARIATION       ccmPatternAlertGroupStatus
    SYNTAX          RowStatus {
                        active(1),
                        createAndGo(4),
                        destroy(6)
                    }
    DESCRIPTION
        "Only a limited set of enumerated values is
        supported."

    VARIATION       ccmEventAlertGroupEnable
    DESCRIPTION
        "Setting the object to 'false' will cause the
        profile to unsubscribe the alert group if
        ccmPeriodicAlertGroupEnable for the profile is
        also 'false'."

    VARIATION       ccmAlertRateLimit
    SYNTAX          Unsigned32 (1..60)
    DESCRIPTION
        "Only a limited set of values is supported."

    VARIATION       ccmSmartCallHomeAnalysisCmd
    SYNTAX          SnmpAdminString (SIZE (0..200))
    DESCRIPTION
        "Only a limited set of values is supported."

    VARIATION       ccmOnDemandMsgSendEntPhyIndex
    DESCRIPTION
        "Only entPhysicalIndex of Supervisor and Line Card
        modules are supported."

    VARIATION       ccmSmartCallHomeCcoId
    SYNTAX          SnmpAdminString (SIZE (0..200))
    DESCRIPTION
        "Only a limited set of values is supported."

    VARIATION       ccmMsgSourceIpAddrType
    SYNTAX          INTEGER  {
                        unknown(0),
                        ipv4(1)
                    }
    DESCRIPTION
        "Only limited set of enumerated values is
        supported."

    ::= { ciscoCallHomeCapability 8 }

cCallHomeCapV15R0002SGPCat4K AGENT-CAPABILITIES
    PRODUCT-RELEASE "Cisco IOS 15.0(2)SG on Catalyst 4000 family
                    switches, except LAN Base images."
    STATUS          current
    DESCRIPTION
        "CISCO-CALLHOME-MIB capabilities."

    SUPPORTS        CISCO-CALLHOME-MIB
    INCLUDES        {
                        chSystemInformationGroup1,
                        ccmConfigurationGroup3,
                        chMultipleSmtpServersGroup,
                        chStatisticsGroup,
                        ccmMIBNotificationsConfigGroup,
                        ccmMIBNotificationsGroup1,
                        ccmProfileActivationGroup,
                        ccmProfileTestGroup,
                        ccmProfileAlertGroupsGroup,
                        ccmProfileAlertGroupControlGroup,
                        ccmSmtpServersPriorityGroup,
                        ccmAlertGroupCapabilityGroup,
                        ccmHttpCfgGroup,
                        ccmSeverityAlertGroupCfgGroup,
                        ccmPeriodicAlertGroupCfgGroup,
                        ccmPatternAlertGroupCfgGroup,
                        ccmEventAlertGroupCfgGroup,
                        ccmSmtpMsgSendFailNotifCtrlGroup,
                        ccmSmtpMsgSendFailNotifGroup,
                        ccmAlertHCStatisticsGroup,
                        ccmAlertRateLimitGroup,
                        ccmSmtpServerStatusGroup,
                        ccmProfileHiMessageSizeGroup,
                        ccmOnDemandMsgSendControlGroup,
                        ccmOnDemandMsgStatusGroup,
                        ccmSmartCallHomeGroup,
                        ccmEventStatsGroup,
                        ccmCallHomeVrfGroup,
                        ccmMessageSourceGroup
                    }
    VARIATION       sysContactEmailAddress
    SYNTAX          SnmpAdminString (SIZE (0..200))
    DESCRIPTION
        "Only a limited set of values is supported."

    VARIATION       callHomeCustomerId
    SYNTAX          SnmpAdminString (SIZE (0..64))
    DESCRIPTION
        "Only a limited set of values is supported."

    VARIATION       callHomeContractId
    SYNTAX          SnmpAdminString (SIZE (0..64))
    DESCRIPTION
        "Only a limited set of values is supported."

    VARIATION       callHomeSiteId
    SYNTAX          SnmpAdminString (SIZE (0..200))
    DESCRIPTION
        "Only a limited set of values is supported."

    VARIATION       callHomeEmailFrom
    SYNTAX          SnmpAdminString (SIZE (0..200))
    DESCRIPTION
        "Only a limited set of values is supported."

    VARIATION       callHomeEmailReplyTo
    SYNTAX          SnmpAdminString (SIZE (0..200))
    DESCRIPTION
        "Only a limited set of values is supported."

    VARIATION       callHomeDestProfileMaxMsgSize
    SYNTAX          Unsigned32 (50..1000000)
    DESCRIPTION
        "Only a limited set of values is supported."

    VARIATION       callHomeDestProfileTrnsprtMthd
    SYNTAX          CallHomeTransportMethod {
                        email(1),
                        http(3),
                        emailAndHttp(4)
                    }
    DESCRIPTION
        "Only a limited set of enumerated values is
        supported."

    VARIATION       callHomeDestProfileStatus
    SYNTAX          RowStatus {
                        active(1),
                        createAndGo(4),
                        destroy(6)
                    }
    DESCRIPTION
        "Only a limited set of enumerated values is
        supported.
        For the system created profile with
        callHomeDestProfileName as 'CiscoTAC-1',
        the only enumeration supported is 'active'."

    VARIATION       callHomeDestProfileHiMaxMsgSize
    SYNTAX          Unsigned32 (50..3145728)
    DESCRIPTION
        "Only a limited set of values is supported."

    VARIATION       callHomeDestEmailAddress
    SYNTAX          SnmpAdminString (SIZE (0..200))
    DESCRIPTION
        "Only a limited set of values is supported."

    VARIATION       callHomeDestEmailAddressStatus
    SYNTAX          RowStatus {
                        active(1),
                        createAndGo(4),
                        destroy(6)
                    }
    DESCRIPTION
        "Only a limited set of enumerated values is
        supported.
        For the system created profile with
        callHomeDestProfileName as 'CiscoTAC-1',
        the only enumeration supported is 'active'."

    VARIATION       callHomeDestHttpUrl
    SYNTAX          CiscoURLString (SIZE (1..200))
    DESCRIPTION
        "Only a limited set of values is supported."

    VARIATION       ccmSmtpServersAddrType
    SYNTAX          INTEGER  {
                        ipv4(1),
                        dns(16)
                    }
    DESCRIPTION
        "Implementation only supports IPv4 and DNS
        addresses."

    VARIATION       callHomeSmtpServerPort
    ACCESS          read-only
    DESCRIPTION
        "Write access is not supported."

    VARIATION       ccmSmtpServersStatus
    SYNTAX          RowStatus {
                        active(1),
                        createAndGo(4),
                        destroy(6)
                    }
    DESCRIPTION
        "Only a limited set of enumerated values is
        supported."

    VARIATION       ccmAlertGroupTypeAddedNotif
    ACCESS          not-implemented
    DESCRIPTION
        "Object not implemented."

    VARIATION       ccmAlertGroupTypeDeletedNotif
    ACCESS          not-implemented
    DESCRIPTION
        "Object not implemented."

    VARIATION       ccmDestProfileTestMessage
    SYNTAX          SnmpAdminString (SIZE (0..128))
    DESCRIPTION
        "Only a limited set of values is supported."

    VARIATION       ccmPeriodicAlertGroupEnable
    DESCRIPTION
        "Setting the object to 'false' will cause the
        profile to unsubscribe the alert group if
        ccmEventAlertGroupEnable for the profile is
        also 'false'."

    VARIATION       ccmPatternAlertGroupStorage
    ACCESS          read-only
    DESCRIPTION
        "Write access is not supported."

    VARIATION       ccmPatternAlertGroupStatus
    SYNTAX          RowStatus {
                        active(1),
                        createAndGo(4),
                        destroy(6)
                    }
    DESCRIPTION
        "Only a limited set of enumerated values is
        supported."

    VARIATION       ccmEventAlertGroupEnable
    DESCRIPTION
        "Setting the object to 'false' will cause the
        profile to unsubscribe the alert group if
        ccmPeriodicAlertGroupEnable for the profile is
        also 'false'."

    VARIATION       ccmAlertRateLimit
    SYNTAX          Unsigned32 (1..60)
    DESCRIPTION
        "Only a limited set of values is supported."

    VARIATION       ccmSmartCallHomeAnalysisCmd
    SYNTAX          SnmpAdminString (SIZE (0..200))
    DESCRIPTION
        "Only a limited set of values is supported."

    VARIATION       ccmOnDemandMsgSendEntPhyIndex
    DESCRIPTION
        "Only entPhysicalIndex of Supervisor and Line Card
        modules are supported."

    VARIATION       ccmSmartCallHomeCcoId
    SYNTAX          SnmpAdminString (SIZE (0..200))
    DESCRIPTION
        "Only a limited set of values is supported."

    VARIATION       ccmMsgSourceIpAddrType
    SYNTAX          INTEGER  {
                        unknown(0),
                        ipv4(1)
                    }
    DESCRIPTION
        "Only limited set of enumerated values is
        supported."

    ::= { ciscoCallHomeCapability 9 }

END
