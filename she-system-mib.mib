--
-- she-system-mib.mib
-- MIB generated by MG-SOFT Visual MIB Builder Version 6.0  Build 88
-- Wednesday, February 04, 2009 at 14:03:20
--

-- Start of ClearCase branch-information of current release:
-- she-system-mib.mib   /main/she_main_grf/28
-- End of ClearCase branch-information.

	SHE-SYSTEM-MIB DEFINITIONS ::= BEGIN
 
		IMPORTS
			she			
				FROM AN-MIB			
			entPhysicalIndex, PhysicalIndex			
				FROM ENTITY-MIB			
			sheAlarmTimeAndDate, sheAlarmReportingSource, sheAlarmReportingSourceType, sheAlarmSeverity			
				FROM SHE-ALARMING-MIB			
			SheControlStatusType, SheCardType, SheSystemFileIndexType			
				FROM SHE-TC-MIB			
			OBJECT-GROUP, MODULE-COMPLIANCE, NOTIFICATION-GROUP			
				FROM SNMPv2-CONF			
			TimeTicks, IpAddress, Integer32, Unsigned32, Gauge32, 
			OBJECT-TYPE, MODULE-IDENTITY, NOTIFICATION-TYPE			
				FROM SNMPv2-SMI			
			DisplayString, TruthValue, TEXTUAL-CONVENTION			
				FROM SNMPv2-TC;
	
	
--  1.3.6.1.4.1.231.7.1.2.2.1.2
		sheSystem MODULE-IDENTITY 
			LAST-UPDATED "200902041300Z"		-- February 04, 2009 at 13:00 GMT
			ORGANIZATION 
				"Nokia Siemens Networks"
			CONTACT-INFO 
				"Gerd Barchmann
				COO BBA DSLAM RD SDE
				
				gerd.barchmann@nsn.com
				+49 3834 555654"
			DESCRIPTION 
				" Definition of system global information and configuration,
				e.g. configuration of external time, snmp configuration
				file management for up and download of 
				- loads, 
				- configuration files
				- errorlog
				- remote inventory
				- performance data file
				- snmp configuration file
				"
			REVISION "200410071000Z"		-- October 07, 2004 at 10:00 GMT
			DESCRIPTION 
				"Add managed objects as to TimeZone"
			REVISION "200411241439Z"		-- November 24, 2004 at 14:39 GMT
			DESCRIPTION 
				"IUS Release 2. Correct access for
				sheSystemControlExternalTime."
			REVISION "200412081000Z"		-- December 08, 2004 at 10:00 GMT
			DESCRIPTION 
				"Change Description for sheSystemVersion."
			REVISION "200412201413Z"		-- December 20, 2004 at 14:13 GMT
			DESCRIPTION 
				"Change the description for the possible values of sheSystemVersion string."
			REVISION "200608221505Z"		-- August 22, 2006 at 15:05 GMT
			DESCRIPTION 
				"Take over by Gerd Barchmann for R2.5."
			REVISION "200609131512Z"		-- September 13, 2006 at 15:12 GMT
			DESCRIPTION 
				"Correct description for some sheSystemConfigLogFtp - parameters.
				Username and password could never be readout via snmp if.
				Correct spelling of variables in sheSystemSwmControl."
			REVISION "200611201222Z"		-- November 20, 2006 at 12:22 GMT
			DESCRIPTION 
				"Correct some names and definitions for backward compatibility.
				Add ControlReqResult and ControlReqStatus to sheSystemConfigLogControl. 
				Correct SheSystemDnsServerNameControlRequestType."
			REVISION "200612061203Z"		-- December 06, 2006 at 12:03 GMT
			DESCRIPTION 
				"Add group sheSystemAutoConfigBackup for backward compatibility. Will not be supported by R2.5."
			REVISION "200701120952Z"		-- January 12, 2007 at 09:52 GMT
			DESCRIPTION 
				"Add new system-version string."
			REVISION "200703301055Z"		-- March 30, 2007 at 10:55 GMT
			DESCRIPTION 
				"Add new system-version string for R2.5.2.
				Add new tables for configuration of IP host and static routes
				via snmp."
			REVISION "200704161524Z"		-- April 16, 2007 at 15:24 GMT
			DESCRIPTION 
				"Expand sheSystemFileControlTypeOfFile for alarmLog and uptimeLog."
			REVISION "200704251330Z"		-- April 25, 2007 at 13:30 GMT
			DESCRIPTION 
				"Modify SheSystemIpHostTable after late review comment."
			REVISION "200705111256Z"		-- May 11, 2007 at 12:56 GMT
			DESCRIPTION 
				"Modify sheSystemIpHostTable and change ..Usage attribute to ..Description."
			REVISION "200705241036Z"		-- May 24, 2007 at 10:36 GMT
			DESCRIPTION 
				"Remove index limits for IpHost- and IpRoute-table."
			REVISION "200706111601Z"		-- June 11, 2007 at 16:01 GMT
			DESCRIPTION 
				"Replace system-version string R2.5.2 with R2.6."
			REVISION "200708151046Z"		-- August 15, 2007 at 10:46 GMT
			DESCRIPTION 
				"Modify unit and range for sheSystemNtpClientXmitInterval and sheSystemNtpClientControlXmitInterval."
			REVISION "200710161349Z"		-- October 16, 2007 at 13:49 GMT
			DESCRIPTION 
				"Add new system version R2.7 and R2.8."
			REVISION "200711141534Z"		-- November 14, 2007 at 15:34 GMT
			DESCRIPTION 
				"Add new system version hiX5622/R1.0.
				Modify comment for sheSystemIpHostUseDhcp."
			REVISION "200711271040Z"		-- November 27, 2007 at 10:40 GMT
			DESCRIPTION 
				"Add systemversion string for R3.0."
			REVISION "200712051242Z"		-- December 05, 2007 at 12:42 GMT
			DESCRIPTION 
				"Add metric parameter to interface route table (CO hiX13598)."
			REVISION "200802221125Z"		-- February 22, 2008 at 11:25 GMT
			DESCRIPTION 
				"Correct missing Object list for swm externalFtpAccessAlarm."
			REVISION "200804091448Z"		-- April 09, 2008 at 14:48 GMT
			DESCRIPTION 
				"Expand valid range for TimeZone configuration."
			REVISION "200805141009Z"		-- May 14, 2008 at 10:09 GMT
			DESCRIPTION 
				"Add new system version string for R2.6S2, R2.7M and R2.8M."
			REVISION "200805281534Z"		-- May 28, 2008 at 15:34 GMT
			DESCRIPTION 
				"Modify valid values for Timezone configuration."
			REVISION "200806111116Z"		-- June 11, 2008 at 11:16 GMT
			DESCRIPTION 
				"Support new file request type for upload of all available inventory records."
			REVISION "200806301036Z"		-- June 30, 2008 at 10:36 GMT
			DESCRIPTION 
				"Add new system versions for feature specific versions of R2.7M."
			REVISION "200807231607Z"		-- July 23, 2008 at 16:07 GMT
			DESCRIPTION 
				"Add systemSwmCurrentStatus with changed and alarm trap."
			REVISION "200810221620Z"		-- October 22, 2008 at 16:20 GMT
			DESCRIPTION 
				"Add new sytem versions represented by new shelftypes.
				Modify enum definition for SheSystemSwmCurrentStatusType."
			REVISION "200901211308Z"		-- January 21, 2009 at 13:08 GMT
			DESCRIPTION 
				"Update systemversion information."
			REVISION "200902041046Z"		-- February 04, 2009 at 10:46 GMT
			DESCRIPTION 
				"New parameter in sheSystemIpHostTable for .1p confoguration of the used vlan's."
			::= { she 2 }

		
	
--
-- Type definitions
--
	
--  --------------------------------------------------------------
-- Commands
-- --------------------------------------------------------------
-- This type specifies the user commands (control requests) for
-- system maintenance from the TMN-OS or LCT.
		SheSystemMaintenanceControlReq ::= INTEGER
			{
			noRequest(1),
			setSystemMaintenanceBase(50),
			setSwmAdminState(51),
			swmUpgrStartRequest(100),
			swmUpgrStartRequestNoReset(101),
			swmReadSAPSContentFile(102),
			backupDb(200),
			refreshDbBackupFilesTable(201),
			dbReloadSpecificFile(202),
			setBackupPeriod(203),
			setLocalBackupAdminState(204),
			setRemoteBackupAdminState(205)
			}

--  --------------------------------------------------------------
-- Result
-- --------------------------------------------------------------
-- This type specifies the command results (controlReqResult) 
-- for the system maintenance to TMN-OS or LCT.
-- 
		SheSystemMaintenanceControlReqResult ::= INTEGER
			{
			noRequest(1),
			ftpIpAddrFailed(11),
			ftpAccountFailed(12),
			ftpPasswdFailed(13),
			ftpDescPathFailed(14),
			commExecStarted(30),
			paramFaulty(31),
			requestBusy(32),
			setDataFailed(34),
			aswTimeout(35),
			commandFailed(36),
			commandSucceeded(37),
			sucUpgrTaskCreationFault(51),
			sucUpgrDbAccessFault(52),
			sucUpgrMissParameter(54),
			sucAlreadyLoaded(55),
			sucOk(60),
			sucNotOk(61),
			sucDbAccessFailed(62),
			sucCardUnlocked(63),
			sucTransmissionError(64),
			sucWrongSwVersion(65),
			sucUnitTypeMismatch(66),
			sucFtpTransError(67),
			sucFtpCrcError(68),
			sucSwHwMismatch(69),
			sucUpgrWrongAvState(70),
			sucFepromCopyFault(71),
			sucUpdateDescFileFailed(72),
			sucFtpServerNoteAvailable(73),
			sucFtpSendError(74),
			sucDbBackupFault(75),
			sucUpgradeComplete(76),
			sucUpgradeNotComplete(77),
			sutInitialized(100),
			sutToDo(101),
			sutStarted(102),
			sutCrashed(103),
			sutFtpDone(104),
			sutDone(105),
			sutReadyForReset(106),
			sutObsolete(107),
			sutResetInProgress(108),
			localBackupOk(150),
			remoteBackupOk(151),
			localBackupFailed(152),
			remoteBackupFailed(153),
			flashAccessFailed(154),
			dbReadFailed(155),
			dbmLocalBackupOk(170),
			dbmRemoteBackupOk(171),
			dbmLocalBackupFailed(172),
			dbmRemoteBackupFailed(173),
			dbmFlashAccessFailed(174),
			dbmDbReadFailed(175),
			dbmLocalBackupFileFaulty(176),
			dbmRemoteBackupFileFaulty(177),
			dbmRestoreFailed(178),
			dbmRestoreOk(179),
			dbmRefreshFailed(180),
			dbmRefreshOk(181)
			}

--  The administrative state of an entity.
		SheSystemAdminState ::= INTEGER
			{
			unlocked(1),
			locked(2)
			}

		SheSystemIpControlReqType ::= INTEGER
			{
			createSystemIpHost(50),
			deleteSystemIpHost(51),
			modifySystemIpHost(52),
			createSystemIpRoute(55),
			deleteSystemIpRoute(56),
			modifySystemIpRoute(57)
			}

--  The current status of an sw maintenance part.
		SheSystemSwmCurrentStatusType ::= INTEGER
			{
			passive(1),
			started(2),
			active(3)
			}

	
--
-- Textual conventions
--
	
--  Textual conventions
-- 
-- type of startup                    
		SheSystemStartupType ::= TEXTUAL-CONVENTION
			STATUS current
			DESCRIPTION 
				"The startup type."
			SYNTAX INTEGER
				{
				resetSystem(1),
				resetSystemWithDefault(2)
				}

--   -----------------------------------------------------------------
-- Textual Conventions
-- -----------------------------------------------------------------
		SheSystemTmnConnectedType ::= TEXTUAL-CONVENTION
			STATUS current
			DESCRIPTION 
				" TMN Connected type."
			SYNTAX INTEGER
				{
				connected(1),
				disconnected(2)
				}

		SheSystemControlRequestType ::= TEXTUAL-CONVENTION
			STATUS current
			DESCRIPTION 
				"The type for system control commands."
			SYNTAX INTEGER
				{
				configureTime(1),
				tmnConnect(2),
				tmnDisconnect(3),
				lctConnect(4),
				lctDisconnect(5),
				writeDatatoFlash(6),
				configureTimeZone(7),
				setCPUThreshold(8),
				setMemoryThreshold(9)
				}

--   GENERAL VALUES FOR USER COMMAND HANDLING
-- RETURN VALUES
		SheSystemControlRequestResultType ::= TEXTUAL-CONVENTION
			STATUS current
			DESCRIPTION 
				"The result type for system control commands."
			SYNTAX INTEGER
				{
				commExecStarted(30),
				paramFaulty(31),
				requestBusy(32),
				setDataFailed(34),
				aswTimeout(35),
				commandFailed(36),
				commandSucceeded(37),
				featureNotSupportedbyRelease(41)
				}

--   type of threshold interval
		SheSystemThresholdIntervalType ::= TEXTUAL-CONVENTION
			STATUS current
			DESCRIPTION 
				"The sampling interval for system threshold"
			SYNTAX INTEGER
				{
				sec5(1),
				sec60(2),
				sec600(3)
				}

--   return values to be defined
-- GENERAL VALUES FOR USER COMMAND HANDLING
-- RETURN VALUES
		SheSystemFileControlRequestType ::= TEXTUAL-CONVENTION
			STATUS current
			DESCRIPTION 
				"The type for file  control commands."
			SYNTAX INTEGER
				{
				upload(1),
				download(2),
				uploadCardsAllOfType(3),
				downloadCardsAllOfType(4),
				uploadAllOfSystem(5)
				}

-- GENERAL VALUES FOR USER COMMAND HANDLING RETURN VALUES
		SheSystemFileControlRequestResultType ::= TEXTUAL-CONVENTION
			STATUS current
			DESCRIPTION 
				"The result type for file  control commands."
			SYNTAX INTEGER
				{
				ftpError(10),
				ftpIpAddrFailed(11),
				ftpAccountFailed(12),
				ftpPasswdFailed(13),
				ftpDescPathFailed(14),
				swLoadPromotionFailed(20),
				commExecStarted(30),
				paramFaulty(31),
				requestBusy(32),
				setDataFailed(34),
				aswTimeout(35),
				commandFailed(36),
				commandSucceeded(37)
				}

-- Type definition for file management
		SheSystemTypeOfFile ::= TEXTUAL-CONVENTION
			STATUS current
			DESCRIPTION 
				"The type of files which can be managed."
			SYNTAX INTEGER
				{
				storedLoad(1),
				errorLog(2),
				restoreFile(3),
				remoteInventory(4),
				performanceData(5),
				alarmLog(6),
				uptimeLog(7)
				}

--   the load status type       
		SheSystemFileLoadStatusType ::= TEXTUAL-CONVENTION
			STATUS current
			DESCRIPTION 
				"The load status type."
			SYNTAX INTEGER
				{
				finished(1),
				running(2),
				broken(3)
				}

--  return values to be defined
-- GENERAL VALUES FOR USER COMMAND HANDLING
-- RETURN VALUES
		SheSystemNtpClientControlRequestType ::= TEXTUAL-CONVENTION
			STATUS current
			DESCRIPTION 
				"The type for NtpClient control commands."
			SYNTAX INTEGER
				{
				enableNtpClient(1),
				disableNtpClient(2),
				changeNtpClientXmitInterval(3),
				addNtpClientServerName(4),
				deleteNtpClientServerName(5)
				}

--   GENERAL VALUES FOR USER COMMAND HANDLING
-- RETURN VALUES
		SheSystemNtpClientControlRequestResultType ::= TEXTUAL-CONVENTION
			STATUS current
			DESCRIPTION 
				"The result type for file  control commands."
			SYNTAX INTEGER
				{
				noRequest(1),
				commExecStarted(30),
				paramFaulty(31),
				requestBusy(32),
				setDataFailed(34),
				aswTimeout(35),
				commandFailed(36),
				commandSucceeded(37),
				ntpClientEnableErr(50),
				ntpClientDisableErr(51),
				ntpClientChangeXmitIntervalErr(52),
				ntpClientServerNameAddErr(53),
				ntpClientServerNameDelErr(54)
				}

--  return values to be defined
-- GENERAL VALUES FOR USER COMMAND HANDLING
-- RETURN VALUES
		SheSystemDnsServerControlRequestType ::= TEXTUAL-CONVENTION
			STATUS current
			DESCRIPTION 
				"The type for DNS Server control commands."
			SYNTAX INTEGER
				{
				addedDnsServerName(1),
				deletedDnsServerName(2)
				}

--   GENERAL VALUES FOR USER COMMAND HANDLING
-- RETURN VALUES
		SheSystemDnsServerControlRequestResultType ::= TEXTUAL-CONVENTION
			STATUS current
			DESCRIPTION 
				"The result type for file  control commands."
			SYNTAX INTEGER
				{
				noRequest(1),
				commExecStarted(30),
				paramFaulty(31),
				requestBusy(32),
				setDataFailed(34),
				aswTimeout(35),
				commandFailed(36),
				commandSucceeded(37),
				dnsServerIpAddErr(60),
				dnsServerIpDelErr(61)
				}

--   type of Management Session                               
		SheSystemManagementSessionType ::= TEXTUAL-CONVENTION
			STATUS current
			DESCRIPTION 
				"Management Session Type."
			SYNTAX INTEGER
				{
				telnet(1),
				snmp(2),
				ssh(3)
				}

--   ManagementSessionControl Request
		SheSystemManagementSessionControlRequestType ::= TEXTUAL-CONVENTION
			STATUS current
			DESCRIPTION 
				"Management Session global user commands."
			SYNTAX INTEGER { setSnmpSessionAgingTime(1) }

--   GENERAL VALUES FOR USER COMMAND HANDLING
-- ManagementSessionControl Return values
		SheSystemManagementSessionControlReqResultType ::= TEXTUAL-CONVENTION
			STATUS current
			DESCRIPTION 
				"The result type for Management Session control commands."
			SYNTAX INTEGER
				{
				noRequest(1),
				commExecStarted(30),
				paramFaulty(31),
				requestBusy(32),
				setDataFailed(34),
				aswTimeout(35),
				commandFailed(36),
				commandSucceeded(37),
				setAgingTimeFailed(60)
				}

--   ConfigLogControl Request
		SheSystemConfigLogControlRequestType ::= TEXTUAL-CONVENTION
			STATUS current
			DESCRIPTION 
				"Config Log control commands."
			SYNTAX INTEGER
				{
				setConfigLogEntryNumber(1),
				setFtpAccount(2),
				setFtpInterval(3)
				}

--   AutoConfigBackupControl Request
		SheSystemAutoConfigBackupControlRequest ::= TEXTUAL-CONVENTION
			STATUS current
			DESCRIPTION 
				"AutoConfig Backup control commands."
			SYNTAX INTEGER
				{
				setAutoConfigBackupEnabled(1),
				setFtpAccount(2),
				setBackupTimerval(3)
				}

--   type of active load                               
		SheSystemLoadType ::= TEXTUAL-CONVENTION
			STATUS current
			DESCRIPTION 
				"The load type."
			SYNTAX INTEGER
				{
				active(1),
				passive(2)
				}

		SheSystemStartupResultType ::= TEXTUAL-CONVENTION
			STATUS current
			DESCRIPTION 
				"Result of the last NE startup. "
			SYNTAX INTEGER
				{
				startupInProgress(1),
				startupFailed(2),
				startupFinished(3)
				}

		SheSystemIpHostUseDhcpType ::= TEXTUAL-CONVENTION
			STATUS current
			DESCRIPTION 
				"Either use DHCP or fixed IP address."
			SYNTAX INTEGER
				{
				noUseDhcp(0),
				useDhcp(1)
				}

	
--
-- Node definitions
--
	
--  Node definitions
-- 
-- MIB contains the following groups
-- 1.3.6.1.4.1.231.7.1.2.2.1.2.1
		sheSystemInfo OBJECT IDENTIFIER ::= { sheSystem 1 }

		
--   -----------------------------------------------------------------
-- System general information group
-- -----------------------------------------------------------------
-- 1.3.6.1.4.1.231.7.1.2.2.1.2.1.1
		sheSystemVersion OBJECT-TYPE
			SYNTAX DisplayString
			MAX-ACCESS read-only
			STATUS current
			DESCRIPTION
				"Contains the version of the net element. The selected version depending on the used CXU SW
				release and detected shelf type of the running NE!!
				hiX5625/R2.5 
				hiX5630/R2.5 
				hiX5635/R2.5 
				hiX5625/R2.5.1 
				hiX5630/R2.5.1 
				hiX5635/R2.5.1 
				hiX5625/R2.6 
				hiX5630/R2.6 
				hiX5635/R2.6
				hiX5625/R2.7 
				hiX5630/R2.7 
				hiX5635/R2.7
				hiX5625/R2.8 
				hiX5630/R2.8 
				hiX5635/R2.8
				hiX5625/R2.6S2 
				hiX5630/R2.6S2 
				hiX5635/R2.6S2
				hiX5625/R2.7MH (support H248) 
				hiX5630/R2.7MH (support H248) 
				hiX5635/R2.7MH (support H248)
				hiX5625/R2.7MS (support SIP)
				hiX5630/R2.7MS (support SIP) 
				hiX5635/R2.7MS (support SIP)
				hiX5625/R2.8M 
				hiX5630/R2.8M
				hiX5635/R2.8M
				hiX5622/R2.8 
				hiX5608/R1.0
				
				
				The used shelftype could be retrieved from shePhysShelfTable.
				Systemversion     -> possible Shelftypes
				SHE hiX5635       -> M1200:E, M1100:E, G1100:E, G1100:B:E, G1100:A
				SHE hiX5630       -> M600:E, G600:E, G600:R:E, M600:DF:E
				SHE hiX5625       -> M400:E, G400:E, G400:R:A, 
				SHE hiX5622 R1.0  -> MDUS:E (obsolete)
				SHE hiX5608 R1.0  -> empty string because no shelf is used, single box system
				
				Shelftype's 2 generation - only new 2G powermodules could be used!  (>= with R2.8 maintenance)
				SHE hiX5635   -> G1100:2G:E, M1100:2G:E
				SHE hiX5630   -> G600:2G:E, G600:R:2G:E, 
				SHE hiX5625   -> G400:2G:E, G400:R:2G:A, 
				SHE hiX5622   -> G200:2G:E"
			::= { sheSystemInfo 1 }

		
--   seabrigde has several flags in the system mib:
-- systemState : normal, upgrade
-- systemUpgradeState : upgrade-preparation, idle, ready-for-switchover
-- 1.3.6.1.4.1.231.7.1.2.2.1.2.1.2
		sheSystemExternalTime OBJECT-TYPE
			SYNTAX TimeTicks
			MAX-ACCESS read-only
			STATUS current
			DESCRIPTION
				"The external time of the net element (UTC).
				The TMN-OS should set this time after first time power up or system resets
				and should refresh it once a day. "
			::= { sheSystemInfo 2 }

		
--  1.3.6.1.4.1.231.7.1.2.2.1.2.1.3
		sheSystemStartupType OBJECT-TYPE
			SYNTAX SheSystemStartupType
			MAX-ACCESS read-only
			STATUS current
			DESCRIPTION
				" Startup type: 
				1..resetSystem
				2..resetSystemWithDefault
				"
			::= { sheSystemInfo 3 }

		
--  1.3.6.1.4.1.231.7.1.2.2.1.2.1.4
		sheSystemTmnConnected OBJECT-TYPE
			SYNTAX SheSystemTmnConnectedType
			MAX-ACCESS read-only
			STATUS current
			DESCRIPTION
				"  The value connected indicates that a manager has received 
				the trap sheSytemStartupEnd and has connected. "
			::= { sheSystemInfo 4 }

		
--  1.3.6.1.4.1.231.7.1.2.2.1.2.1.5
		sheSystemLctConnected OBJECT-TYPE
			SYNTAX SheSystemTmnConnectedType
			MAX-ACCESS read-only
			STATUS current
			DESCRIPTION
				"  The value connected indicates that a manager has connected as LCT. 
				SHE sends the trap sheSystemLctConnected to all known
				TMN systems to inform whether the LCT session has been setup or terminated. "
			::= { sheSystemInfo 5 }

		
--   -----------------------------------------------------------------
-- System feature capability table
-- -----------------------------------------------------------------
-- 1.3.6.1.4.1.231.7.1.2.2.1.2.1.6
		sheSystemFeatureCapabilityTable OBJECT-TYPE
			SYNTAX SEQUENCE OF SheSystemFeatureCapabilityEntry
			MAX-ACCESS not-accessible
			STATUS current
			DESCRIPTION
				" The alarm severity table.
				The alarm severity table associates
				profile index and AlarmID pairs with severities to be
				used for alarm traps.
				(Note that this table does not apply to cleared alarms). "
			::= { sheSystemInfo 6 }

		
--  1.3.6.1.4.1.231.7.1.2.2.1.2.1.6.1
		sheSystemFeatureCapabilityEntry OBJECT-TYPE
			SYNTAX SheSystemFeatureCapabilityEntry
			MAX-ACCESS not-accessible
			STATUS current
			DESCRIPTION
				" Entry of the sheSystemFeatureCapabilityTable. "
			INDEX { sheSystemFeatureIndex }
			::= { sheSystemFeatureCapabilityTable 1 }

		
		SheSystemFeatureCapabilityEntry ::=
			SEQUENCE { 
				sheSystemFeatureIndex
					Unsigned32,
				sheSystemFeatureName
					DisplayString
			 }

--  1.3.6.1.4.1.231.7.1.2.2.1.2.1.6.1.1
		sheSystemFeatureIndex OBJECT-TYPE
			SYNTAX Unsigned32 (1..65535)
			MAX-ACCESS read-only
			STATUS current
			DESCRIPTION
				" The system feature index. "
			::= { sheSystemFeatureCapabilityEntry 1 }

		
--  1.3.6.1.4.1.231.7.1.2.2.1.2.1.6.1.2
		sheSystemFeatureName OBJECT-TYPE
			SYNTAX DisplayString
			MAX-ACCESS read-only
			STATUS current
			DESCRIPTION
				" The system feature name. "
			::= { sheSystemFeatureCapabilityEntry 2 }

		
--   -----------------------------------------------------------------
-- System control group
-- -----------------------------------------------------------------
-- 1.3.6.1.4.1.231.7.1.2.2.1.2.1.7
		sheSystemControl OBJECT IDENTIFIER ::= { sheSystemInfo 7 }

		
--  1.3.6.1.4.1.231.7.1.2.2.1.2.1.7.1
		sheSystemControlRequest OBJECT-TYPE
			SYNTAX SheSystemControlRequestType
			MAX-ACCESS read-write
			STATUS current
			DESCRIPTION
				"  System commands :
				configureTime : 
				   The command to configure the external time.
				tmnConnect :
				    the command for a manager to connect in order to be allowed
				    to manage the SHE and to stop the NE sending the sheSystemStartupEnd trap.
				tmnDisconnect:
				    the command for a TMN to disconnect from the NE. 
				lctConnect :
				    the command for a manager to connect as a LCT.
				    The SHE then sends the sheSystemLctSession trap.
				lctDisconnect:
				    the command for a LCT to disconnect from the NE.
				    The SHE then sends the sheSystemLctSession trap. 
				    If a LCT does not disconnect a LCT session is automatically
				    disconnected by the SHE after a internal timer expired.
				writeDatatoFlash:
				    the command to start writing configuration data of all subsystems
				    to flash-memory (long running command).
				configureTimeZone:
				    the command to change the current timezone.
				setCPUThreshold:
					the command to configure the threshold that
					when CPU usage exceeds the certain limit, notification is sent.
				setMemoryThreshold:
					the command to configure the threshold that
					when Memory usage exceeds the certain limit, notification is sent.
				Notifications : 
				    sheSystemStartupEnd, sheSystemLctSession, sheSystemWriteDatatoFlashFinished,
				    sheSystemChangedCPULoadThreshold, sheSystemChangedMemoryThreshold.
				"
			::= { sheSystemControl 1 }

		
--  1.3.6.1.4.1.231.7.1.2.2.1.2.1.7.2
		sheSystemControlStatus OBJECT-TYPE
			SYNTAX SheControlStatusType
			MAX-ACCESS read-only
			STATUS current
			DESCRIPTION
				" The status of a control request. "
			::= { sheSystemControl 2 }

		
--  1.3.6.1.4.1.231.7.1.2.2.1.2.1.7.3
		sheSystemControlTimer OBJECT-TYPE
			SYNTAX Unsigned32
			MAX-ACCESS read-only
			STATUS current
			DESCRIPTION
				" The maximum wait time for the manager for command ending.
				For long running commands.
				The manager reads this value from the SHE. "
			::= { sheSystemControl 3 }

		
--  1.3.6.1.4.1.231.7.1.2.2.1.2.1.7.4
		sheSystemControlReqResult OBJECT-TYPE
			SYNTAX SheSystemControlRequestResultType
			MAX-ACCESS read-only
			STATUS current
			DESCRIPTION
				" The result of the last user command. "
			::= { sheSystemControl 4 }

		
--  1.3.6.1.4.1.231.7.1.2.2.1.2.1.7.5
		sheSystemControlTimeStamp OBJECT-TYPE
			SYNTAX Unsigned32
			UNITS "sec"
			MAX-ACCESS read-only
			STATUS current
			DESCRIPTION
				" The time stamp of the last command (end of command). "
			::= { sheSystemControl 5 }

		
--  1.3.6.1.4.1.231.7.1.2.2.1.2.1.7.6
		sheSystemControlExternalTime OBJECT-TYPE
			SYNTAX TimeTicks
			MAX-ACCESS read-write
			STATUS current
			DESCRIPTION
				"The external time of the net element (UTC).
				The manager should set this time after first time power up or resetSystem
				and should refresh it once a day. "
			::= { sheSystemControl 6 }

		
--  1.3.6.1.4.1.231.7.1.2.2.1.2.1.7.7
		sheSystemControlTimeZone OBJECT-TYPE
			SYNTAX OCTET STRING (SIZE (0..16))
			MAX-ACCESS read-write
			STATUS current
			DESCRIPTION
				"The Time Zone of the net element.
				The TMN-OS should set this time zone in front of the NE's external time. 
				UTC,
				UTC+1,
				UTC+2,
				UTC+3,
				UTC+3.30,
				UTC+4,
				UTC+4.30,
				UTC+5,
				UTC+5.30,
				UTC+5.45,
				UTC+6,
				UTC+6.30,
				UTC+7,
				UTC+8,
				UTC+8.45,
				UTC+9,
				UTC+9.30,
				UTC+10,
				UTC+10.30,
				UTC+11,
				UTC+11.30,
				UTC+12,
				UTC+12.45,
				UTC+13,
				UTC+14,
				UTC-1,
				UTC-2,
				UTC-2.30,
				UTC-3,
				UTC-3.30,
				UTC-4,
				UTC-4.30,
				UTC-5,
				UTC-6,
				UTC-7,
				UTC-8,
				UTC-9,
				UTC-9.30,
				UTC-10,
				UTC-11,
				UTC-12,
				
				An automatic DST (dayligth saving time) switchover is not supported by the NE!!"
			::= { sheSystemControl 7 }

		
--  1.3.6.1.4.1.231.7.1.2.2.1.2.1.7.8
		sheSystemControlCPUThreshold OBJECT-TYPE
			SYNTAX Integer32 (20..100)
			UNITS "%"
			MAX-ACCESS read-write
			STATUS current
			DESCRIPTION
				" The CPU Load Threshold of System.
				The manager should set this threshold about CPU Load. "
			::= { sheSystemControl 8 }

		
--  1.3.6.1.4.1.231.7.1.2.2.1.2.1.7.9
		sheSystemControlCPUThresholdInterval OBJECT-TYPE
			SYNTAX SheSystemThresholdIntervalType
			MAX-ACCESS read-write
			STATUS current
			DESCRIPTION
				" The sampling interval for CPU threshold.
				Average CPU usage is checked on every interval configured. "
			::= { sheSystemControl 9 }

		
--  1.3.6.1.4.1.231.7.1.2.2.1.2.1.7.10
		sheSystemControlMemoryThreshold OBJECT-TYPE
			SYNTAX Integer32
			UNITS "kBytes"
			MAX-ACCESS read-write
			STATUS current
			DESCRIPTION
				" The Memory Usage Threshold of System.
				The manager should set this threshold about Memory usage. "
			::= { sheSystemControl 10 }

		
--  1.3.6.1.4.1.231.7.1.2.2.1.2.1.7.11
		sheSystemControlMemoryThresholdInterval OBJECT-TYPE
			SYNTAX SheSystemThresholdIntervalType
			MAX-ACCESS read-write
			STATUS current
			DESCRIPTION
				" The sampling interval for CPU threshold.
				Memory usage is checked on every interval configured. "
			::= { sheSystemControl 11 }

		
--  1.3.6.1.4.1.231.7.1.2.2.1.2.1.8
		sheSystemTimeZone OBJECT-TYPE
			SYNTAX OCTET STRING (SIZE (0..16))
			MAX-ACCESS read-only
			STATUS current
			DESCRIPTION
				"The Time Zone of the net element.
				The TMN-OS should set this time zone in front of the NE's external time. 
				UTC,
				UTC+1,
				UTC+2,
				UTC+3,
				UTC+3.30,
				UTC+4,
				UTC+4.30,
				UTC+5,
				UTC+5.30,
				UTC+5.45,
				UTC+6,
				UTC+6.30,
				UTC+7,
				UTC+8,
				UTC+8.45,
				UTC+9,
				UTC+9.30,
				UTC+10,
				UTC+10.30,
				UTC+11,
				UTC+11.30,
				UTC+12,
				UTC+12.45,
				UTC+13,
				UTC+14,
				UTC-1,
				UTC-2,
				UTC-2.30,
				UTC-3,
				UTC-3.30,
				UTC-4,
				UTC-4.30,
				UTC-5,
				UTC-6,
				UTC-7,
				UTC-8,
				UTC-9,
				UTC-9.30,
				UTC-10,
				UTC-11,
				UTC-12,
				
				An automatic DST (dayligth saving time) switchover is not supported by the NE!!"
			::= { sheSystemInfo 8 }

		
--  1.3.6.1.4.1.231.7.1.2.2.1.2.1.9
		sheSystem5SecCPULoad OBJECT-TYPE
			SYNTAX Integer32
			UNITS "%"
			MAX-ACCESS read-only
			STATUS current
			DESCRIPTION
				"  The Avg. Value of CPU Load for 5 seconds. "
			::= { sheSystemInfo 9 }

		
--  1.3.6.1.4.1.231.7.1.2.2.1.2.1.10
		sheSystem1MinCPULoad OBJECT-TYPE
			SYNTAX Integer32
			UNITS "%"
			MAX-ACCESS read-only
			STATUS current
			DESCRIPTION
				"  The Avg. Value of CPU Load for 1 minute. "
			::= { sheSystemInfo 10 }

		
--  1.3.6.1.4.1.231.7.1.2.2.1.2.1.11
		sheSystem10MinCPULoad OBJECT-TYPE
			SYNTAX Integer32
			UNITS "%"
			MAX-ACCESS read-only
			STATUS current
			DESCRIPTION
				"  The Avg. Value of CPU Load for 1p minutes. "
			::= { sheSystemInfo 11 }

		
--  1.3.6.1.4.1.231.7.1.2.2.1.2.1.12
		sheSystemCPULoadThreshold OBJECT-TYPE
			SYNTAX Integer32 (20..100)
			UNITS "%"
			MAX-ACCESS read-only
			STATUS current
			DESCRIPTION
				"  The threshold of CPU Load. "
			DEFVAL { 50 }
			::= { sheSystemInfo 12 }

		
--  1.3.6.1.4.1.231.7.1.2.2.1.2.1.13
		sheSystemCPULoadThresholdInterval OBJECT-TYPE
			SYNTAX SheSystemThresholdIntervalType
			MAX-ACCESS read-only
			STATUS current
			DESCRIPTION
				"  The sampling interval of CPU Load. "
			DEFVAL { sec60 }
			::= { sheSystemInfo 13 }

		
--  1.3.6.1.4.1.231.7.1.2.2.1.2.1.14
		sheSystemTotalMemory OBJECT-TYPE
			SYNTAX Integer32
			UNITS "kBytes"
			MAX-ACCESS read-only
			STATUS current
			DESCRIPTION
				"  The Total memory of system. "
			::= { sheSystemInfo 14 }

		
--  1.3.6.1.4.1.231.7.1.2.2.1.2.1.15
		sheSystemUsedMemory OBJECT-TYPE
			SYNTAX Integer32
			UNITS "kBytes"
			MAX-ACCESS read-only
			STATUS current
			DESCRIPTION
				"  The Used memory of system. "
			::= { sheSystemInfo 15 }

		
--  1.3.6.1.4.1.231.7.1.2.2.1.2.1.16
		sheSystemFreeMemory OBJECT-TYPE
			SYNTAX Integer32
			UNITS "kBytes"
			MAX-ACCESS read-only
			STATUS current
			DESCRIPTION
				"  The Free memory of system. "
			::= { sheSystemInfo 16 }

		
--  1.3.6.1.4.1.231.7.1.2.2.1.2.1.17
		sheSystemMemoryThreshold OBJECT-TYPE
			SYNTAX Integer32
			UNITS "kBytes"
			MAX-ACCESS read-only
			STATUS current
			DESCRIPTION
				"  The threshold of Memory Usage. "
			::= { sheSystemInfo 17 }

		
--  1.3.6.1.4.1.231.7.1.2.2.1.2.1.18
		sheSystemMemoryThresholdInterval OBJECT-TYPE
			SYNTAX SheSystemThresholdIntervalType
			MAX-ACCESS read-only
			STATUS current
			DESCRIPTION
				"  The sampling interval of Memory Usage. "
			DEFVAL { sec60 }
			::= { sheSystemInfo 18 }

		
--  1.3.6.1.4.1.231.7.1.2.2.1.2.1.19
		sheSystemBootloaderVersion OBJECT-TYPE
			SYNTAX DisplayString
			MAX-ACCESS read-only
			STATUS current
			DESCRIPTION
				" Contains the version of bootloader."
			::= { sheSystemInfo 19 }

		
--  1.3.6.1.4.1.231.7.1.2.2.1.2.1.20
		sheSystemCliConnected OBJECT-TYPE
			SYNTAX SheSystemTmnConnectedType
			MAX-ACCESS read-only
			STATUS current
			DESCRIPTION
				"The value connected indicates that a CLI session is active. 
				SHE sends the trap sheSystemCliConnected to all known
				TMN systems to inform whether the CLI session has been setup or terminated. "
			::= { sheSystemInfo 20 }

		
		sheSystemStartupResult OBJECT-TYPE
			SYNTAX SheSystemStartupResultType
			MAX-ACCESS read-only
			STATUS current
			DESCRIPTION
				"Result of the last NE startup .
				Values:
				startupInProgress(1),
				startupFailed(2),
				startupFinished(3)"
			::= { sheSystemInfo 21 }

		
--  1.3.6.1.4.1.231.7.1.2.2.1.2.2
		sheSystemFile OBJECT IDENTIFIER ::= { sheSystem 2 }

		
--   --------------------------------------------------------------
-- System file management control subgroup
-- --------------------------------------------------------------
-- 1.3.6.1.4.1.231.7.1.2.2.1.2.2.1
		sheSystemFileControl OBJECT IDENTIFIER ::= { sheSystemFile 1 }

		
--  1.3.6.1.4.1.231.7.1.2.2.1.2.2.1.1
		sheSystemFileControlRequest OBJECT-TYPE
			SYNTAX SheSystemFileControlRequestType
			MAX-ACCESS read-write
			STATUS current
			DESCRIPTION
				"File management commands :
				
				upload   : a file is uploaded to the FTP server from the SHE NE.
				download : a file is downloaded from a FTP server to the SHE NE.
				
				uploadCardsAllOfType   : upload for all cards af the same type.
				downloadCardsAllOfType : download for all cards af the same type.
				
				uploadAllOfSystem : Only for upload of all available remote inventory records!
				
				Parameters specify the type of file and the FTP server.
				
				downloads:
				- SW to a singleCard : commands to load a new load  
				- SW to all cards of a type
				- restoreFile (configuration files)
				
				uploads:
				- log files
				- restoreFile (congfiguration files)
				- remote inventory (also AllOfSystem)
				- performance data
				             
				Notifications : 
				   sheSystemFtp
				   sheSystemSwLoadPromoted                      
				
				Alarms:
				   sheSystemSwmFtpAccessError
				   sheSystemSwmFtpExternalAccessError     "
			::= { sheSystemFileControl 1 }

		
--  1.3.6.1.4.1.231.7.1.2.2.1.2.2.1.2
		sheSystemFileControlStatus OBJECT-TYPE
			SYNTAX SheControlStatusType
			MAX-ACCESS read-only
			STATUS current
			DESCRIPTION
				" The status of a control request. "
			::= { sheSystemFileControl 2 }

		
--  1.3.6.1.4.1.231.7.1.2.2.1.2.2.1.3
		sheSystemFileControlTimer OBJECT-TYPE
			SYNTAX Unsigned32
			MAX-ACCESS read-only
			STATUS current
			DESCRIPTION
				" The maximum wait time for the manager for command ending.
				For long running commands.
				The manager reads this value from the SHE. "
			::= { sheSystemFileControl 3 }

		
--  1.3.6.1.4.1.231.7.1.2.2.1.2.2.1.4
		sheSystemFileControlReqResult OBJECT-TYPE
			SYNTAX SheSystemFileControlRequestResultType
			MAX-ACCESS read-only
			STATUS current
			DESCRIPTION
				" The result of the last user command. "
			::= { sheSystemFileControl 4 }

		
--  1.3.6.1.4.1.231.7.1.2.2.1.2.2.1.5
		sheSystemFileControlTimeStamp OBJECT-TYPE
			SYNTAX Unsigned32
			UNITS "sec"
			MAX-ACCESS read-only
			STATUS current
			DESCRIPTION
				" The time stamp of the last command (end of command). "
			::= { sheSystemFileControl 5 }

		
--  1.3.6.1.4.1.231.7.1.2.2.1.2.2.1.6
		sheSystemFileControlTypeOfFile OBJECT-TYPE
			SYNTAX SheSystemTypeOfFile
			MAX-ACCESS read-write
			STATUS current
			DESCRIPTION
				" The file type definition:
				1..stored load,    (only download)
				2..error log,      (only upload)
				3..restoreFile     (both up/download)
				4..remoteInventory (only upload, AllOfSystem possible)
				5..performanceData (only upload)
				6..alarmLog        (only upload)
				7..uptimeLog       (only upload)
				"
			::= { sheSystemFileControl 6 }

		
--  1.3.6.1.4.1.231.7.1.2.2.1.2.2.1.7
		sheSystemFileControlPathName OBJECT-TYPE
			SYNTAX OCTET STRING (SIZE (0..128))
			MAX-ACCESS read-write
			STATUS current
			DESCRIPTION
				"Path name of file on FTP server. 
				This path should be set relative to the ftp-server root.
				Use only linux notation ( / ). 
				
				Spaces in pathnames are not allowed, because of possible problems with
				different FTP implementations (client and/or server)!!"
			::= { sheSystemFileControl 7 }

		
--  1.3.6.1.4.1.231.7.1.2.2.1.2.2.1.8
		sheSystemFileControlFileName OBJECT-TYPE
			SYNTAX OCTET STRING (SIZE (1..128))
			MAX-ACCESS read-write
			STATUS current
			DESCRIPTION
				" File name of file on FTP server. 
				Spaces in filenames are not allowed, because of possible problems with
				different FTP implementations (client and/or server)!!
				"
			::= { sheSystemFileControl 8 }

		
--  1.3.6.1.4.1.231.7.1.2.2.1.2.2.1.9
		sheSystemFileControlCardType OBJECT-TYPE
			SYNTAX SheCardType
			MAX-ACCESS read-write
			STATUS current
			DESCRIPTION
				" The card type to be upgraded. "
			::= { sheSystemFileControl 9 }

		
--  1.3.6.1.4.1.231.7.1.2.2.1.2.2.1.10
		sheSystemFileControlEntPhysicalIndex OBJECT-TYPE
			SYNTAX PhysicalIndex
			MAX-ACCESS read-write
			STATUS current
			DESCRIPTION
				" The entPhysicalIndex of the card to be loaded. "
			::= { sheSystemFileControl 10 }

		
--  1.3.6.1.4.1.231.7.1.2.2.1.2.2.1.12
		sheSystemFileControlLoadStatus OBJECT-TYPE
			SYNTAX SheSystemFileLoadStatusType
			MAX-ACCESS read-only
			STATUS current
			DESCRIPTION
				" Status of SHE download.                                              
				1..finished,                                                           
				2..running,                                                            
				3..broken,                                                             
				"
			::= { sheSystemFileControl 12 }

		
--  1.3.6.1.4.1.231.7.1.2.2.1.2.2.1.13
		sheSystemFileControlServerAddr OBJECT-TYPE
			SYNTAX OCTET STRING (SIZE (0..20))
			MAX-ACCESS read-write
			STATUS current
			DESCRIPTION
				" Address of FTP server (dotted notation).                               
				Attribute only valid in var bind list with correct sheSystemFileControlCommand.      
				Read-access will report an empty string."
			::= { sheSystemFileControl 13 }

		
--   read to this attribute will deliver 20 times sign '-'                         
-- 1.3.6.1.4.1.231.7.1.2.2.1.2.2.1.14
		sheSystemFileControlUsrName OBJECT-TYPE
			SYNTAX OCTET STRING (SIZE (0..20))
			MAX-ACCESS read-write
			STATUS current
			DESCRIPTION
				" Username for FTP access.                                                             
				Attribute only valid in var bind list with correct sheSystemFileControlCommand.
				Read-access will report an empty string. "
			::= { sheSystemFileControl 14 }

		
--   read to this attribute will deliver 20 times sign '-'                         
-- 1.3.6.1.4.1.231.7.1.2.2.1.2.2.1.15
		sheSystemFileControlPassword OBJECT-TYPE
			SYNTAX OCTET STRING (SIZE (0..20))
			MAX-ACCESS read-write
			STATUS current
			DESCRIPTION
				" Password for FTP access.                                                              
				Attribute only valid in var bind list with correct sheSystemFileControlCommand.
				Read-access will report an empty string. "
			::= { sheSystemFileControl 15 }

		
--   --------------------------------------------------------------
-- System file table 
-- --------------------------------------------------------------
-- 1.3.6.1.4.1.231.7.1.2.2.1.2.2.2
		sheSystemFileSwFileTable OBJECT-TYPE
			SYNTAX SEQUENCE OF SheSystemFileSwFileEntry
			MAX-ACCESS not-accessible
			STATUS current
			DESCRIPTION
				" File Table of SHE. 
				List of all files per card present on the SHE and their 
				counterpart on the FTP server
				
				Information about Primary and Secondary 
				loads is also found in this table. "
			::= { sheSystemFile 2 }

		
--  1.3.6.1.4.1.231.7.1.2.2.1.2.2.2.1
		sheSystemFileSwFileEntry OBJECT-TYPE
			SYNTAX SheSystemFileSwFileEntry
			MAX-ACCESS not-accessible
			STATUS current
			DESCRIPTION
				" An entry in the sheSystemFileSwTable.
				Notifications : none. "
			INDEX { entPhysicalIndex, sheSystemFileSwfIndex }
			::= { sheSystemFileSwFileTable 1 }

		
		SheSystemFileSwFileEntry ::=
			SEQUENCE { 
				sheSystemFileSwfIndex
					SheSystemFileIndexType,
				sheSystemFileSwfFileName
					OCTET STRING,
				sheSystemFileSwfTypeOfFile
					SheSystemTypeOfFile,
				sheSystemFileSwfVersion
					OCTET STRING,
				sheSystemFileSwfSize
					Integer32,
				sheSystemFileSwfTimeStamp
					Unsigned32
			 }

--  1.3.6.1.4.1.231.7.1.2.2.1.2.2.2.1.1
		sheSystemFileSwfIndex OBJECT-TYPE
			SYNTAX SheSystemFileIndexType
			MAX-ACCESS read-only
			STATUS current
			DESCRIPTION
				" Second Index of file table.  "
			::= { sheSystemFileSwFileEntry 1 }

		
--  1.3.6.1.4.1.231.7.1.2.2.1.2.2.2.1.2
		sheSystemFileSwfFileName OBJECT-TYPE
			SYNTAX OCTET STRING (SIZE (0..128))
			MAX-ACCESS read-only
			STATUS current
			DESCRIPTION
				" File name of file in SHE file system. "
			::= { sheSystemFileSwFileEntry 2 }

		
--  1.3.6.1.4.1.231.7.1.2.2.1.2.2.2.1.3
		sheSystemFileSwfTypeOfFile OBJECT-TYPE
			SYNTAX SheSystemTypeOfFile
			MAX-ACCESS read-only
			STATUS current
			DESCRIPTION
				" The file type definition: 
				1..stored load,    (only download) 
				2..error log,      (only upload)
				3..restoreFile     (both up/download)
				4..remoteInventory (only upload, AllOfSystem possible)
				5..performanceData (only upload)
				6..alarmLog        (only upload)
				7..uptimeLog       (only upload)"
			::= { sheSystemFileSwFileEntry 3 }

		
--  1.3.6.1.4.1.231.7.1.2.2.1.2.2.2.1.4
		sheSystemFileSwfVersion OBJECT-TYPE
			SYNTAX OCTET STRING (SIZE (0..20))
			MAX-ACCESS read-only
			STATUS current
			DESCRIPTION
				" File or software version of file in the SHE file system. "
			::= { sheSystemFileSwFileEntry 4 }

		
--  1.3.6.1.4.1.231.7.1.2.2.1.2.2.2.1.5
		sheSystemFileSwfSize OBJECT-TYPE
			SYNTAX Integer32
			MAX-ACCESS read-only
			STATUS current
			DESCRIPTION
				" Size of file in SHE file system. "
			::= { sheSystemFileSwFileEntry 5 }

		
--  1.3.6.1.4.1.231.7.1.2.2.1.2.2.2.1.6
		sheSystemFileSwfTimeStamp OBJECT-TYPE
			SYNTAX Unsigned32
			UNITS "sec"
			MAX-ACCESS read-only
			STATUS current
			DESCRIPTION
				" Time stamp of file in file system of SHE. 
				"
			::= { sheSystemFileSwFileEntry 6 }

		
--  1.3.6.1.4.1.231.7.1.2.2.1.2.3
		sheSystemNotifications OBJECT IDENTIFIER ::= { sheSystem 3 }

		
--   --------------------------------------------------------------
-- System notification subgroup
-- --------------------------------------------------------------
-- 1.3.6.1.4.1.231.7.1.2.2.1.2.3.1
		sheSystemEvents OBJECT IDENTIFIER ::= { sheSystemNotifications 1 }

		
--   Start up end event
-- 1.3.6.1.4.1.231.7.1.2.2.1.2.3.1.1
		sheSystemStartupEnd NOTIFICATION-TYPE
			OBJECTS { sheSystemExternalTime, sheSystemStartupType }
			STATUS current
			DESCRIPTION 
				" End of startup. "
			::= { sheSystemEvents 1 }

		
--  1.3.6.1.4.1.231.7.1.2.2.1.2.3.1.2
		sheSystemFtp NOTIFICATION-TYPE
			OBJECTS { sheSystemFileControlTimeStamp, sheSystemFileControlRequest, sheSystemFileControlTypeOfFile, sheSystemFileControlPathName, sheSystemFileControlFileName, 
				sheSystemFileControlEntPhysicalIndex, sheSystemFileControlLoadStatus, sheSystemFileControlReqResult }
			STATUS current
			DESCRIPTION 
				" Reports the result of a file up/download. 
				The sheSystemFileControlRequest reports either upload / download
				The sheSystemFileControlLoadStatus reports either 
				            finished / ongoing / broken.    
				"
			::= { sheSystemEvents 2 }

		
--  1.3.6.1.4.1.231.7.1.2.2.1.2.3.1.3
		sheSystemSwLoadPromoted NOTIFICATION-TYPE
			OBJECTS { sheSystemFileControlTimeStamp, entPhysicalIndex }
			STATUS current
			DESCRIPTION 
				" The upgraded load is promoted to be good/trusted. "
			::= { sheSystemEvents 3 }

		
--  1.3.6.1.4.1.231.7.1.2.2.1.2.3.1.4
		sheSystemSwLoadPromotionFailed NOTIFICATION-TYPE
			OBJECTS { sheSystemFileControlTimeStamp, entPhysicalIndex, sheSystemFileControlReqResult }
			STATUS current
			DESCRIPTION 
				" Sent when load promotion failed. 
				Card will restart with fallback load. The ReqResult should
				contain some detailed information about the error-reason (tbd.)."
			::= { sheSystemEvents 4 }

		
--   LCT connected event
-- 1.3.6.1.4.1.231.7.1.2.2.1.2.3.1.5
		sheSystemLctSession NOTIFICATION-TYPE
			OBJECTS { sheSystemExternalTime, sheSystemLctConnected }
			STATUS current
			DESCRIPTION 
				" A LCT session is connected or disconnected. "
			::= { sheSystemEvents 5 }

		
--  1.3.6.1.4.1.231.7.1.2.2.1.2.3.1.6
		sheSystemWriteDatatoFlashFinished NOTIFICATION-TYPE
			OBJECTS { sheSystemControlStatus, sheSystemControlReqResult, sheSystemControlTimeStamp }
			STATUS current
			DESCRIPTION 
				"Description."
			::= { sheSystemEvents 6 }

		
--  1.3.6.1.4.1.231.7.1.2.2.1.2.3.1.7
		sheSystemChangedCPULoadThreshold NOTIFICATION-TYPE
			OBJECTS { sheSystemControlStatus, sheSystemControlReqResult, sheSystemControlTimeStamp }
			STATUS current
			DESCRIPTION 
				"CPU Load Threshold change state by user."
			::= { sheSystemEvents 7 }

		
--  1.3.6.1.4.1.231.7.1.2.2.1.2.3.1.8
		sheSystemChangedMemoryThreshold NOTIFICATION-TYPE
			OBJECTS { sheSystemControlStatus, sheSystemControlReqResult, sheSystemControlTimeStamp }
			STATUS current
			DESCRIPTION 
				"Memory usage Threshold change state by user."
			::= { sheSystemEvents 8 }

		
		sheSystemCliSession NOTIFICATION-TYPE
			OBJECTS { sheSystemExternalTime, sheSystemCliConnected }
			STATUS current
			DESCRIPTION 
				" A CLI session is connected or disconnected. "
			::= { sheSystemEvents 9 }

		
--   -----------------------------------------------------------------  
-- 1.3.6.1.4.1.231.7.1.2.2.1.2.3.2
		sheSystemAlarms OBJECT IDENTIFIER ::= { sheSystemNotifications 2 }

		
--  1.3.6.1.4.1.231.7.1.2.2.1.2.3.2.1
		sheSystemCPULoadThresholdExceeded NOTIFICATION-TYPE
			OBJECTS { sheAlarmTimeAndDate, sheAlarmReportingSource, sheAlarmReportingSourceType, sheAlarmSeverity }
			STATUS current
			DESCRIPTION 
				"Measured CPU load has exceeded the threshold in the given measuring interval."
			::= { sheSystemAlarms 1 }

		
--  1.3.6.1.4.1.231.7.1.2.2.1.2.3.2.2
		sheSystemMemoryThresholdExceeded NOTIFICATION-TYPE
			OBJECTS { sheAlarmTimeAndDate, sheAlarmReportingSource, sheAlarmReportingSourceType, sheAlarmSeverity }
			STATUS current
			DESCRIPTION 
				"Measured memory usage has exceeded the threshold in the given measuring interval."
			::= { sheSystemAlarms 2 }

		
--  1.3.6.1.4.1.231.7.1.2.2.1.2.5
		sheSystemNtpClient OBJECT IDENTIFIER ::= { sheSystem 5 }

		
--   --------------------------------------------------------------
-- System NTP Client/Server table 
-- --------------------------------------------------------------
-- 1.3.6.1.4.1.231.7.1.2.2.1.2.5.1
		sheSystemNtpClientEnabled OBJECT-TYPE
			SYNTAX INTEGER
				{
				false(0),
				true(1)
				}
			MAX-ACCESS read-only
			STATUS current
			DESCRIPTION
				"NTP Client enable status."
			::= { sheSystemNtpClient 1 }

		
--  1.3.6.1.4.1.231.7.1.2.2.1.2.5.2
		sheSystemNtpClientXmitInterval OBJECT-TYPE
			SYNTAX Integer32 (1..2160)
			UNITS "hour"
			MAX-ACCESS read-only
			STATUS current
			DESCRIPTION
				"NTP Client transmit-packet interval to request time information from NTP server..
				Valid range is 1 hour up to 2160 hours (3 months).
				The default value should be 24 hours."
			::= { sheSystemNtpClient 2 }

		
--  1.3.6.1.4.1.231.7.1.2.2.1.2.5.3
		sheSystemNtpClientServerTable OBJECT-TYPE
			SYNTAX SEQUENCE OF SheSystemNtpClientServerEntry
			MAX-ACCESS not-accessible
			STATUS current
			DESCRIPTION
				" NTP Client server Table of SHE."
			::= { sheSystemNtpClient 3 }

		
--  1.3.6.1.4.1.231.7.1.2.2.1.2.5.3.1
		sheSystemNtpClientServerEntry OBJECT-TYPE
			SYNTAX SheSystemNtpClientServerEntry
			MAX-ACCESS not-accessible
			STATUS current
			DESCRIPTION
				" An entry in the sheSystemNtpClientTable.
				Notifications : none. "
			INDEX { sheSystemNtpClientServerIndex }
			::= { sheSystemNtpClientServerTable 1 }

		
		SheSystemNtpClientServerEntry ::=
			SEQUENCE { 
				sheSystemNtpClientServerIndex
					Integer32,
				sheSystemNtpClientServerName
					OCTET STRING
			 }

--  1.3.6.1.4.1.231.7.1.2.2.1.2.5.3.1.1
		sheSystemNtpClientServerIndex OBJECT-TYPE
			SYNTAX Integer32 (1..100)
			MAX-ACCESS read-only
			STATUS current
			DESCRIPTION
				" Index of file table.  "
			::= { sheSystemNtpClientServerEntry 1 }

		
--  1.3.6.1.4.1.231.7.1.2.2.1.2.5.3.1.2
		sheSystemNtpClientServerName OBJECT-TYPE
			SYNTAX OCTET STRING (SIZE (1..64))
			MAX-ACCESS read-only
			STATUS current
			DESCRIPTION
				" Server name of NTP Client in SHE NTP Client system. "
			::= { sheSystemNtpClientServerEntry 2 }

		
--   --------------------------------------------------------------
-- System NtpClient management control subgroup
-- --------------------------------------------------------------
-- 1.3.6.1.4.1.231.7.1.2.2.1.2.5.4
		sheSystemNtpClientControl OBJECT IDENTIFIER ::= { sheSystemNtpClient 4 }

		
--  1.3.6.1.4.1.231.7.1.2.2.1.2.5.4.1
		sheSystemNtpClientControlRequest OBJECT-TYPE
			SYNTAX SheSystemNtpClientControlRequestType
			MAX-ACCESS read-write
			STATUS current
			DESCRIPTION
				"  NtpClient management commands :
				
				enabledNtpClient   : NtpClient client is enabled by users.
				disabledNtpClient  : NtpClient client is disabled bu users
				
				changedNtpClientXmitInterval   : NtpClient transmit-packet interval is changed by users.
				
				addedNtpClientServerName : NtpClient source hostname is added into source list.
				deletedNtpClientServerName : NtpClient source hostname is deleted in source list.
				
				Notifications: ZZZZZZ
					        "
			::= { sheSystemNtpClientControl 1 }

		
--  1.3.6.1.4.1.231.7.1.2.2.1.2.5.4.2
		sheSystemNtpClientControlStatus OBJECT-TYPE
			SYNTAX SheControlStatusType
			MAX-ACCESS read-only
			STATUS current
			DESCRIPTION
				" The status of a control request. "
			::= { sheSystemNtpClientControl 2 }

		
--  1.3.6.1.4.1.231.7.1.2.2.1.2.5.4.3
		sheSystemNtpClientControlTimer OBJECT-TYPE
			SYNTAX Unsigned32
			MAX-ACCESS read-only
			STATUS current
			DESCRIPTION
				" The maximum wait time for the manager for command ending.
				For long running commands.
				The manager reads this value from the SHE. "
			::= { sheSystemNtpClientControl 3 }

		
--  1.3.6.1.4.1.231.7.1.2.2.1.2.5.4.4
		sheSystemNtpClientControlReqResult OBJECT-TYPE
			SYNTAX SheSystemNtpClientControlRequestResultType
			MAX-ACCESS read-only
			STATUS current
			DESCRIPTION
				" The result of the last user command. "
			::= { sheSystemNtpClientControl 4 }

		
--  1.3.6.1.4.1.231.7.1.2.2.1.2.5.4.5
		sheSystemNtpClientControlTimeStamp OBJECT-TYPE
			SYNTAX Unsigned32
			UNITS "sec"
			MAX-ACCESS read-only
			STATUS current
			DESCRIPTION
				" The time stamp of the last command (end of command). "
			::= { sheSystemNtpClientControl 5 }

		
--  1.3.6.1.4.1.231.7.1.2.2.1.2.5.4.6
		sheSystemNtpClientControlXmitInterval OBJECT-TYPE
			SYNTAX Integer32 (1..2160)
			UNITS "hour"
			MAX-ACCESS read-write
			STATUS current
			DESCRIPTION
				"Configure NTP Client transmit-packet interval to request time information from NTP server..
				Valid range is 1 hour up to 2160 hours (3 months).
				The default value should be 24 hours."
			::= { sheSystemNtpClientControl 6 }

		
--  1.3.6.1.4.1.231.7.1.2.2.1.2.5.4.7
		sheSystemNtpClientControlServername OBJECT-TYPE
			SYNTAX OCTET STRING (SIZE (0..32))
			MAX-ACCESS read-write
			STATUS current
			DESCRIPTION
				"NtpClient Source hostname or Ip address to get current time."
			::= { sheSystemNtpClientControl 7 }

		
--  1.3.6.1.4.1.231.7.1.2.2.1.2.5.4.7
		sheSystemNtpClientControlServerIndex OBJECT-TYPE
			SYNTAX Integer32 (1..100)
			MAX-ACCESS read-write
			STATUS current
			DESCRIPTION
				"Index of the addressed table entry."
			::= { sheSystemNtpClientControl 8 }

		
--   --------------------------------------------------------------
-- System NtpClient management notification subgroup
-- --------------------------------------------------------------
-- 1.3.6.1.4.1.231.7.1.2.2.1.2.5.5
		sheSystemNtpClientNotifications OBJECT IDENTIFIER ::= { sheSystemNtpClient 5 }

		
--  1.3.6.1.4.1.231.7.1.2.2.1.2.5.5.1
		sheSystemNtpClientEnable NOTIFICATION-TYPE
			OBJECTS { sheSystemNtpClientControlStatus, sheSystemNtpClientControlReqResult, sheSystemNtpClientControlTimeStamp }
			STATUS current
			DESCRIPTION 
				"Description."
			::= { sheSystemNtpClientNotifications 1 }

		
--  1.3.6.1.4.1.231.7.1.2.2.1.2.5.5.2
		sheSystemNtpClientDisable NOTIFICATION-TYPE
			OBJECTS { sheSystemNtpClientControlStatus, sheSystemNtpClientControlReqResult, sheSystemNtpClientControlTimeStamp }
			STATUS current
			DESCRIPTION 
				"Description."
			::= { sheSystemNtpClientNotifications 2 }

		
--  1.3.6.1.4.1.231.7.1.2.2.1.2.5.5.3
		sheSystemNtpClientChangeXmitInterval NOTIFICATION-TYPE
			OBJECTS { sheSystemNtpClientControlStatus, sheSystemNtpClientControlReqResult, sheSystemNtpClientControlTimeStamp, sheSystemNtpClientControlXmitInterval }
			STATUS current
			DESCRIPTION 
				"Description."
			::= { sheSystemNtpClientNotifications 3 }

		
--  1.3.6.1.4.1.231.7.1.2.2.1.2.5.5.4
		sheSystemNtpClientAddServerName NOTIFICATION-TYPE
			OBJECTS { sheSystemNtpClientControlStatus, sheSystemNtpClientControlReqResult, sheSystemNtpClientControlTimeStamp, sheSystemNtpClientControlServerIndex, sheSystemNtpClientControlServername
				 }
			STATUS current
			DESCRIPTION 
				"Description."
			::= { sheSystemNtpClientNotifications 4 }

		
--  1.3.6.1.4.1.231.7.1.2.2.1.2.5.5.5
		sheSystemNtpClientDeleteServerName NOTIFICATION-TYPE
			OBJECTS { sheSystemNtpClientControlStatus, sheSystemNtpClientControlReqResult, sheSystemNtpClientControlTimeStamp, sheSystemNtpClientControlServerIndex, sheSystemNtpClientControlServername
				 }
			STATUS current
			DESCRIPTION 
				"Description."
			::= { sheSystemNtpClientNotifications 5 }

		
--  1.3.6.1.4.1.231.7.1.2.2.1.2.6
		sheSystemDnsServer OBJECT IDENTIFIER ::= { sheSystem 6 }

		
--   --------------------------------------------------------------
-- System DNS Server table 
-- --------------------------------------------------------------
-- 1.3.6.1.4.1.231.7.1.2.2.1.2.6.1
		sheSystemDnsServerTable OBJECT-TYPE
			SYNTAX SEQUENCE OF SheSystemDnsServerEntry
			MAX-ACCESS not-accessible
			STATUS current
			DESCRIPTION
				" DNS server Table of SHE."
			::= { sheSystemDnsServer 1 }

		
--  1.3.6.1.4.1.231.7.1.2.2.1.2.6.1.1
		sheSystemDnsServerEntry OBJECT-TYPE
			SYNTAX SheSystemDnsServerEntry
			MAX-ACCESS not-accessible
			STATUS current
			DESCRIPTION
				" An entry in the sheSystemDnsServerTable.
				Notifications : none. "
			INDEX { sheSystemDnsServerIndex }
			::= { sheSystemDnsServerTable 1 }

		
		SheSystemDnsServerEntry ::=
			SEQUENCE { 
				sheSystemDnsServerIndex
					Integer32,
				sheSystemDnsServerAddr
					OCTET STRING
			 }

--  1.3.6.1.4.1.231.7.1.2.2.1.2.6.1.1.1
		sheSystemDnsServerIndex OBJECT-TYPE
			SYNTAX Integer32 (1..100)
			MAX-ACCESS read-only
			STATUS current
			DESCRIPTION
				" Index of DnsServer table.  "
			::= { sheSystemDnsServerEntry 1 }

		
--  1.3.6.1.4.1.231.7.1.2.2.1.2.6.1.1.2
		sheSystemDnsServerAddr OBJECT-TYPE
			SYNTAX OCTET STRING (SIZE (0..32))
			MAX-ACCESS read-only
			STATUS current
			DESCRIPTION
				" IP address of DNS Server system. "
			::= { sheSystemDnsServerEntry 2 }

		
--   --------------------------------------------------------------
-- System DNS Server management control subgroup
-- --------------------------------------------------------------
-- 1.3.6.1.4.1.231.7.1.2.2.1.2.6.2
		sheSystemDnsServerControl OBJECT IDENTIFIER ::= { sheSystemDnsServer 2 }

		
--  1.3.6.1.4.1.231.7.1.2.2.1.2.6.2.1
		sheSystemDnsServerControlRequest OBJECT-TYPE
			SYNTAX SheSystemDnsServerControlRequestType
			MAX-ACCESS read-write
			STATUS current
			DESCRIPTION
				"  DNS Server management commands :
				
				addedDnsServerName : DNS Server IP Address is added into server list.
				deletedDnsServerName : DNS Server IP Address is deleted in server list.
				
				Notifications: ZZZZZZ
					        "
			::= { sheSystemDnsServerControl 1 }

		
--  1.3.6.1.4.1.231.7.1.2.2.1.2.6.2.2
		sheSystemDnsServerControlStatus OBJECT-TYPE
			SYNTAX SheControlStatusType
			MAX-ACCESS read-only
			STATUS current
			DESCRIPTION
				" The status of a control request. "
			::= { sheSystemDnsServerControl 2 }

		
--  1.3.6.1.4.1.231.7.1.2.2.1.2.6.2.3
		sheSystemDnsServerControlTimer OBJECT-TYPE
			SYNTAX Unsigned32
			MAX-ACCESS read-only
			STATUS current
			DESCRIPTION
				" The maximum wait time for the manager for command ending.
				For long running commands.
				The manager reads this value from the SHE. "
			::= { sheSystemDnsServerControl 3 }

		
--  1.3.6.1.4.1.231.7.1.2.2.1.2.6.2.4
		sheSystemDnsServerControlReqResult OBJECT-TYPE
			SYNTAX SheSystemDnsServerControlRequestResultType
			MAX-ACCESS read-only
			STATUS current
			DESCRIPTION
				" The result of the last user command. "
			::= { sheSystemDnsServerControl 4 }

		
--  1.3.6.1.4.1.231.7.1.2.2.1.2.6.2.5
		sheSystemDnsServerControlTimeStamp OBJECT-TYPE
			SYNTAX Unsigned32
			UNITS "sec"
			MAX-ACCESS read-only
			STATUS current
			DESCRIPTION
				" The time stamp of the last command (end of command). "
			::= { sheSystemDnsServerControl 5 }

		
--  1.3.6.1.4.1.231.7.1.2.2.1.2.6.2.6
		sheSystemDnsServerControlAddr OBJECT-TYPE
			SYNTAX OCTET STRING (SIZE (0..32))
			MAX-ACCESS read-write
			STATUS current
			DESCRIPTION
				"DNS Server Ip address."
			::= { sheSystemDnsServerControl 6 }

		
--  1.3.6.1.4.1.231.7.1.2.2.1.2.6.2.6
		sheSystemDnsServerControlIndex OBJECT-TYPE
			SYNTAX Integer32 (1..100)
			MAX-ACCESS read-write
			STATUS current
			DESCRIPTION
				"Index of the addressed table entry."
			::= { sheSystemDnsServerControl 7 }

		
--   --------------------------------------------------------------
-- System DNS Server management notification subgroup
-- --------------------------------------------------------------
-- 1.3.6.1.4.1.231.7.1.2.2.1.2.6.3
		sheSystemDnsServerNotifications OBJECT IDENTIFIER ::= { sheSystemDnsServer 3 }

		
--  1.3.6.1.4.1.231.7.1.2.2.1.2.6.3.1
		sheSystemDnsServerAddAddr NOTIFICATION-TYPE
			OBJECTS { sheSystemDnsServerControlStatus, sheSystemDnsServerControlReqResult, sheSystemDnsServerControlTimeStamp, sheSystemDnsServerControlAddr, sheSystemDnsServerControlIndex
				 }
			STATUS current
			DESCRIPTION 
				"Description."
			::= { sheSystemDnsServerNotifications 1 }

		
--  1.3.6.1.4.1.231.7.1.2.2.1.2.6.3.2
		sheSystemDnsServerDeleteAddr NOTIFICATION-TYPE
			OBJECTS { sheSystemDnsServerControlStatus, sheSystemDnsServerControlReqResult, sheSystemDnsServerControlTimeStamp, sheSystemDnsServerControlIndex }
			STATUS current
			DESCRIPTION 
				"Description."
			::= { sheSystemDnsServerNotifications 2 }

		
--  1.3.6.1.4.1.231.7.1.2.2.1.2.7
		sheSystemManagementSession OBJECT IDENTIFIER ::= { sheSystem 7 }

		
--   --------------------------------------------------------------
-- System Management Session group 
-- --------------------------------------------------------------
-- 1.3.6.1.4.1.231.7.1.2.2.1.2.7.1
		sheSystemManagementSessionSnmpAgingTime OBJECT-TYPE
			SYNTAX Integer32 (300..3600)
			MAX-ACCESS read-only
			STATUS current
			DESCRIPTION
				"Aging time for SNMP management session."
			::= { sheSystemManagementSession 1 }

		
--   -----------------------------------------------------------------
-- System Management Session Table
-- -----------------------------------------------------------------
-- 1.3.6.1.4.1.231.7.1.2.2.1.2.7.2
		sheSystemManagementSessionTable OBJECT-TYPE
			SYNTAX SEQUENCE OF SheSystemManagementSessionEntry
			MAX-ACCESS not-accessible
			STATUS current
			DESCRIPTION
				" Management session information table for SHE."
			::= { sheSystemManagementSession 2 }

		
--  1.3.6.1.4.1.231.7.1.2.2.1.2.7.2.1
		sheSystemManagementSessionEntry OBJECT-TYPE
			SYNTAX SheSystemManagementSessionEntry
			MAX-ACCESS not-accessible
			STATUS current
			DESCRIPTION
				" An entry in the sheSystemManagementSessionTable.
				Notifications : none. "
			INDEX { sheSystemManagementSessionIndex }
			::= { sheSystemManagementSessionTable 1 }

		
		SheSystemManagementSessionEntry ::=
			SEQUENCE { 
				sheSystemManagementSessionIndex
					Integer32,
				sheSystemManagementSessionType
					SheSystemManagementSessionType,
				sheSystemManagementSessionSnmpExpiredTime
					Integer32,
				sheSystemManagementSessionAddress
					IpAddress
			 }

--  1.3.6.1.4.1.231.7.1.2.2.1.2.7.2.1.1
		sheSystemManagementSessionIndex OBJECT-TYPE
			SYNTAX Integer32 (1..100)
			MAX-ACCESS read-only
			STATUS current
			DESCRIPTION
				" Index of Management Session Table."
			::= { sheSystemManagementSessionEntry 1 }

		
--  1.3.6.1.4.1.231.7.1.2.2.1.2.7.2.1.2
		sheSystemManagementSessionType OBJECT-TYPE
			SYNTAX SheSystemManagementSessionType
			MAX-ACCESS read-only
			STATUS current
			DESCRIPTION
				" Management Session Type."
			::= { sheSystemManagementSessionEntry 2 }

		
--  1.3.6.1.4.1.231.7.1.2.2.1.2.7.2.1.3
		sheSystemManagementSessionSnmpExpiredTime OBJECT-TYPE
			SYNTAX Integer32
			MAX-ACCESS read-only
			STATUS current
			DESCRIPTION
				" Only SNMP Management Session expired Time.
				If the session is Telnet, this value is 0."
			::= { sheSystemManagementSessionEntry 3 }

		
--  1.3.6.1.4.1.231.7.1.2.2.1.2.7.2.1.4
		sheSystemManagementSessionAddress OBJECT-TYPE
			SYNTAX IpAddress
			MAX-ACCESS read-only
			STATUS current
			DESCRIPTION
				" Management Session IP Address."
			::= { sheSystemManagementSessionEntry 4 }

		
--   --------------------------------------------------------------
-- System Management Session control subgroup
-- --------------------------------------------------------------
-- 1.3.6.1.4.1.231.7.1.2.2.1.2.7.3			
		sheSystemManagementSessionControl OBJECT IDENTIFIER ::= { sheSystemManagementSession 3 }

		
--  1.3.6.1.4.1.231.7.1.2.2.1.2.7.3.1
		sheSystemManagementSessionControlRequest OBJECT-TYPE
			SYNTAX SheSystemManagementSessionControlRequestType
			MAX-ACCESS read-write
			STATUS current
			DESCRIPTION
				"  Management Session global user commands :
				
				setSnmpSessionAgingTime : configuring SNMP session aging time.
				
				Notifications: sheSystemManagementSessionChangedSnmpAgingTime
					        "
			::= { sheSystemManagementSessionControl 1 }

		
--  1.3.6.1.4.1.231.7.1.2.2.1.2.7.3.2
		sheSystemManagementSessionControlStatus OBJECT-TYPE
			SYNTAX SheControlStatusType
			MAX-ACCESS read-only
			STATUS current
			DESCRIPTION
				" The status of a control request. "
			::= { sheSystemManagementSessionControl 2 }

		
--  1.3.6.1.4.1.231.7.1.2.2.1.2.7.3.3
		sheSystemManagementSessionControlTimer OBJECT-TYPE
			SYNTAX Unsigned32
			MAX-ACCESS read-only
			STATUS current
			DESCRIPTION
				" The maximum wait time for the manager for command ending.
				For long running commands.
				The manager reads this value from the SHE. "
			::= { sheSystemManagementSessionControl 3 }

		
--  1.3.6.1.4.1.231.7.1.2.2.1.2.7.3.4
		sheSystemManagementSessionControlReqResult OBJECT-TYPE
			SYNTAX SheSystemManagementSessionControlReqResultType
			MAX-ACCESS read-only
			STATUS current
			DESCRIPTION
				" The result of the last user command. "
			::= { sheSystemManagementSessionControl 4 }

		
--  1.3.6.1.4.1.231.7.1.2.2.1.2.7.3.5
		sheSystemManagementSessionControlTimeStamp OBJECT-TYPE
			SYNTAX Unsigned32
			UNITS "sec"
			MAX-ACCESS read-only
			STATUS current
			DESCRIPTION
				" The time stamp of the last command (end of command). "
			::= { sheSystemManagementSessionControl 5 }

		
--  1.3.6.1.4.1.231.7.1.2.2.1.2.7.3.6
		sheSystemManagementSessionControlSnmpAgingTime OBJECT-TYPE
			SYNTAX Integer32 (300..3600)
			UNITS "sec"
			MAX-ACCESS read-write
			STATUS current
			DESCRIPTION
				"SNMP Session Aging Time."
			::= { sheSystemManagementSessionControl 6 }

		
--   --------------------------------------------------------------
-- System Management Session notification subgroup
-- --------------------------------------------------------------
-- 1.3.6.1.4.1.231.7.1.2.2.1.2.7.4
		sheSystemManagementSessionNotifications OBJECT IDENTIFIER ::= { sheSystemManagementSession 4 }

		
--  1.3.6.1.4.1.231.7.1.2.2.1.2.7.4.1
		sheSystemManagementSessionConnection NOTIFICATION-TYPE
			OBJECTS { sheSystemManagementSessionType, sheSystemManagementSessionSnmpExpiredTime, sheSystemManagementSessionAddress }
			STATUS current
			DESCRIPTION 
				"Management Session Connect event.
				When a new session is detected, the event occurs."
			::= { sheSystemManagementSessionNotifications 1 }

		
--  1.3.6.1.4.1.231.7.1.2.2.1.2.7.4.2
		sheSystemManagementSessionDisconnection NOTIFICATION-TYPE
			OBJECTS { sheSystemManagementSessionType, sheSystemManagementSessionSnmpExpiredTime, sheSystemManagementSessionAddress }
			STATUS current
			DESCRIPTION 
				"Management Session Disonnect event.
				When an existing session is diconnected, the event occurs.
				In case of SNMP sessions, when SNMP aging timer is expired, disconnection decision."
			::= { sheSystemManagementSessionNotifications 2 }

		
--  1.3.6.1.4.1.231.7.1.2.2.1.2.7.4.3
		sheSystemManagementSessionChangedSnmpAgingTime NOTIFICATION-TYPE
			OBJECTS { sheSystemManagementSessionControlSnmpAgingTime }
			STATUS current
			DESCRIPTION 
				"SNMP Management Session Aging Time Change Event."
			::= { sheSystemManagementSessionNotifications 3 }

		
--  1.3.6.1.4.1.231.7.1.2.2.1.2.8
		sheSystemConfigLog OBJECT IDENTIFIER ::= { sheSystem 8 }

		
--   --------------------------------------------------------------
-- System Config Log group 
-- --------------------------------------------------------------
-- 1.3.6.1.4.1.231.7.1.2.2.1.2.8.1
		sheSystemConfigLogGroup OBJECT IDENTIFIER ::= { sheSystemConfigLog 1 }

		
--  1.3.6.1.4.1.231.7.1.2.2.1.2.8.1.1
		sheSystemConfigLogEntryNumber OBJECT-TYPE
			SYNTAX Integer32 (0..1000)
			MAX-ACCESS read-only
			STATUS current
			DESCRIPTION
				"The number of the configuration log entries to keep.
				0: disable configuration logging
				"
			DEFVAL { 500 }
			::= { sheSystemConfigLogGroup 1 }

		
--  1.3.6.1.4.1.231.7.1.2.2.1.2.8.1.2
		sheSystemConfigLogFtpServerAddress OBJECT-TYPE
			SYNTAX IpAddress
			MAX-ACCESS read-only
			STATUS current
			DESCRIPTION
				"FTP server's IP address to which log file will be transferred.
				Default:0.0.0.0
				0.0.0.0: disable FTP transfer
				"
			::= { sheSystemConfigLogGroup 2 }

		
--  1.3.6.1.4.1.231.7.1.2.2.1.2.8.1.3
		sheSystemConfigLogFtpUser OBJECT-TYPE
			SYNTAX OCTET STRING (SIZE (0..128))
			MAX-ACCESS read-only
			STATUS current
			DESCRIPTION
				"User ID for FTP server.
				
				Merge-Info:
				Element is not needed. Read-access will report an empty string."
			::= { sheSystemConfigLogGroup 3 }

		
--  1.3.6.1.4.1.231.7.1.2.2.1.2.8.1.4
		sheSystemConfigLogFtpPassword OBJECT-TYPE
			SYNTAX OCTET STRING (SIZE (0..128))
			MAX-ACCESS read-only
			STATUS current
			DESCRIPTION
				"Password for FTP server.
				
				Merge-Info:
				Element is not needed. Read-access will report an empty string."
			::= { sheSystemConfigLogGroup 4 }

		
--  1.3.6.1.4.1.231.7.1.2.2.1.2.8.1.5
		sheSystemConfigLogFtpInterval OBJECT-TYPE
			SYNTAX Integer32 (0..2147483647)
			UNITS "sec"
			MAX-ACCESS read-only
			STATUS current
			DESCRIPTION
				"Timer interval between FTP transfers of log in second
				0: disable FTP transfer
				"
			DEFVAL { 300 }
			::= { sheSystemConfigLogGroup 5 }

		
--  1.3.6.1.4.1.231.7.1.2.2.1.2.8.1.6
		sheSystemConfigLogFtpPathName OBJECT-TYPE
			SYNTAX OCTET STRING (SIZE (0..128))
			MAX-ACCESS read-only
			STATUS current
			DESCRIPTION
				"Path name of file on FTP server. This path should be set relative to the ftp-server root. Use only linux notation ( / )."
			DEFVAL { "/" }
			::= { sheSystemConfigLogGroup 6 }

		
--  1.3.6.1.4.1.231.7.1.2.2.1.2.8.2
		sheSystemConfigLogControl OBJECT IDENTIFIER ::= { sheSystemConfigLog 2 }

		
--  1.3.6.1.4.1.231.7.1.2.2.1.2.8.2.1
		sheSystemConfigLogControlRequest OBJECT-TYPE
			SYNTAX SheSystemConfigLogControlRequestType
			MAX-ACCESS read-write
			STATUS current
			DESCRIPTION
				"Config log global user commands"
			::= { sheSystemConfigLogControl 1 }

		
--  1.3.6.1.4.1.231.7.1.2.2.1.2.8.2.2
		sheSystemConfigLogControlEntryNumber OBJECT-TYPE
			SYNTAX Integer32 (0..1000)
			MAX-ACCESS read-write
			STATUS current
			DESCRIPTION
				"The number of the configuration log entries to keep"
			::= { sheSystemConfigLogControl 2 }

		
--  1.3.6.1.4.1.231.7.1.2.2.1.2.8.2.3
		sheSystemConfigLogControlFtpAddress OBJECT-TYPE
			SYNTAX IpAddress
			MAX-ACCESS read-write
			STATUS current
			DESCRIPTION
				"FTP server's IP address to which log file will be transferred"
			::= { sheSystemConfigLogControl 3 }

		
--  1.3.6.1.4.1.231.7.1.2.2.1.2.8.2.4
		sheSystemConfigLogControlFtpUser OBJECT-TYPE
			SYNTAX OCTET STRING (SIZE (0..128))
			MAX-ACCESS read-write
			STATUS current
			DESCRIPTION
				"User ID for FTP server.
				Read-access will report an empty string. "
			::= { sheSystemConfigLogControl 4 }

		
--  1.3.6.1.4.1.231.7.1.2.2.1.2.8.2.5
		sheSystemConfigLogControlFtpPassword OBJECT-TYPE
			SYNTAX OCTET STRING (SIZE (0..128))
			MAX-ACCESS read-write
			STATUS current
			DESCRIPTION
				"Password for FTP server.
				Read-access will report an empty string."
			::= { sheSystemConfigLogControl 5 }

		
--  1.3.6.1.4.1.231.7.1.2.2.1.2.8.2.6
		sheSystemConfigLogControlFtpInterval OBJECT-TYPE
			SYNTAX Integer32 (0..2147483647)
			UNITS "sec"
			MAX-ACCESS read-write
			STATUS current
			DESCRIPTION
				"Timer interval between FTP transfers of log in second
				0: disable FTP transfer
				"
			::= { sheSystemConfigLogControl 6 }

		
--  1.3.6.1.4.1.231.7.1.2.2.1.2.8.2.7
		sheSystemConfigLogControlFtpPathName OBJECT-TYPE
			SYNTAX OCTET STRING (SIZE (0..128))
			MAX-ACCESS read-write
			STATUS current
			DESCRIPTION
				"Path name of file on FTP server. This path should be set relative to the ftp-server root. Use only linux notation ( / )."
			DEFVAL { "/" }
			::= { sheSystemConfigLogControl 7 }

		
--  1.3.6.1.4.1.231.7.1.2.2.1.2.8.2.8
		sheSystemConfigLogControlReqResult OBJECT-TYPE
			SYNTAX SheSystemControlRequestResultType
			MAX-ACCESS read-only
			STATUS current
			DESCRIPTION
				" The result of the last user command. "
			::= { sheSystemConfigLogControl 8 }

		
--  1.3.6.1.4.1.231.7.1.2.2.1.2.8.2.9
		sheSystemConfigLogControlStatus OBJECT-TYPE
			SYNTAX SheControlStatusType
			MAX-ACCESS read-only
			STATUS current
			DESCRIPTION
				" The status of a control request. "
			::= { sheSystemConfigLogControl 9 }

		
--  1.3.6.1.4.1.231.7.1.2.2.1.2.8.2.10
		sheSystemConfigLogControlTimeStamp OBJECT-TYPE
			SYNTAX Unsigned32
			UNITS "sec"
			MAX-ACCESS read-only
			STATUS current
			DESCRIPTION
				" The time stamp of the last command (end of command). "
			::= { sheSystemConfigLogControl 10 }

		
--  1.3.6.1.4.1.231.7.1.2.2.1.2.8.3
		sheSystemConfigLogNotifications OBJECT IDENTIFIER ::= { sheSystemConfigLog 3 }

		
--  1.3.6.1.4.1.231.7.1.2.2.1.2.8.3.1
		sheSystemConfigLogEntryNumberChanged NOTIFICATION-TYPE
			OBJECTS { sheSystemConfigLogEntryNumber }
			STATUS current
			DESCRIPTION 
				"Config entry number to keep is changed."
			::= { sheSystemConfigLogNotifications 1 }

		
--  1.3.6.1.4.1.231.7.1.2.2.1.2.8.3.2
		sheSystemConfigLogFtpLoginInfoChanged NOTIFICATION-TYPE
			OBJECTS { sheSystemConfigLogFtpServerAddress, sheSystemConfigLogFtpUser, sheSystemConfigLogFtpPassword, sheSystemConfigLogFtpPathName }
			STATUS current
			DESCRIPTION 
				"FTP server address and login information is changed."
			::= { sheSystemConfigLogNotifications 2 }

		
--  1.3.6.1.4.1.231.7.1.2.2.1.2.8.3.3
		sheSystemConfigLogFtpIntervalChanged NOTIFICATION-TYPE
			OBJECTS { sheSystemConfigLogFtpInterval }
			STATUS current
			DESCRIPTION 
				"Timer interval is changed."
			::= { sheSystemConfigLogNotifications 3 }

		
-- --------------------------------------------------------------
-- System Auto Config Backup group 
-- --------------------------------------------------------------
-- 1.3.6.1.4.1.231.7.1.2.2.1.2.9
-- 
-- Only contained for backward compatibility. 
-- Will never be supported by SHE R2.5 or higher!
		sheSystemAutoConfigBackup OBJECT IDENTIFIER ::= { sheSystem 9 }

		
--  1.3.6.1.4.1.231.7.1.2.2.1.2.9.1
		sheSystemAutoConfigBackupGroup OBJECT IDENTIFIER ::= { sheSystemAutoConfigBackup 1 }

		
--  1.3.6.1.4.1.231.7.1.2.2.1.2.9.1.1
		sheSystemAutoConfigBackupEnabled OBJECT-TYPE
			SYNTAX TruthValue
			MAX-ACCESS read-only
			STATUS current
			DESCRIPTION
				"Enable/disable auto configuration backup feature
				true: enable
				false: disable
				"
			DEFVAL { false }
			::= { sheSystemAutoConfigBackupGroup 1 }

		
--  1.3.6.1.4.1.231.7.1.2.2.1.2.9.1.2
		sheSystemAutoConfigBackupFtpServerAddress OBJECT-TYPE
			SYNTAX IpAddress
			MAX-ACCESS read-only
			STATUS current
			DESCRIPTION
				"FTP server's IP address to which config file will be transferred.
				Default:0.0.0.0
				0.0.0.0: disable FTP transfer
				"
			::= { sheSystemAutoConfigBackupGroup 2 }

		
--  1.3.6.1.4.1.231.7.1.2.2.1.2.9.1.3
		sheSystemAutoConfigBackupFtpUser OBJECT-TYPE
			SYNTAX OCTET STRING (SIZE (128))
			MAX-ACCESS read-only
			STATUS current
			DESCRIPTION
				"User ID for FTP server"
			::= { sheSystemAutoConfigBackupGroup 3 }

		
--  1.3.6.1.4.1.231.7.1.2.2.1.2.9.1.4
		sheSystemAutoConfigBackupFtpPassword OBJECT-TYPE
			SYNTAX OCTET STRING (SIZE (128))
			MAX-ACCESS read-only
			STATUS current
			DESCRIPTION
				"Password for FTP server"
			::= { sheSystemAutoConfigBackupGroup 4 }

		
--  1.3.6.1.4.1.231.7.1.2.2.1.2.9.1.5
		sheSystemAutoConfigBackupFtpPathName OBJECT-TYPE
			SYNTAX OCTET STRING (SIZE (128))
			MAX-ACCESS read-only
			STATUS current
			DESCRIPTION
				"Path name of file on FTP server. This path should be set relative to the ftp-server root. Use only linux notation ( / )
				Default: /
				"
			DEFVAL { "/" }
			::= { sheSystemAutoConfigBackupGroup 5 }

		
--  1.3.6.1.4.1.231.7.1.2.2.1.2.9.1.6
		sheSystemAutoConfigBackupTime OBJECT-TYPE
			SYNTAX Integer32 (30..2147483647)
			UNITS "sec"
			MAX-ACCESS read-only
			STATUS current
			DESCRIPTION
				"It indicates a time that ftp backup should be performed since autoconfiguration has been set."
			DEFVAL { 300 }
			::= { sheSystemAutoConfigBackupGroup 6 }

		
--  1.3.6.1.4.1.231.7.1.2.2.1.2.9.2
		sheSystemAutoConfigBackupControl OBJECT IDENTIFIER ::= { sheSystemAutoConfigBackup 2 }

		
--  1.3.6.1.4.1.231.7.1.2.2.1.2.9.2.1			                      
		sheSystemAutoConfigBackupControlRequest OBJECT-TYPE
			SYNTAX SheSystemAutoConfigBackupControlRequest
			MAX-ACCESS read-write
			STATUS current
			DESCRIPTION
				"AutoConfigBackup global user commands"
			::= { sheSystemAutoConfigBackupControl 1 }

		
--  1.3.6.1.4.1.231.7.1.2.2.1.2.9.2.2
		sheSystemAutoConfigBackupControlEnabled OBJECT-TYPE
			SYNTAX TruthValue
			MAX-ACCESS read-write
			STATUS current
			DESCRIPTION
				"Enable/disable auto configuration backup feature
				true: enabled
				false: disabled
				"
			DEFVAL { false }
			::= { sheSystemAutoConfigBackupControl 2 }

		
--  1.3.6.1.4.1.231.7.1.2.2.1.2.9.2.3
		sheSystemAutoConfigBackupControlFtpServerAddress OBJECT-TYPE
			SYNTAX IpAddress
			MAX-ACCESS read-write
			STATUS current
			DESCRIPTION
				"FTP server's IP address to which config file will be transferred."
			::= { sheSystemAutoConfigBackupControl 3 }

		
--  1.3.6.1.4.1.231.7.1.2.2.1.2.9.2.4
		sheSystemAutoConfigBackupControlFtpUser OBJECT-TYPE
			SYNTAX OCTET STRING (SIZE (128))
			MAX-ACCESS read-write
			STATUS current
			DESCRIPTION
				"User ID for FTP server"
			::= { sheSystemAutoConfigBackupControl 4 }

		
--  1.3.6.1.4.1.231.7.1.2.2.1.2.9.2.5
		sheSystemAutoConfigBackupControlFtpPassword OBJECT-TYPE
			SYNTAX OCTET STRING (SIZE (128))
			MAX-ACCESS read-write
			STATUS current
			DESCRIPTION
				"Password for FTP server"
			::= { sheSystemAutoConfigBackupControl 5 }

		
--  1.3.6.1.4.1.231.7.1.2.2.1.2.9.2.6
		sheSystemAutoConfigBackupControlFtpPathName OBJECT-TYPE
			SYNTAX OCTET STRING (SIZE (128))
			MAX-ACCESS read-write
			STATUS current
			DESCRIPTION
				"Path name of file on FTP server. This path should be set relative to the ftp-server root. Use only linux notation ( / ).
				Default: /
				"
			::= { sheSystemAutoConfigBackupControl 6 }

		
--  1.3.6.1.4.1.231.7.1.2.2.1.2.9.2.7
		sheSystemAutoConfigBackupControlBackupTime OBJECT-TYPE
			SYNTAX Integer32 (30..2147483647)
			MAX-ACCESS read-write
			STATUS current
			DESCRIPTION
				"It indicates a time that ftp backup should be performed since autoconfiguration has been set."
			::= { sheSystemAutoConfigBackupControl 7 }

		
--  1.3.6.1.4.1.231.7.1.2.2.1.2.9.3
		sheSystemAutoConfigBackupNotifications OBJECT IDENTIFIER ::= { sheSystemAutoConfigBackup 3 }

		
--  1.3.6.1.4.1.231.7.1.2.2.1.2.9.3.1
		sheSystemAutoConfigBackupEnabledChanged NOTIFICATION-TYPE
			OBJECTS { sheSystemAutoConfigBackupEnabled }
			STATUS current
			DESCRIPTION 
				"Auto configuration backup is enabled or disabled."
			::= { sheSystemAutoConfigBackupNotifications 1 }

		
--  1.3.6.1.4.1.231.7.1.2.2.1.2.9.3.2
		sheSystemAutoConfigBackupFtpLoginInfoChanged NOTIFICATION-TYPE
			OBJECTS { sheSystemAutoConfigBackupFtpServerAddress, sheSystemAutoConfigBackupFtpUser, sheSystemAutoConfigBackupFtpPassword, sheSystemAutoConfigBackupFtpPathName }
			STATUS current
			DESCRIPTION 
				"FTP server address and login information is changed."
			::= { sheSystemAutoConfigBackupNotifications 2 }

		
--  1.3.6.1.4.1.231.7.1.2.2.1.2.9.3.3
		sheSystemAutoConfigBackupTimeChanged NOTIFICATION-TYPE
			OBJECTS { sheSystemAutoConfigBackupTime }
			STATUS current
			DESCRIPTION 
				"Config backup time is changed."
			::= { sheSystemAutoConfigBackupNotifications 3 }

		
		sheSystemSnmp OBJECT IDENTIFIER ::= { sheSystem 10 }

		
		sheSystemNotificationCounter OBJECT-TYPE
			SYNTAX Unsigned32
			MAX-ACCESS read-only
			STATUS current
			DESCRIPTION
				"Number of last sended notification.
				
				This OID is last member of each sended notification from SHE NE. A TMN system should
				now be able to check, if all notification were received and if not a consistency check 
				could be performed.
				"
			::= { sheSystemSnmp 1 }

		
--  Configuration and status information for automatic sw upgrade and db backup controls.
		sheSystemMaintenance OBJECT IDENTIFIER ::= { sheSystem 11 }

		
		sheSystemSwMaintenance OBJECT IDENTIFIER ::= { sheSystemMaintenance 1 }

		
		sheSystemSwMaintenanceBase OBJECT IDENTIFIER ::= { sheSystemSwMaintenance 1 }

		
		sheSystemSwmSapsServerAddr OBJECT-TYPE
			SYNTAX OCTET STRING (SIZE (0..20))
			MAX-ACCESS read-only
			STATUS current
			DESCRIPTION
				"Address of SAPS FTP server (dotted notation)."
			::= { sheSystemSwMaintenanceBase 1 }

		
		sheSystemSwmSapsPathName OBJECT-TYPE
			SYNTAX OCTET STRING (SIZE (0..128))
			MAX-ACCESS read-only
			STATUS current
			DESCRIPTION
				"Path name of SAPS file on FTP server. 
				This path should be set relative to the ftp-server root.
				Use only linux notation ( / ). 
				
				Spaces in pathnames are not allowed, because of possible problems with
				different FTP implementations (client and/or server)!!"
			::= { sheSystemSwMaintenanceBase 2 }

		
		sheSystemSwmSapsFileName OBJECT-TYPE
			SYNTAX OCTET STRING (SIZE (1..128))
			MAX-ACCESS read-only
			STATUS current
			DESCRIPTION
				"File name of SAPS file on FTP server. 
				
				Spaces in filenames are not allowed, because of possible problems with
				different FTP implementations (client and/or server)!!
				"
			::= { sheSystemSwMaintenanceBase 3 }

		
		sheSystemSwmAdminState OBJECT-TYPE
			SYNTAX SheSystemAdminState
			MAX-ACCESS read-only
			STATUS current
			DESCRIPTION
				"This state describes the current usage of automatic sw upgrade.
				The following states are supported:
				
				unlocked(1)  -> saps handling used
				locked(2)    -> saps handling not used (default)
				
				Important Note: If the automatic sw upgrade system is enabled, the sheSystemFileControl group
				for single sw upgrades is always busy!! If a sw upgrade should be start for a single Card or a single
				card type, the sheSystemSwmAdminState has to be locked and then the sheSystemFileControl could be used!"
			DEFVAL { 2 }
			::= { sheSystemSwMaintenanceBase 4 }

		
		sheSystemSwmCurrentStatus OBJECT-TYPE
			SYNTAX SheSystemSwmCurrentStatusType
			MAX-ACCESS read-only
			STATUS current
			DESCRIPTION
				"This parameter describes the current status of automatic sw upgrade process.
				The following states are supported:
				
				passive(1)	-> saps handling disabled (default)  or 
						    saps handling enabled but last request failed 
				started(2)	-> saps handling enabled, start loading S-APS file
				active(3)	-> saps handling enabled and running
				"
			::= { sheSystemSwMaintenanceBase 5 }

		
--    --------------------------------------------------------------
-- SW Upgrade Task Table
-- --------------------------------------------------------------
-- 
		sheSystemSwMaintenanceTaskTable OBJECT-TYPE
			SYNTAX SEQUENCE OF SheSystemSwMaintenanceTaskEntry
			MAX-ACCESS not-accessible
			STATUS current
			DESCRIPTION
				"Table of the current active or failed tasks of SW upgrade.
				This table is used to display the automatic upgrade status for single plugin
				units at the TMN. "
			::= { sheSystemSwMaintenance 2 }

		
--    info-IMPL:    V2.0->
		sheSystemSwMaintenanceTaskEntry OBJECT-TYPE
			SYNTAX SheSystemSwMaintenanceTaskEntry
			MAX-ACCESS not-accessible
			STATUS current
			DESCRIPTION
				"Entry of the SW upgrade task table.
				"
			INDEX { sheSystemSwmTIndex }
			::= { sheSystemSwMaintenanceTaskTable 1 }

		
		SheSystemSwMaintenanceTaskEntry ::=
			SEQUENCE { 
				sheSystemSwmTIndex
					Unsigned32,
				sheSystemSwmTCardType
					SheCardType,
				sheSystemSwmTEntPhysicalIndex
					PhysicalIndex,
				sheSystemSwmTTimeStamp
					Unsigned32,
				sheSystemSwmTUpgradeState
					SheSystemMaintenanceControlReqResult,
				sheSystemSwmTUpgradeResult
					SheSystemMaintenanceControlReqResult,
				sheSystemSwmTSwVersion
					OCTET STRING,
				sheSystemSwmTSwVersionNeed
					OCTET STRING
			 }

		sheSystemSwmTIndex OBJECT-TYPE
			SYNTAX Unsigned32 (1..255)
			MAX-ACCESS read-only
			STATUS current
			DESCRIPTION
				"Unique value to identify an entry of this table. "
			::= { sheSystemSwMaintenanceTaskEntry 1 }

		
		sheSystemSwmTCardType OBJECT-TYPE
			SYNTAX SheCardType
			MAX-ACCESS read-only
			STATUS current
			DESCRIPTION
				" Indicates the plug-in unit type to be upgraded. "
			::= { sheSystemSwMaintenanceTaskEntry 2 }

		
		sheSystemSwmTEntPhysicalIndex OBJECT-TYPE
			SYNTAX PhysicalIndex
			MAX-ACCESS read-only
			STATUS current
			DESCRIPTION
				"The entPhysicalIndex of PIU to be loaded."
			::= { sheSystemSwMaintenanceTaskEntry 3 }

		
		sheSystemSwmTTimeStamp OBJECT-TYPE
			SYNTAX Unsigned32
			UNITS "sec"
			MAX-ACCESS read-only
			STATUS current
			DESCRIPTION
				"The time stamp of the task. It is updated anytime the upgrade task state changes. "
			::= { sheSystemSwMaintenanceTaskEntry 4 }

		
		sheSystemSwmTUpgradeState OBJECT-TYPE
			SYNTAX SheSystemMaintenanceControlReqResult
			MAX-ACCESS read-only
			STATUS current
			DESCRIPTION
				"Identifies the current processing state of the upgrade task: 
				- sutInitialized
				- sutToDo
				- sutStarted
				- sutCrashed
				- sutFtpDone
				- sutDone
				- sutReadyForReset
				- sutResetInProgress
				- sutObsolete"
			::= { sheSystemSwMaintenanceTaskEntry 5 }

		
		sheSystemSwmTUpgradeResult OBJECT-TYPE
			SYNTAX SheSystemMaintenanceControlReqResult
			MAX-ACCESS read-only
			STATUS current
			DESCRIPTION
				"This read-only attribute informs about the result of the performed upgrade
				(in case of failed upgrade the error reason). "
			::= { sheSystemSwMaintenanceTaskEntry 6 }

		
		sheSystemSwmTSwVersion OBJECT-TYPE
			SYNTAX OCTET STRING (SIZE (0..128))
			MAX-ACCESS read-only
			STATUS current
			DESCRIPTION
				"String containing the APS version which is loaded into the plug-in unit. "
			::= { sheSystemSwMaintenanceTaskEntry 7 }

		
		sheSystemSwmTSwVersionNeed OBJECT-TYPE
			SYNTAX OCTET STRING (SIZE (0..128))
			MAX-ACCESS read-only
			STATUS current
			DESCRIPTION
				"String containing the APS version which should be loaded into the plug-in unit. "
			::= { sheSystemSwMaintenanceTaskEntry 8 }

		
--  --------------------------------------------------------------
-- SW maintenance control subgroup
-- --------------------------------------------------------------
-- This managed entity represents the control group for saps sw maintenance user commands.
-- The following user commands are implemented :
-- 
-- setSystemMaintenanceBase
-- Set needed ftp access information for automatic SAPS request's.
-- 
-- setSwmAdminState
-- Enable/Disable the automatic saps sw maintenance system.
-- 
-- swmUpgrStartRequest:    
-- Start upgrade for the sytem in the background including sw activation.
-- 
-- swmUpgrStartRequestNoReset:    
-- Start upgrade for the sytem in the background without sw activation.
-- To activate new sw versions, the piu's should be made a reset.
-- 
-- swmReadSAPSContentFile : 
-- The SAPS (Sytem Application Software) content file describes an assignment of
-- available SW loads to loadable PIUs inclusively the CXU .
-- If there is a new SAPs content file at the FTP server f.ex. because of bug fix
-- release the crafts person has to request the reading of the SAPS content file
-- so that the information is available in the DSLAM.
-- The SAPS content file is automatically read after reload or after activation
-- of a CXU load.
-- 
-- 
		sheSystemSwMaintenanceControl OBJECT IDENTIFIER ::= { sheSystemSwMaintenance 3 }

		
		sheSystemSwmControlRequest OBJECT-TYPE
			SYNTAX SheSystemMaintenanceControlReq
			MAX-ACCESS read-write
			STATUS current
			DESCRIPTION
				"SW upgrade command requests from TMN.
				
				setSystemMaintenanceBase(50), 
				- Set needed ftp access information for automatic SAPS request's.
				notifications: 
				  sheSystemSwmBaseSet
				
				setSwmAdminState(51),
				- lock or unlock the automatic saps system
				notifications:                       
				  sheSystemSwmBaseAdminStateSet
				  sheSystemReadSAPSContentFileReady (if set to unlock)
				  sheSystemSwmFTPError              (if ftp could not reached)
				
				swmUpgrStartRequest(100),
				- start new upgrade procedure including automatic load activation
				notifications:
				 sheSystemSwmFTPError
				 sheSystemSwmUpgradeStartResult
				
				swmUpgrStartRequestNoReset(101),
				- start new upgrade procedure without automatic load activation
				notifications:
				 sheSystemSwmReadyForReset
				 sheSystemSwmFTPError
				 sheSystemUpgradeCanceled (bad case only) 
				 sheSystemSwmUpgradeStartResult
				
				
				swmReadSAPSContentFile(102),
				- start request of new SAPS file from server, no download action is started 
				notification:
				 sheSystemReadSAPSContentFileReady
				 sheSystemSwmFTPError
				
				"
			::= { sheSystemSwMaintenanceControl 1 }

		
		sheSystemSwmControlStatus OBJECT-TYPE
			SYNTAX SheControlStatusType
			MAX-ACCESS read-only
			STATUS current
			DESCRIPTION
				" The status of the current request. "
			::= { sheSystemSwMaintenanceControl 2 }

		
		sheSystemSwmControlTimer OBJECT-TYPE
			SYNTAX Unsigned32
			MAX-ACCESS read-only
			STATUS current
			DESCRIPTION
				"Wait time in seconds after complete upgrade for a unit type. "
			::= { sheSystemSwMaintenanceControl 3 }

		
		sheSystemSwmControlReqResult OBJECT-TYPE
			SYNTAX SheSystemMaintenanceControlReqResult
			MAX-ACCESS read-only
			STATUS current
			DESCRIPTION
				"The result of the last user command."
			::= { sheSystemSwMaintenanceControl 4 }

		
		sheSystemSwmControlTimeStamp OBJECT-TYPE
			SYNTAX Unsigned32
			UNITS "sec"
			MAX-ACCESS read-only
			STATUS current
			DESCRIPTION
				" The time stamp of the last command (end of command). "
			::= { sheSystemSwMaintenanceControl 5 }

		
		sheSystemSwmControlSapsServerAddr OBJECT-TYPE
			SYNTAX OCTET STRING (SIZE (0..20))
			MAX-ACCESS read-write
			STATUS current
			DESCRIPTION
				"Address of SAPS FTP server (dotted notation)."
			::= { sheSystemSwMaintenanceControl 6 }

		
		sheSystemSwmControlSapsPathName OBJECT-TYPE
			SYNTAX OCTET STRING (SIZE (0..128))
			MAX-ACCESS read-write
			STATUS current
			DESCRIPTION
				"Path name of SAPS file on FTP server. 
				This path should be set relative to the ftp-server root.
				Use only linux notation ( / ). 
				
				Spaces in pathnames are not allowed, because of possible problems with
				different FTP implementations (client and/or server)!!"
			::= { sheSystemSwMaintenanceControl 7 }

		
		sheSystemSwmControlSapsFileName OBJECT-TYPE
			SYNTAX OCTET STRING (SIZE (1..128))
			MAX-ACCESS read-write
			STATUS current
			DESCRIPTION
				"File name of SAPS file on FTP server. 
				
				Spaces in filenames are not allowed, because of possible problems with
				different FTP implementations (client and/or server)!!
				"
			::= { sheSystemSwMaintenanceControl 8 }

		
		sheSystemSwmControlSapsUsrName OBJECT-TYPE
			SYNTAX OCTET STRING (SIZE (0..20))
			MAX-ACCESS read-write
			STATUS current
			DESCRIPTION
				"Username for SAPS FTP access.                                                             
				
				Read-access to this attribute will deliver 20 times sign '-'  "
			::= { sheSystemSwMaintenanceControl 9 }

		
		sheSystemSwmControlSapsPassword OBJECT-TYPE
			SYNTAX OCTET STRING (SIZE (0..20))
			MAX-ACCESS read-write
			STATUS current
			DESCRIPTION
				"Password for SAPS FTP access.                                                              
				
				Read-access to this attribute will deliver 20 times sign '-'  "
			::= { sheSystemSwMaintenanceControl 10 }

		
		sheSystemSwmControlAdminState OBJECT-TYPE
			SYNTAX SheSystemAdminState
			MAX-ACCESS read-write
			STATUS current
			DESCRIPTION
				"This set the current usage of automatic sw upgrade.
				The following states are supported:
				
				unlocked(1)  -> saps handling used
				locked(2)    -> saps handling not used (default)
				
				"
			::= { sheSystemSwMaintenanceControl 11 }

		
		sheSystemSwMaintenanceNotifications OBJECT IDENTIFIER ::= { sheSystemSwMaintenance 4 }

		
		sheSystemSwmBaseSet NOTIFICATION-TYPE
			OBJECTS { sheSystemSwmControlStatus, sheSystemSwmControlReqResult, sheSystemSwmControlTimeStamp }
			STATUS current
			DESCRIPTION 
				"Configuration trap for SAPS basic ftp access settings."
			::= { sheSystemSwMaintenanceNotifications 1 }

		
		sheSystemSwmAdminStateSet NOTIFICATION-TYPE
			OBJECTS { sheSystemSwmControlStatus, sheSystemSwmControlReqResult, sheSystemSwmControlTimeStamp, sheSystemSwmAdminState }
			STATUS current
			DESCRIPTION 
				"Configuration trap for SAPS basic admin state settings."
			::= { sheSystemSwMaintenanceNotifications 2 }

		
		sheSystemReadSAPSContentFileReady NOTIFICATION-TYPE
			OBJECTS { sheSystemSwmControlStatus, sheSystemSwmControlReqResult, sheSystemSwmControlTimeStamp }
			STATUS current
			DESCRIPTION 
				"Result trap for request of new SAPS file from server."
			::= { sheSystemSwMaintenanceNotifications 3 }

		
		sheSystemSwmReadyForReset NOTIFICATION-TYPE
			OBJECTS { sheSystemSwmControlStatus, sheSystemSwmControlReqResult, sheSystemSwmControlTimeStamp, sheSystemSwmTEntPhysicalIndex }
			STATUS current
			DESCRIPTION 
				"Trap will be send after succesfull SwUpgrade for a single card if a sw upgrade
				was started without automatic load activation."
			::= { sheSystemSwMaintenanceNotifications 4 }

		
		sheSystemSwmFTPError NOTIFICATION-TYPE
			OBJECTS { sheSystemSwmControlStatus, sheSystemSwmControlReqResult, sheSystemSwmControlTimeStamp }
			STATUS current
			DESCRIPTION 
				"Result trap for sw upgrade FTP access."
			::= { sheSystemSwMaintenanceNotifications 5 }

		
		sheSystemSwmUpgradeStartResult NOTIFICATION-TYPE
			OBJECTS { sheSystemSwmControlRequest, sheSystemSwmControlStatus, sheSystemSwmControlReqResult, sheSystemSwmControlTimeStamp }
			STATUS current
			DESCRIPTION 
				"Configuration result trap for long running command."
			::= { sheSystemSwMaintenanceNotifications 6 }

		
		sheSystemSwmCurrentStatusChanged NOTIFICATION-TYPE
			OBJECTS { sheSystemSwmControlTimeStamp, sheSystemSwmCurrentStatus }
			STATUS current
			DESCRIPTION 
				"The current operational status of the automatic sw upgrade process changed."
			::= { sheSystemSwMaintenanceNotifications 7 }

		
		sheSystemSwMaintenanceAlarms OBJECT IDENTIFIER ::= { sheSystemSwMaintenance 5 }

		
		sheSystemSwmFtpAccessError NOTIFICATION-TYPE
			OBJECTS { sheAlarmTimeAndDate, sheAlarmReportingSource, sheAlarmReportingSourceType, sheAlarmSeverity }
			STATUS current
			DESCRIPTION 
				"Alarm will be set because of failures during read or write during the NE internal 
				FTP communication. A successful ftp process will clear this alarm.
				
				Alarm will be used by manual download and automatic saps upgrade."
			::= { sheSystemSwMaintenanceAlarms 1 }

		
		sheSystemSwmFtpExternalAccessError NOTIFICATION-TYPE
			OBJECTS { sheAlarmTimeAndDate, sheAlarmReportingSource, sheAlarmReportingSourceType, sheAlarmSeverity }
			STATUS current
			DESCRIPTION 
				"Alarm will be set because of failures during read or write during the NE external 
				FTP communication (access to external ftp server failed).
				A successful ftp process will clear this alarm.
				
				Alarm will be used by manual download and automatic saps upgrade."
			::= { sheSystemSwMaintenanceAlarms 2 }

		
		sheSystemSwmStatusError NOTIFICATION-TYPE
			OBJECTS { sheAlarmTimeAndDate, sheAlarmReportingSource, sheAlarmReportingSourceType, sheAlarmSeverity }
			STATUS current
			DESCRIPTION 
				"Alarm will be set because of failures during automatic sw upgrade process which
				force a temporary switch off for this process.
				
				A restart could be triggered by the following command's:
				setSwmAdminState(51)
				swmUpgrStartRequest(100)
				swmUpgrStartRequestNoReset(101)
				"
			::= { sheSystemSwMaintenanceAlarms 3 }

		
		sheSystemDbMaintenance OBJECT IDENTIFIER ::= { sheSystemMaintenance 2 }

		
		sheSystemDbMaintenanceBase OBJECT IDENTIFIER ::= { sheSystemDbMaintenance 1 }

		
		sheSystemDbmServerAddr OBJECT-TYPE
			SYNTAX OCTET STRING (SIZE (0..20))
			MAX-ACCESS read-only
			STATUS current
			DESCRIPTION
				"Address of DB FTP server (dotted notation)."
			::= { sheSystemDbMaintenanceBase 1 }

		
		sheSystemDbmPathName OBJECT-TYPE
			SYNTAX OCTET STRING (SIZE (0..128))
			MAX-ACCESS read-only
			STATUS current
			DESCRIPTION
				"Path name of DB backup files on FTP server. 
				This path should be set relative to the ftp-server root.
				Use only linux notation ( / ). 
				
				Spaces in pathnames are not allowed, because of possible problems with
				different FTP implementations (client and/or server)!!"
			::= { sheSystemDbMaintenanceBase 2 }

		
		sheSystemDbmRemoteBackupAdminState OBJECT-TYPE
			SYNTAX SheSystemAdminState
			MAX-ACCESS read-only
			STATUS current
			DESCRIPTION
				"This state describes the current usage of automatic remote db backup.
				The following states are supported:
				
				unlocked(1)  -> remote db backup handling used
				locked(2)    -> remote db backup handling not used (default)"
			DEFVAL { 2 }
			::= { sheSystemDbMaintenanceBase 3 }

		
		sheSystemDbmBackupStartTime OBJECT-TYPE
			SYNTAX Unsigned32 (0..1439)
			UNITS "minute"
			MAX-ACCESS read-only
			STATUS current
			DESCRIPTION
				"Start time basis for remote DB backup after system restart, backup timer 
				reconfigurations or system clock reset.
				The first backup will be started at this time + sheSystemDbmBackupPeriod and
				will then be repeated each sheSystemDbmBackupPeriod.
				Range: 0 (0 am) .. 1439 (23.59 pm). 
				Default: 0  
				Reminder: NE uses always a UTC time base."
			DEFVAL { 0 }
			::= { sheSystemDbMaintenanceBase 4 }

		
		sheSystemDbmBackupPeriod OBJECT-TYPE
			SYNTAX Unsigned32 (1..48)
			UNITS "hour"
			MAX-ACCESS read-only
			STATUS current
			DESCRIPTION
				"Interval between two remote backup operations in hours. 
				Backup is started only if there were relevant configuration
				changes during the last period.
				Default: 24 hours "
			DEFVAL { 24 }
			::= { sheSystemDbMaintenanceBase 5 }

		
		sheSystemDbmBackupWaitingPeriod OBJECT-TYPE
			SYNTAX Unsigned32 (1..59)
			UNITS "minute"
			MAX-ACCESS read-only
			STATUS current
			DESCRIPTION
				"Waiting period in minutes before next local backup, in case of configuration changes.
				Default value : 5 minutes. "
			DEFVAL { 5 }
			::= { sheSystemDbMaintenanceBase 6 }

		
		sheSystemDbmBackupMaxFileNumber OBJECT-TYPE
			SYNTAX Unsigned32 (1..32)
			MAX-ACCESS read-only
			STATUS current
			DESCRIPTION
				"This number describes the maximum set of different backup files on the remote ftp site.
				Default number is 5."
			DEFVAL { 5 }
			::= { sheSystemDbMaintenanceBase 7 }

		
		sheSystemDbmLocalBackupAdminState OBJECT-TYPE
			SYNTAX SheSystemAdminState
			MAX-ACCESS read-only
			STATUS current
			DESCRIPTION
				"This value administrate the automatic local db backup after sheSystemDbmBackupWaitingPeriod
				in case of configuration actions.
				Default: unlocked  (automatic local backup is enabled)"
			DEFVAL { 1 }
			::= { sheSystemDbMaintenanceBase 8 }

		
		sheSystemDbBackupFilesTable OBJECT-TYPE
			SYNTAX SEQUENCE OF SheSystemDbBackupFilesEntry
			MAX-ACCESS not-accessible
			STATUS current
			DESCRIPTION
				" Table shows the DB backup files at the FTP server 
				with time and date of their creation.
				The table is empty per default and can be updated 
				with user command refreshDbBackupFilesTable.
				This command searches all existing DB backup files
				at the FTP server. "
			::= { sheSystemDbMaintenance 2 }

		
--   info-IMPL:    V3.0->
		sheSystemDbBackupFilesEntry OBJECT-TYPE
			SYNTAX SheSystemDbBackupFilesEntry
			MAX-ACCESS not-accessible
			STATUS current
			DESCRIPTION
				" Entry of the xldv20DbBackupFilesTable.
				Notifications :  . "
			INDEX { sheSystemDbBackupFileIndex }
			::= { sheSystemDbBackupFilesTable 1 }

		
		SheSystemDbBackupFilesEntry ::=
			SEQUENCE { 
				sheSystemDbBackupFileIndex
					Unsigned32,
				sheSystemDbBackupFileName
					DisplayString,
				sheSystemDbBackupFileTimeStamp
					Unsigned32
			 }

		sheSystemDbBackupFileIndex OBJECT-TYPE
			SYNTAX Unsigned32 (1..32)
			MAX-ACCESS read-only
			STATUS current
			DESCRIPTION
				"Unique value to identify an entry of this table. "
			::= { sheSystemDbBackupFilesEntry 1 }

		
		sheSystemDbBackupFileName OBJECT-TYPE
			SYNTAX DisplayString (SIZE (0..128))
			MAX-ACCESS read-only
			STATUS current
			DESCRIPTION
				" The name of the DB backup file. "
			::= { sheSystemDbBackupFilesEntry 2 }

		
		sheSystemDbBackupFileTimeStamp OBJECT-TYPE
			SYNTAX Unsigned32
			UNITS "sec"
			MAX-ACCESS read-only
			STATUS current
			DESCRIPTION
				" The time stamp of the DB backup file, i.e. the time and
				date when the DB backup file has been created. "
			::= { sheSystemDbBackupFilesEntry 3 }

		
--   ==============================================================
-- D a t a B a s e   M a n a g e m e n t   G r o u p
-- ==============================================================
-- --------------------------------------------------------------
--       DataBase Management control subgroup
-- --------------------------------------------------------------
		sheSystemDbmControl OBJECT IDENTIFIER ::= { sheSystemDbMaintenance 3 }

		
--  This managed entity manages the control request for storage
-- of the database.
		sheSystemDbmControlRequest OBJECT-TYPE
			SYNTAX SheSystemMaintenanceControlReq
			MAX-ACCESS read-write
			STATUS current
			DESCRIPTION
				"  Database Management commands :
				
				setSystemMaintenanceBase:
				- Set needed ftp access information for automatic DB request's.
				notifications: 
				  sheSystemDbmBaseSet
				
				backupDb : 
				- The command for a manual database backup
				  into the FEPROM of the DSLAM and to the FTP server.
				  The return value commExecStarted indicates the beginning
				  of DB storage.
				notification:
				 sheSystemDbmResult
				 
				refreshDbBackupFilesTable :
				- The DSLAM supports several
				  backup files. The command retrieves the backup files 
				  at the FTP server and provides their file names and  
				  time and date of creation in the table sheSystemDbBackFilesTable.
				notification:
				 sheSystemRefreshDbmBackupFilesTable
				 
				dbReloadSpecificFile:
				- Reload a specific file from sheSystemDbBackFilesTable
				  into the DSLAM. If successful, the CXU perform a reset 
				  for activation.
				notification:
				 sheSystemDbmResult
				
				setBackupPeriod:
				- Configure the backup period settings for automatic remote 
				  backup to ftp server and local backup to EEPROM.   
				notification:
				 sheSystemDbmBackupPeriodSet
				
				setLocalBackupAdminState:
				- Enables or disables the automatic local backup feature.
				notification:
				 sheSystemDbmLocalBackupAdminstateSet
				
				setRemoteBackupAdminState:
				- Enables or disables the automatic remote backup feature.
				notification:
				 sheSystemDbmRemoteBackupAdminstateSet
				
				"
			::= { sheSystemDbmControl 1 }

		
		sheSystemDbmControlStatus OBJECT-TYPE
			SYNTAX SheControlStatusType
			MAX-ACCESS read-only
			STATUS current
			DESCRIPTION
				" The status of the control request. "
			::= { sheSystemDbmControl 2 }

		
		sheSystemDbmControlTimer OBJECT-TYPE
			SYNTAX Unsigned32
			MAX-ACCESS read-only
			STATUS current
			DESCRIPTION
				" The maximum wait time for the manager when a DB storage
				request cannot be executed immediately (value commExecStarted
				in the result attribute sheSystemMaintenanceControlReqResult).
				The manager reads this value from the DSLAM.
				The end of request indicates the trap sheSystemTrDbBackup. "
			::= { sheSystemDbmControl 3 }

		
		sheSystemDbmControlReqResultLocal OBJECT-TYPE
			SYNTAX SheSystemMaintenanceControlReqResult
			MAX-ACCESS read-only
			STATUS current
			DESCRIPTION
				" The result of the local backup request. "
			::= { sheSystemDbmControl 4 }

		
		sheSystemDbmControlReqResultRemote OBJECT-TYPE
			SYNTAX SheSystemMaintenanceControlReqResult
			MAX-ACCESS read-only
			STATUS current
			DESCRIPTION
				" The result of the last remote backup request. "
			::= { sheSystemDbmControl 5 }

		
		sheSystemDbmControlTimeStamp OBJECT-TYPE
			SYNTAX Unsigned32
			UNITS "sec"
			MAX-ACCESS read-only
			STATUS current
			DESCRIPTION
				" The time stamp of the last command (end of command). "
			::= { sheSystemDbmControl 6 }

		
		sheSystemDbmControlServerAddr OBJECT-TYPE
			SYNTAX OCTET STRING (SIZE (0..20))
			MAX-ACCESS read-write
			STATUS current
			DESCRIPTION
				"Address of DB FTP server (dotted notation)."
			::= { sheSystemDbmControl 7 }

		
		sheSystemDbmControlPathName OBJECT-TYPE
			SYNTAX OCTET STRING (SIZE (0..128))
			MAX-ACCESS read-write
			STATUS current
			DESCRIPTION
				"Path name of DB backup files on FTP server. 
				This path should be set relative to the ftp-server root.
				Use only linux notation ( / ). 
				
				Spaces in pathnames are not allowed, because of possible problems with
				different FTP implementations (client and/or server)!!"
			::= { sheSystemDbmControl 8 }

		
		sheSystemDbmControlUsrName OBJECT-TYPE
			SYNTAX OCTET STRING (SIZE (0..20))
			MAX-ACCESS read-write
			STATUS current
			DESCRIPTION
				"Username for DB backup FTP access.                                                             
				
				Read-access to this attribute will deliver 20 times sign '-'  "
			::= { sheSystemDbmControl 9 }

		
		sheSystemDbmControlPassword OBJECT-TYPE
			SYNTAX OCTET STRING (SIZE (0..20))
			MAX-ACCESS read-write
			STATUS current
			DESCRIPTION
				"Password for DB backup FTP access.                                                              
				
				Read-access to this attribute will deliver 20 times sign '-'  "
			::= { sheSystemDbmControl 10 }

		
		sheSystemDbmControlRemoteBackupAdminState OBJECT-TYPE
			SYNTAX SheSystemAdminState
			MAX-ACCESS read-write
			STATUS current
			DESCRIPTION
				"This set the current usage of automatic remote db backup.
				The following states are supported:
				
				unlocked(1)  -> remote db backup handling used
				locked(2)    -> remote db backup handling not used (default)"
			::= { sheSystemDbmControl 11 }

		
		sheSystemDbmControlBackupStartTime OBJECT-TYPE
			SYNTAX Unsigned32 (0..1439)
			UNITS "minute"
			MAX-ACCESS read-write
			STATUS current
			DESCRIPTION
				"Start time basis for remote DB backup after system restart, backup timer 
				reconfigurations or system clock reset.
				The first backup will be started at this time + sheSystemDbmBackupPeriod and
				will then be repeated each sheSystemDbmBackupPeriod.
				Range: 0 (0 am) .. 1439 (23.59 pm).
				Reminder: NE uses always a UTC time base.
				"
			::= { sheSystemDbmControl 12 }

		
		sheSystemDbmControlBackupPeriod OBJECT-TYPE
			SYNTAX Unsigned32 (1..48)
			UNITS "hour"
			MAX-ACCESS read-write
			STATUS current
			DESCRIPTION
				"Interval between two remote backup operations in hours. 
				Backup is started only if there were relevant configuration
				changes during the last period."
			::= { sheSystemDbmControl 13 }

		
		sheSystemDbmControlBackupWaitingPeriod OBJECT-TYPE
			SYNTAX Unsigned32 (1..59)
			UNITS "minute"
			MAX-ACCESS read-write
			STATUS current
			DESCRIPTION
				"Waiting period in minutes before next local backup, in case of configuration changes."
			::= { sheSystemDbmControl 14 }

		
		sheSystemDbmControlBackupMaxFileNumber OBJECT-TYPE
			SYNTAX Unsigned32 (1..32)
			MAX-ACCESS read-write
			STATUS current
			DESCRIPTION
				"This number describes the maximum set of different backup files on the remote ftp site.
				"
			::= { sheSystemDbmControl 15 }

		
		sheSystemDbmControlLocalBackupAdminState OBJECT-TYPE
			SYNTAX SheSystemAdminState
			MAX-ACCESS read-write
			STATUS current
			DESCRIPTION
				"This value administrate the automatic local db backup after sheSystemDbmBackupWaitingPeriod
				in case of configuration actions.
				Default: unlocked  (automatic local backup is enabled)"
			::= { sheSystemDbmControl 16 }

		
		sheSystemDbmControlBackupFileIndex OBJECT-TYPE
			SYNTAX Integer32 (1..32)
			MAX-ACCESS read-write
			STATUS current
			DESCRIPTION
				"The index selects the DB backup file in the sheSystemDbBackupFilesTable which shall be loaded
				into the DSLAM from the FTP server with user command dbReloadSpecificFile. "
			::= { sheSystemDbmControl 17 }

		
		sheSystemDbMaintenanceNotifications OBJECT IDENTIFIER ::= { sheSystemDbMaintenance 4 }

		
		sheSystemDbmBaseSet NOTIFICATION-TYPE
			OBJECTS { sheSystemDbmControlStatus, sheSystemDbmControlTimeStamp, sheSystemDbmControlReqResultRemote, sheSystemDbmControlServerAddr, sheSystemDbmControlPathName
				 }
			STATUS current
			DESCRIPTION 
				"Configuration trap for remote DB basic access settings."
			::= { sheSystemDbMaintenanceNotifications 1 }

		
		sheSystemDbmResult NOTIFICATION-TYPE
			OBJECTS { sheSystemDbmControlTimeStamp, sheSystemDbmControlReqResultLocal, sheSystemDbmControlReqResultRemote, sheSystemDbmControlStatus }
			STATUS current
			DESCRIPTION 
				"Indicates the end and the result of the database backup or restore."
			::= { sheSystemDbMaintenanceNotifications 3 }

		
		sheSystemDbmBackupFilesTableRefreshed NOTIFICATION-TYPE
			OBJECTS { sheSystemDbmControlTimeStamp, sheSystemDbmControlStatus, sheSystemDbmControlReqResultRemote }
			STATUS current
			DESCRIPTION 
				"Indicates end of user command refreshDbmBackupFilesTable."
			::= { sheSystemDbMaintenanceNotifications 4 }

		
		sheSystemDbmBackupPeriodSet NOTIFICATION-TYPE
			OBJECTS { sheSystemDbmControlTimeStamp, sheSystemDbmControlStatus, sheSystemDbmBackupMaxFileNumber, sheSystemDbmControlReqResultLocal, sheSystemDbmBackupPeriod, 
				sheSystemDbmBackupStartTime, sheSystemDbmBackupWaitingPeriod }
			STATUS current
			DESCRIPTION 
				"Settings for automatic backup period are set."
			::= { sheSystemDbMaintenanceNotifications 5 }

		
		sheSystemDbmLocalBackupAdminstateSet NOTIFICATION-TYPE
			OBJECTS { sheSystemDbmControlTimeStamp, sheSystemDbmControlReqResultLocal, sheSystemDbmControlStatus, sheSystemDbmLocalBackupAdminState }
			STATUS current
			DESCRIPTION 
				"Configuration notification for local db backup."
			::= { sheSystemDbMaintenanceNotifications 6 }

		
		sheSystemDbmRemoteBackupAdminstateSet NOTIFICATION-TYPE
			OBJECTS { sheSystemDbmControlTimeStamp, sheSystemDbmControlStatus, sheSystemDbmControlReqResultRemote, sheSystemDbmControlRemoteBackupAdminState }
			STATUS current
			DESCRIPTION 
				"Configuration notification for local db backup."
			::= { sheSystemDbMaintenanceNotifications 7 }

		
		sheSystemDbMaintenanceAlarms OBJECT IDENTIFIER ::= { sheSystemDbMaintenance 5 }

		
		sheSystemLocalDbInvalid NOTIFICATION-TYPE
			OBJECTS { sheAlarmTimeAndDate, sheAlarmReportingSource, sheAlarmReportingSourceType, sheAlarmSeverity }
			STATUS current
			DESCRIPTION 
				"Alarm will be set if the local DB is invalid because of failures during
				read/write local DB or if the local DB was not updated yet after a 
				configuration sequence."
			::= { sheSystemDbMaintenanceAlarms 1 }

		
		sheSystemRemoteDbInvalid NOTIFICATION-TYPE
			OBJECTS { sheAlarmTimeAndDate, sheAlarmReportingSource, sheAlarmReportingSourceType, sheAlarmSeverity }
			STATUS current
			DESCRIPTION 
				"Alarm will be set if the remote DB is invalid because of failures during 
				read/write remote DB or if the remote DB was not updated yet after a 
				configuration sequence."
			::= { sheSystemDbMaintenanceAlarms 2 }

		
		sheSystemDbFtpAccessError NOTIFICATION-TYPE
			OBJECTS { sheAlarmTimeAndDate, sheAlarmReportingSource, sheAlarmReportingSourceType, sheAlarmSeverity }
			STATUS current
			DESCRIPTION 
				"Alarm will be set because of failures during read or write on DB Ftp server."
			::= { sheSystemDbMaintenanceAlarms 3 }

		
-- New supported with SHE R2.6.
		sheSystemIpConfig OBJECT IDENTIFIER ::= { sheSystem 12 }

		
		sheSystemIpHostTable OBJECT-TYPE
			SYNTAX SEQUENCE OF SheSystemIpHostEntry
			MAX-ACCESS not-accessible
			STATUS current
			DESCRIPTION
				"This table contains attributes for each IP host interface."
			::= { sheSystemIpConfig 1 }

		
		sheSystemIpHostEntry OBJECT-TYPE
			SYNTAX SheSystemIpHostEntry
			MAX-ACCESS not-accessible
			STATUS current
			DESCRIPTION
				"An entry represents a set of configurations in sheSystemIpHostTable. 
				"
			INDEX { sheSystemIpHostIndex }
			::= { sheSystemIpHostTable 1 }

		
		SheSystemIpHostEntry ::=
			SEQUENCE { 
				sheSystemIpHostIndex
					Unsigned32,
				sheSystemIpHostName
					DisplayString,
				sheSystemIpHostUseDhcp
					SheSystemIpHostUseDhcpType,
				sheSystemIpHostIpAddress
					IpAddress,
				sheSystemIpHostSubnetMask
					IpAddress,
				sheSystemIpHostOuterVlanId
					Unsigned32,
				sheSystemIpHostInnerVlanId
					Unsigned32,
				sheSystemIpHostDescription
					OCTET STRING,
				sheSystemIpHostOuterVlanPriority
					Unsigned32,
				sheSystemIpHostInnerVlanPriority
					Unsigned32
			 }

		sheSystemIpHostIndex OBJECT-TYPE
			SYNTAX Unsigned32
			MAX-ACCESS read-only
			STATUS current
			DESCRIPTION
				"Table index. Each index uniquely identifies one Ip host table entry."
			::= { sheSystemIpHostEntry 1 }

		
		sheSystemIpHostName OBJECT-TYPE
			SYNTAX DisplayString (SIZE (1..32))
			MAX-ACCESS read-only
			STATUS current
			DESCRIPTION
				"A descriptional name that uniquely identifies a entry of this table.
				The name is selected by the NE and identify the interface also on CLI."
			::= { sheSystemIpHostEntry 2 }

		
		sheSystemIpHostUseDhcp OBJECT-TYPE
			SYNTAX SheSystemIpHostUseDhcpType
			MAX-ACCESS read-only
			STATUS current
			DESCRIPTION
				"Either to use Dhcp or not. If set to 0 (default) no DHCP will be used.
				Valid values:
				noUseDhcp(0),
				useDhcp(1)
				
				Note: Currently no support planed."
			DEFVAL { noUseDhcp }
			::= { sheSystemIpHostEntry 3 }

		
		sheSystemIpHostIpAddress OBJECT-TYPE
			SYNTAX IpAddress
			MAX-ACCESS read-only
			STATUS current
			DESCRIPTION
				"IpAddress. Assigned by operator request or by DHCP if used."
			::= { sheSystemIpHostEntry 4 }

		
		sheSystemIpHostSubnetMask OBJECT-TYPE
			SYNTAX IpAddress
			MAX-ACCESS read-only
			STATUS current
			DESCRIPTION
				"subnet mask"
			::= { sheSystemIpHostEntry 5 }

		
		sheSystemIpHostOuterVlanId OBJECT-TYPE
			SYNTAX Unsigned32 (0 | 1..4093)
			MAX-ACCESS read-only
			STATUS current
			DESCRIPTION
				"The host vlan for this ip interface which should be used as outer tag in double tagging mode
				or in single tagging mode.
				Set to 0 if no host VLAN should be used."
			DEFVAL { 0 }
			::= { sheSystemIpHostEntry 6 }

		
		sheSystemIpHostInnerVlanId OBJECT-TYPE
			SYNTAX Unsigned32 (0 | 1..4093)
			MAX-ACCESS read-only
			STATUS current
			DESCRIPTION
				"The host vlan for this ip interface which should be used as inner tag if the NE
				run in double tagging mode.
				Set to 0 if no host VLAN should be used or if the NE uses single tag mode."
			DEFVAL { 0 }
			::= { sheSystemIpHostEntry 7 }

		
		sheSystemIpHostDescription OBJECT-TYPE
			SYNTAX OCTET STRING (SIZE (0..32))
			MAX-ACCESS read-only
			STATUS current
			DESCRIPTION
				"Could describe who uses this ip interface. This description could be used
				by the operator to store information about the intended interface usage. The
				parameter will not be evaluated by the NE."
			::= { sheSystemIpHostEntry 8 }

		
		sheSystemIpHostOuterVlanPriority OBJECT-TYPE
			SYNTAX Unsigned32 (0..7)
			MAX-ACCESS read-only
			STATUS current
			DESCRIPTION
				"The used .1p priority for host vlan of this ip interface which should be used as outer tag in double tagging mode
				or in single tagging mode.
				Setting is don't care if no host VLAN should be used.
				
				New with R2.8 maintenance."
			DEFVAL { 7 }
			::= { sheSystemIpHostEntry 9 }

		
		sheSystemIpHostInnerVlanPriority OBJECT-TYPE
			SYNTAX Unsigned32 (0..7)
			MAX-ACCESS read-only
			STATUS current
			DESCRIPTION
				"The used .1p priority for host vlan of this ip interface which should be used as inner tag if the NE
				run in double tagging mode.
				Setting is don't care if no host VLAN should be used.
				
				New with R2.8 maintenance."
			DEFVAL { 7 }
			::= { sheSystemIpHostEntry 10 }

		
		sheSystemIpHostControl OBJECT IDENTIFIER ::= { sheSystemIpConfig 2 }

		
		sheSystemIpHostControlRequest OBJECT-TYPE
			SYNTAX SheSystemIpControlReqType
			MAX-ACCESS read-write
			STATUS current
			DESCRIPTION
				"The request of a user command.
				createSystemIpHost    (50)
				      sheSystemIpHostControlUseDhcp
				      sheSystemIpHostControlIpAddress
				      sheSystemIpHostControlSubnetMask
				      sheSystemIpHostControlOuterVlanId
				      sheSystemIpHostControlInnerVlanId
				      sheSystemIpHostControlDescription
				      sheSystemIpHostControlOuterVlanPriority      (new with R2.8 maintenance)
				      sheSystemIpHostControlInnerVlanPriority      (new with R2.8 maintenance)      
				 
				deleteSystemIpHost    (51), 
				      sheSystemIpHostControlIndex 
				 
				modifySystemIpHost    (52), 
				      sheSystemIpHostControlIndex 
				      sheSystemIpHostControlUseDhcp
				      sheSystemIpHostControlIpAddress
				      sheSystemIpHostControlSubnetMask
				      sheSystemIpHostControlOuterVlanId
				      sheSystemIpHostControlInnerVlanId
				      sheSystemIpHostControlDescription
				      sheSystemIpHostControlOuterVlanPriority      (new with R2.8 maintenance)    
				      sheSystemIpHostControlInnerVlanPriority      (new with R2.8 maintenance)
				"
			::= { sheSystemIpHostControl 1 }

		
		sheSystemIpHostControlIndex OBJECT-TYPE
			SYNTAX Unsigned32
			MAX-ACCESS read-write
			STATUS current
			DESCRIPTION
				"Table index"
			::= { sheSystemIpHostControl 2 }

		
		sheSystemIpHostControlStatus OBJECT-TYPE
			SYNTAX SheControlStatusType
			MAX-ACCESS read-only
			STATUS current
			DESCRIPTION
				"The status of a user command."
			::= { sheSystemIpHostControl 3 }

		
		sheSystemIpHostControlReqResult OBJECT-TYPE
			SYNTAX SheSystemControlRequestResultType
			MAX-ACCESS read-only
			STATUS current
			DESCRIPTION
				"The result of the last user command."
			::= { sheSystemIpHostControl 4 }

		
		sheSystemIpHostControlTimer OBJECT-TYPE
			SYNTAX Gauge32
			MAX-ACCESS read-only
			STATUS current
			DESCRIPTION
				"The maximum wait time for the manager for a long running user command."
			::= { sheSystemIpHostControl 5 }

		
		sheSystemIpHostControlTimeStamp OBJECT-TYPE
			SYNTAX Unsigned32
			UNITS "sec"
			MAX-ACCESS read-only
			STATUS current
			DESCRIPTION
				"The time stamp of the last command (end of command)."
			::= { sheSystemIpHostControl 6 }

		
		sheSystemIpHostControlName OBJECT-TYPE
			SYNTAX DisplayString (SIZE (1..32))
			MAX-ACCESS read-only
			STATUS current
			DESCRIPTION
				"A descriptional name that uniquely identifies an entry of this table. 
				This name was selected by the NE and identifies the interface also on CLI."
			::= { sheSystemIpHostControl 7 }

		
		sheSystemIpHostControlUseDhcp OBJECT-TYPE
			SYNTAX SheSystemIpHostUseDhcpType
			MAX-ACCESS read-write
			STATUS current
			DESCRIPTION
				"Either to use Dhcp or not. If set to 0 (default) no DHCP will be used.
				Valid values:
				noUseDhcp(0),
				useDhcp(1)
				
				Note: Currently no support planed."
			::= { sheSystemIpHostControl 8 }

		
		sheSystemIpHostControlIpAddress OBJECT-TYPE
			SYNTAX IpAddress
			MAX-ACCESS read-write
			STATUS current
			DESCRIPTION
				"Ipaddress if no Dhcp is used."
			::= { sheSystemIpHostControl 9 }

		
		sheSystemIpHostControlSubnetMask OBJECT-TYPE
			SYNTAX IpAddress
			MAX-ACCESS read-write
			STATUS current
			DESCRIPTION
				"Subnet mask"
			::= { sheSystemIpHostControl 10 }

		
		sheSystemIpHostControlOuterVlanId OBJECT-TYPE
			SYNTAX Unsigned32 (0 | 1..4093)
			MAX-ACCESS read-write
			STATUS current
			DESCRIPTION
				"The host vlan for this ip interface which should be used as outer tag in double tagging mode
				or in single tagging mode.
				Set to 0 if no host VLAN should be used."
			::= { sheSystemIpHostControl 11 }

		
		sheSystemIpHostControlInnerVlanId OBJECT-TYPE
			SYNTAX Unsigned32 (0 | 1..4093)
			MAX-ACCESS read-write
			STATUS current
			DESCRIPTION
				"The host vlan for this ip interface which should be used as inner tag if the NE
				run in double tagging mode.
				Set to 0 if no host VLAN should be used or if the NE uses single tag mode."
			::= { sheSystemIpHostControl 12 }

		
		sheSystemIpHostControlDescription OBJECT-TYPE
			SYNTAX OCTET STRING (SIZE (0..32))
			MAX-ACCESS read-write
			STATUS current
			DESCRIPTION
				"Could describe who uses this ip interface. This description could be used
				by the operator to store information about the intended interface usage. The
				parameter will not be evaluated by the NE."
			::= { sheSystemIpHostControl 13 }

		
		sheSystemIpHostControlOuterVlanPriority OBJECT-TYPE
			SYNTAX Unsigned32 (0..7)
			MAX-ACCESS read-write
			STATUS current
			DESCRIPTION
				"The used .1p priority for host vlan of this ip interface which should be used as outer tag in double tagging mode
				or in single tagging mode.
				Setting is don't care if no host VLAN should be used.
				
				New with R2.8 maintenance."
			::= { sheSystemIpHostControl 14 }

		
		sheSystemIpHostControlInnerVlanPriority OBJECT-TYPE
			SYNTAX Unsigned32 (0..7)
			MAX-ACCESS read-write
			STATUS current
			DESCRIPTION
				"The used .1p priority for host vlan of this ip interface which should be used as inner tag if the NE
				run in double tagging mode.
				Setting is don't care if no host VLAN should be used.
				
				New with R2.8 maintenance."
			::= { sheSystemIpHostControl 15 }

		
		sheSystemIpRouteTable OBJECT-TYPE
			SYNTAX SEQUENCE OF SheSystemIpRouteEntry
			MAX-ACCESS not-accessible
			STATUS current
			DESCRIPTION
				"This table contains attributes for each static configured IP route.
				Learned routes from routing protocols will not be shown here!"
			::= { sheSystemIpConfig 3 }

		
		sheSystemIpRouteEntry OBJECT-TYPE
			SYNTAX SheSystemIpRouteEntry
			MAX-ACCESS not-accessible
			STATUS current
			DESCRIPTION
				"An entry represents a set of configurations in sheSystemIpRouteTable. 
				"
			INDEX { sheSystemIpRouteIndex }
			::= { sheSystemIpRouteTable 1 }

		
		SheSystemIpRouteEntry ::=
			SEQUENCE { 
				sheSystemIpRouteIndex
					Unsigned32,
				sheSystemIpRouteName
					DisplayString,
				sheSystemIpRouteDestIpAddress
					IpAddress,
				sheSystemIpRouteSubnetMask
					IpAddress,
				sheSystemIpRouteGatewayIpAddress
					IpAddress,
				sheSystemIpRouteMetric
					Integer32
			 }

		sheSystemIpRouteIndex OBJECT-TYPE
			SYNTAX Unsigned32
			MAX-ACCESS read-only
			STATUS current
			DESCRIPTION
				"Table index. Each index uniquely identifies one an Ip route table entry."
			::= { sheSystemIpRouteEntry 1 }

		
		sheSystemIpRouteName OBJECT-TYPE
			SYNTAX DisplayString (SIZE (1..32))
			MAX-ACCESS read-only
			STATUS current
			DESCRIPTION
				"A describable name that uniquely identifies an  entry of this table.
				The name is user specified.
				Special characters like space ? . are not allowed."
			::= { sheSystemIpRouteEntry 2 }

		
		sheSystemIpRouteDestIpAddress OBJECT-TYPE
			SYNTAX IpAddress
			MAX-ACCESS read-only
			STATUS current
			DESCRIPTION
				"Destination IpAddress for this route."
			::= { sheSystemIpRouteEntry 4 }

		
		sheSystemIpRouteSubnetMask OBJECT-TYPE
			SYNTAX IpAddress
			MAX-ACCESS read-only
			STATUS current
			DESCRIPTION
				"subnet mask 
				"
			::= { sheSystemIpRouteEntry 5 }

		
		sheSystemIpRouteGatewayIpAddress OBJECT-TYPE
			SYNTAX IpAddress
			MAX-ACCESS read-only
			STATUS current
			DESCRIPTION
				"Gateway IpAddress for this route."
			::= { sheSystemIpRouteEntry 6 }

		
		sheSystemIpRouteMetric OBJECT-TYPE
			SYNTAX Integer32
			MAX-ACCESS read-only
			STATUS current
			DESCRIPTION
				"The routing metric for this route.
				If this metric is not used, its value should be set to -1."
			DEFVAL { -1 }
			::= { sheSystemIpRouteEntry 7 }

		
		sheSystemIpRouteControl OBJECT IDENTIFIER ::= { sheSystemIpConfig 4 }

		
		sheSystemIpRouteControlRequest OBJECT-TYPE
			SYNTAX SheSystemIpControlReqType
			MAX-ACCESS read-write
			STATUS current
			DESCRIPTION
				"The request of a user command.  
				createSystemIpRoute    (55), 
				   sheSystemIpRouteControlName 
				   sheSystemIpRouteControlDestIpAddress
				   sheSystemIpRouteControlGatewayIpAddress  			       	            
				   sheSystemIpRouteControlSubnetMask
				   sheSystemIpRouteControlMetric 			        	 
				         			   
				deleteSystemIpRoute    (56), 
				  sheSystemIpRouteControlIndex 
					 
				modifySystemIpRoute    (57), 
				  sheSystemIpRouteControlIndex 				              
				  sheSystemIpRouteControlDestIpAddress
				  sheSystemIpRouteControlGatewayIpAddress  			       	            
				  sheSystemIpRouteControlSubnetMask 
				  sheSystemIpRouteControlMetric"
			::= { sheSystemIpRouteControl 1 }

		
		sheSystemIpRouteControlIndex OBJECT-TYPE
			SYNTAX Unsigned32
			MAX-ACCESS read-write
			STATUS current
			DESCRIPTION
				"Table index"
			::= { sheSystemIpRouteControl 2 }

		
		sheSystemIpRouteControlStatus OBJECT-TYPE
			SYNTAX SheControlStatusType
			MAX-ACCESS read-only
			STATUS current
			DESCRIPTION
				"The status of a user command."
			::= { sheSystemIpRouteControl 3 }

		
		sheSystemIpRouteControlReqResult OBJECT-TYPE
			SYNTAX SheSystemControlRequestResultType
			MAX-ACCESS read-only
			STATUS current
			DESCRIPTION
				"The result of the last user command."
			::= { sheSystemIpRouteControl 4 }

		
		sheSystemIpRouteControlTimer OBJECT-TYPE
			SYNTAX Gauge32
			MAX-ACCESS read-only
			STATUS current
			DESCRIPTION
				"The maximum wait time for the manager for a  
				long running user command."
			::= { sheSystemIpRouteControl 5 }

		
		sheSystemIpRouteControlTimeStamp OBJECT-TYPE
			SYNTAX Unsigned32
			UNITS "sec"
			MAX-ACCESS read-only
			STATUS current
			DESCRIPTION
				"The time stamp of the last command (end of command)."
			::= { sheSystemIpRouteControl 6 }

		
		sheSystemIpRouteControlName OBJECT-TYPE
			SYNTAX DisplayString (SIZE (1..32))
			MAX-ACCESS read-write
			STATUS current
			DESCRIPTION
				"A describable name that uniquely identifies a entry of this table.
				The route name is user specified."
			::= { sheSystemIpRouteControl 7 }

		
		sheSystemIpRouteControlDestIpAddress OBJECT-TYPE
			SYNTAX IpAddress
			MAX-ACCESS read-write
			STATUS current
			DESCRIPTION
				"Destination Ipaddress."
			::= { sheSystemIpRouteControl 8 }

		
		sheSystemIpRouteControlSubnetMask OBJECT-TYPE
			SYNTAX IpAddress
			MAX-ACCESS read-write
			STATUS current
			DESCRIPTION
				"Subnet mask."
			::= { sheSystemIpRouteControl 9 }

		
		sheSystemIpRouteControlGatewayIpAddress OBJECT-TYPE
			SYNTAX IpAddress
			MAX-ACCESS read-write
			STATUS current
			DESCRIPTION
				"Gateway Ipaddress ."
			::= { sheSystemIpRouteControl 10 }

		
		sheSystemIpRouteControlMetric OBJECT-TYPE
			SYNTAX Integer32
			MAX-ACCESS read-write
			STATUS current
			DESCRIPTION
				"The routing metric for this route.
				If this metric is not used, its value should be
				set to -1."
			::= { sheSystemIpRouteControl 11 }

		
		sheSystemIpHostNotification OBJECT IDENTIFIER ::= { sheSystemIpConfig 5 }

		
		sheSystemIpHostCreated NOTIFICATION-TYPE
			OBJECTS { sheSystemIpHostControlIndex, sheSystemIpHostControlReqResult, sheSystemIpHostControlTimeStamp, sheSystemIpHostControlName, sheSystemIpHostControlUseDhcp, 
				sheSystemIpHostControlIpAddress, sheSystemIpHostControlSubnetMask, sheSystemIpHostControlOuterVlanId, sheSystemIpHostControlInnerVlanId, sheSystemIpHostControlDescription, 
				sheSystemIpHostControlOuterVlanPriority, sheSystemIpHostControlInnerVlanPriority }
			STATUS current
			DESCRIPTION 
				"Configuration trap."
			::= { sheSystemIpHostNotification 1 }

		
		sheSystemIpHostDeleted NOTIFICATION-TYPE
			OBJECTS { sheSystemIpHostControlIndex, sheSystemIpHostControlTimeStamp }
			STATUS current
			DESCRIPTION 
				"Configuration trap."
			::= { sheSystemIpHostNotification 2 }

		
		sheSystemIpHostModified NOTIFICATION-TYPE
			OBJECTS { sheSystemIpHostControlIndex, sheSystemIpHostControlReqResult, sheSystemIpHostControlTimeStamp, sheSystemIpHostControlName, sheSystemIpHostControlUseDhcp, 
				sheSystemIpHostControlIpAddress, sheSystemIpHostControlSubnetMask, sheSystemIpHostControlOuterVlanId, sheSystemIpHostControlInnerVlanId, sheSystemIpHostControlDescription, 
				sheSystemIpHostControlOuterVlanPriority, sheSystemIpHostControlInnerVlanPriority }
			STATUS current
			DESCRIPTION 
				"Configuration trap."
			::= { sheSystemIpHostNotification 3 }

		
		sheSystemIpRouteCreated NOTIFICATION-TYPE
			OBJECTS { sheSystemIpRouteControlIndex, sheSystemIpRouteControlReqResult, sheSystemIpRouteControlTimeStamp, sheSystemIpRouteControlName, sheSystemIpRouteControlDestIpAddress, 
				sheSystemIpRouteControlSubnetMask, sheSystemIpRouteControlGatewayIpAddress, sheSystemIpRouteControlMetric }
			STATUS current
			DESCRIPTION 
				"Configuration trap."
			::= { sheSystemIpHostNotification 4 }

		
		sheSystemIpRouteDeleted NOTIFICATION-TYPE
			OBJECTS { sheSystemIpRouteControlIndex, sheSystemIpRouteControlTimeStamp }
			STATUS current
			DESCRIPTION 
				"Configuration trap."
			::= { sheSystemIpHostNotification 5 }

		
		sheSystemIpRouteModified NOTIFICATION-TYPE
			OBJECTS { sheSystemIpRouteControlIndex, sheSystemIpRouteControlReqResult, sheSystemIpRouteControlTimeStamp, sheSystemIpRouteControlName, sheSystemIpRouteControlDestIpAddress, 
				sheSystemIpRouteControlSubnetMask, sheSystemIpRouteControlGatewayIpAddress, sheSystemIpRouteControlMetric }
			STATUS current
			DESCRIPTION 
				"Configuration trap."
			::= { sheSystemIpHostNotification 6 }

		
		sheSystemConformance OBJECT IDENTIFIER ::= { sheSystem 100 }

		
		sheSystemGroups OBJECT IDENTIFIER ::= { sheSystemConformance 1 }

		
		sheSystemGroup OBJECT-GROUP
			OBJECTS { sheSystemFeatureIndex, sheSystemFeatureName, sheSystemFileSwfIndex, sheSystemFileSwfFileName, sheSystemFileSwfTypeOfFile, 
				sheSystemFileSwfVersion, sheSystemFileSwfSize, sheSystemFileSwfTimeStamp, sheSystemDbBackupFileIndex, sheSystemDbBackupFileName, 
				sheSystemManagementSessionIndex, sheSystemManagementSessionType, sheSystemManagementSessionSnmpExpiredTime, sheSystemManagementSessionAddress, sheSystemDnsServerIndex, 
				sheSystemDnsServerAddr, sheSystemNtpClientServerIndex, sheSystemNtpClientServerName, sheSystemDbBackupFileTimeStamp, sheSystemSwmTIndex, 
				sheSystemSwmTCardType, sheSystemSwmTEntPhysicalIndex, sheSystemSwmTTimeStamp, sheSystemSwmTUpgradeState, sheSystemSwmTUpgradeResult, 
				sheSystemSwmTSwVersion, sheSystemSwmTSwVersionNeed }
			STATUS current
			DESCRIPTION 
				" "
			::= { sheSystemGroups 1 }

		
		sheSystemControlGroup OBJECT-GROUP
			OBJECTS { sheSystemVersion, sheSystemExternalTime, sheSystemStartupType, sheSystemTmnConnected, sheSystemLctConnected, 
				sheSystemControlRequest, sheSystemControlStatus, sheSystemControlTimer, sheSystemControlReqResult, sheSystemControlTimeStamp, 
				sheSystemControlExternalTime, sheSystemCliConnected, sheSystemFileControlRequest, sheSystemFileControlStatus, sheSystemFileControlTimer, 
				sheSystemFileControlReqResult, sheSystemFileControlTimeStamp, sheSystemFileControlTypeOfFile, sheSystemFileControlPathName, sheSystemFileControlFileName, 
				sheSystemFileControlCardType, sheSystemFileControlEntPhysicalIndex, sheSystemFileControlLoadStatus, sheSystemFileControlServerAddr, sheSystemFileControlUsrName, 
				sheSystemFileControlPassword, sheSystemNotificationCounter, sheSystemSwmSapsServerAddr, sheSystemSwmSapsPathName, sheSystemSwmSapsFileName, 
				sheSystemSwmAdminState, sheSystemSwmControlSapsServerAddr, sheSystemSwmControlSapsPathName, sheSystemSwmControlSapsFileName, sheSystemSwmControlSapsUsrName, 
				sheSystemSwmControlSapsPassword, sheSystemSwmControlAdminState, sheSystemDbmServerAddr, sheSystemDbmPathName, sheSystemDbmRemoteBackupAdminState, 
				sheSystemDbmBackupPeriod, sheSystemDbmBackupStartTime, sheSystemDbmBackupWaitingPeriod, sheSystemDbmBackupMaxFileNumber, sheSystemDbmLocalBackupAdminState, 
				sheSystemDbmControlRequest, sheSystemDbmControlStatus, sheSystemDbmControlTimer, sheSystemDbmControlReqResultLocal, sheSystemDbmControlReqResultRemote, 
				sheSystemDbmControlTimeStamp, sheSystemDbmControlServerAddr, sheSystemDbmControlPathName, sheSystemDbmControlUsrName, sheSystemDbmControlPassword, 
				sheSystemDbmControlRemoteBackupAdminState, sheSystemDbmControlBackupPeriod, sheSystemDbmControlBackupStartTime, sheSystemDbmControlBackupWaitingPeriod, sheSystemDbmControlBackupMaxFileNumber, 
				sheSystemDbmControlLocalBackupAdminState, sheSystemNtpClientEnabled, sheSystemNtpClientXmitInterval, sheSystemManagementSessionControlRequest, sheSystemManagementSessionControlStatus, 
				sheSystemManagementSessionControlTimer, sheSystemManagementSessionControlReqResult, sheSystemManagementSessionControlTimeStamp, sheSystemManagementSessionControlSnmpAgingTime, sheSystemConfigLogEntryNumber, 
				sheSystemConfigLogFtpUser, sheSystemConfigLogFtpPassword, sheSystemConfigLogFtpInterval, sheSystemConfigLogFtpPathName, sheSystemConfigLogControlRequest, 
				sheSystemConfigLogControlEntryNumber, sheSystemConfigLogControlFtpAddress, sheSystemConfigLogControlFtpUser, sheSystemConfigLogControlFtpPassword, sheSystemConfigLogControlFtpInterval, 
				sheSystemConfigLogControlFtpPathName, sheSystemDnsServerControlRequest, sheSystemDnsServerControlStatus, sheSystemDnsServerControlTimer, sheSystemDnsServerControlReqResult, 
				sheSystemDnsServerControlTimeStamp, sheSystemDnsServerControlAddr, sheSystemDnsServerControlIndex, sheSystemManagementSessionSnmpAgingTime, sheSystemNtpClientControlRequest, 
				sheSystemNtpClientControlStatus, sheSystemNtpClientControlTimer, sheSystemNtpClientControlReqResult, sheSystemNtpClientControlTimeStamp, sheSystemNtpClientControlXmitInterval, 
				sheSystemSwmControlRequest, sheSystemSwmControlStatus, sheSystemSwmControlTimer, sheSystemSwmControlReqResult, sheSystemSwmControlTimeStamp, 
				sheSystemNtpClientControlServerIndex, sheSystemControlTimeZone, sheSystemControlCPUThreshold, sheSystemControlCPUThresholdInterval, sheSystemControlMemoryThreshold, 
				sheSystemControlMemoryThresholdInterval, sheSystemTimeZone, sheSystem5SecCPULoad, sheSystem1MinCPULoad, sheSystem10MinCPULoad, 
				sheSystemCPULoadThreshold, sheSystemCPULoadThresholdInterval, sheSystemTotalMemory, sheSystemUsedMemory, sheSystemFreeMemory, 
				sheSystemMemoryThreshold, sheSystemMemoryThresholdInterval, sheSystemBootloaderVersion, sheSystemStartupResult, sheSystemDbmControlBackupFileIndex, 
				sheSystemConfigLogControlReqResult, sheSystemConfigLogControlStatus, sheSystemConfigLogControlTimeStamp, sheSystemSwmCurrentStatus, sheSystemConfigLogFtpServerAddress, 
				sheSystemNtpClientControlServername }
			STATUS current
			DESCRIPTION 
				" "
			::= { sheSystemGroups 2 }

		
		sheSystemNotificationGroup NOTIFICATION-GROUP
			NOTIFICATIONS { sheSystemStartupEnd, sheSystemFtp, sheSystemSwLoadPromoted, sheSystemSwLoadPromotionFailed, sheSystemLctSession, 
				sheSystemWriteDatatoFlashFinished, sheSystemCliSession, sheSystemSwmBaseSet, sheSystemReadSAPSContentFileReady, sheSystemDbmBaseSet, 
				sheSystemDbmBackupFilesTableRefreshed, sheSystemDbmBackupPeriodSet, sheSystemDbmLocalBackupAdminstateSet, sheSystemLocalDbInvalid, sheSystemRemoteDbInvalid, 
				sheSystemDbFtpAccessError, sheSystemSwmFtpExternalAccessError, sheSystemChangedCPULoadThreshold, sheSystemChangedMemoryThreshold, sheSystemCPULoadThresholdExceeded, 
				sheSystemMemoryThresholdExceeded, sheSystemNtpClientEnable, sheSystemNtpClientDisable, sheSystemNtpClientChangeXmitInterval, sheSystemNtpClientAddServerName, 
				sheSystemNtpClientDeleteServerName, sheSystemDnsServerAddAddr, sheSystemDnsServerDeleteAddr, sheSystemManagementSessionConnection, sheSystemManagementSessionDisconnection, 
				sheSystemManagementSessionChangedSnmpAgingTime, sheSystemConfigLogEntryNumberChanged, sheSystemConfigLogFtpLoginInfoChanged, sheSystemConfigLogFtpIntervalChanged, sheSystemSwmCurrentStatusChanged, 
				sheSystemSwmStatusError, sheSystemDbmRemoteBackupAdminstateSet, sheSystemSwmAdminStateSet, sheSystemSwmReadyForReset, sheSystemSwmFTPError, 
				sheSystemSwmUpgradeStartResult, sheSystemSwmFtpAccessError, sheSystemDbmResult }
			STATUS current
			DESCRIPTION 
				" "
			::= { sheSystemGroups 3 }

		
		sheSystemIpGroup OBJECT-GROUP
			OBJECTS { sheSystemIpHostIndex, sheSystemIpHostName, sheSystemIpHostUseDhcp, sheSystemIpHostIpAddress, sheSystemIpHostSubnetMask, 
				sheSystemIpHostOuterVlanId, sheSystemIpHostInnerVlanId, sheSystemIpHostControlRequest, sheSystemIpHostControlIndex, sheSystemIpHostControlStatus, 
				sheSystemIpHostControlReqResult, sheSystemIpHostControlTimer, sheSystemIpHostControlTimeStamp, sheSystemIpHostControlName, sheSystemIpHostControlUseDhcp, 
				sheSystemIpHostControlIpAddress, sheSystemIpHostControlSubnetMask, sheSystemIpHostControlOuterVlanId, sheSystemIpHostControlInnerVlanId, sheSystemIpRouteIndex, 
				sheSystemIpRouteName, sheSystemIpRouteDestIpAddress, sheSystemIpRouteSubnetMask, sheSystemIpRouteGatewayIpAddress, sheSystemIpRouteControlRequest, 
				sheSystemIpRouteControlIndex, sheSystemIpRouteControlStatus, sheSystemIpRouteControlReqResult, sheSystemIpRouteControlTimer, sheSystemIpRouteControlTimeStamp, 
				sheSystemIpRouteControlName, sheSystemIpRouteControlDestIpAddress, sheSystemIpRouteControlSubnetMask, sheSystemIpRouteMetric, sheSystemIpRouteControlMetric, 
				sheSystemIpHostOuterVlanPriority, sheSystemIpHostInnerVlanPriority, sheSystemIpHostControlOuterVlanPriority, sheSystemIpHostControlInnerVlanPriority, sheSystemIpRouteControlGatewayIpAddress, 
				sheSystemIpHostDescription, sheSystemIpHostControlDescription }
			STATUS current
			DESCRIPTION 
				"Description."
			::= { sheSystemGroups 4 }

		
		sheSystemIpNotificationGroup NOTIFICATION-GROUP
			NOTIFICATIONS { sheSystemIpHostCreated, sheSystemIpHostDeleted, sheSystemIpHostModified, sheSystemIpRouteCreated, sheSystemIpRouteDeleted, 
				sheSystemIpRouteModified }
			STATUS current
			DESCRIPTION 
				"Description."
			::= { sheSystemGroups 5 }

		
		sheSystemObsoleteGroup OBJECT-GROUP
			OBJECTS { sheSystemAutoConfigBackupEnabled, sheSystemAutoConfigBackupFtpServerAddress, sheSystemAutoConfigBackupFtpUser, sheSystemAutoConfigBackupFtpPassword, sheSystemAutoConfigBackupFtpPathName, 
				sheSystemAutoConfigBackupTime, sheSystemAutoConfigBackupControlRequest, sheSystemAutoConfigBackupControlEnabled, sheSystemAutoConfigBackupControlFtpServerAddress, sheSystemAutoConfigBackupControlFtpUser, 
				sheSystemAutoConfigBackupControlFtpPassword, sheSystemAutoConfigBackupControlFtpPathName, sheSystemAutoConfigBackupControlBackupTime }
			STATUS current
			DESCRIPTION 
				"Description."
			::= { sheSystemGroups 6 }

		
		sheSystemObsoleteNotificationGroup NOTIFICATION-GROUP
			NOTIFICATIONS { sheSystemAutoConfigBackupEnabledChanged, sheSystemAutoConfigBackupFtpLoginInfoChanged, sheSystemAutoConfigBackupTimeChanged }
			STATUS current
			DESCRIPTION 
				"Description."
			::= { sheSystemGroups 7 }

		
		sheSystemCompliances OBJECT IDENTIFIER ::= { sheSystemConformance 2 }

		
		sheSystemCompliance MODULE-COMPLIANCE
			STATUS current
			DESCRIPTION 
				"The compliance statement for SNMP entities which 
				manage VDSL interfaces in SHE."
			MODULE -- this module
				MANDATORY-GROUPS { sheSystemGroup, sheSystemControlGroup, sheSystemNotificationGroup, sheSystemIpGroup, sheSystemIpNotificationGroup
					 }
				GROUP sheSystemObsoleteGroup
					DESCRIPTION 
						"Not used by SHR R2.5.x..."
				GROUP sheSystemObsoleteNotificationGroup
					DESCRIPTION 
						"Not used by SHR R2.5.x..."
			::= { sheSystemCompliances 1 }

		
	
	END

--
-- she-system-mib.mib
--
