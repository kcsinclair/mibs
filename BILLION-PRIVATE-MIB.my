BILLION-MIB DEFINITIONS ::= BEGIN

   IMPORTS
       MODULE-IDENTITY, Integer32, IpAddress, 
       enterprises	FROM SNMPv2-SMI
       TEXTUAL-CONVENTION, DisplayString,
       MacAddress 	FROM SNMPv2-TC;

billion			OBJECT IDENTIFIER ::= { enterprises 17453 }
lte  		OBJECT IDENTIFIER ::= { billion 4 }
act  		OBJECT IDENTIFIER ::= { billion 5 }
info  		OBJECT IDENTIFIER ::= { billion 6 }
lte1  		OBJECT IDENTIFIER ::= { lte 1 }

--
--  lte1
--
	status OBJECT-TYPE
		SYNTAX	DisplayString 
		MAX-ACCESS	read-only
		STATUS	current
		DESCRIPTION
			"status"
		::= { lte1 1 }
		
	sim-status OBJECT-TYPE
		SYNTAX	DisplayString 
		MAX-ACCESS	read-only
		STATUS	current
		DESCRIPTION
			"SIM Status"
		::= { lte1 2 }	       
		
	signal OBJECT-TYPE
		SYNTAX	Integer32 
		MAX-ACCESS	read-only
		STATUS	current
		DESCRIPTION
			"signal"
		::= { lte1 3 }	  

	signal-information OBJECT-TYPE
		SYNTAX	DisplayString 
		MAX-ACCESS	read-only
		STATUS	current
		DESCRIPTION
			"signal Information"
		::= { lte1 4 }	       		

	network-name OBJECT-TYPE
		SYNTAX	DisplayString 
		MAX-ACCESS	read-only
		STATUS	current
		DESCRIPTION
			"Network Name"
		::= { lte1 5 }	       		

	cell-id OBJECT-TYPE
		SYNTAX	DisplayString 
		MAX-ACCESS	read-only
		STATUS	current
		DESCRIPTION
			"Cell ID"
		::= { lte1 6 }	       		

	phy-cell OBJECT-TYPE
		SYNTAX	DisplayString 
		MAX-ACCESS	read-only
		STATUS	current
		DESCRIPTION
			"Phy Cell"
		::= { lte1 7 }	       		

	imei OBJECT-TYPE
		SYNTAX	DisplayString 
		MAX-ACCESS	read-only
		STATUS	current
		DESCRIPTION
			"IMEI"
		::= { lte1 8 }	       		

	imsi OBJECT-TYPE
		SYNTAX	DisplayString 
		MAX-ACCESS	read-only
		STATUS	current
		DESCRIPTION
			"IMSI"
		::= { lte1 9 }	       		

	network-mode OBJECT-TYPE
		SYNTAX	DisplayString 
		MAX-ACCESS	read-only
		STATUS	current
		DESCRIPTION
			"Network Mode"
		::= { lte1 10 }	       		

	network-band OBJECT-TYPE
		SYNTAX	DisplayString 
		MAX-ACCESS	read-only
		STATUS	current
		DESCRIPTION
			"Network Band"
		::= { lte1 11 }	       		              

	rx-bytes OBJECT-TYPE
		SYNTAX	Counter32
		MAX-ACCESS	read-only
		STATUS	current
		DESCRIPTION
			"Rx traffic consumed by the minute time interval"
		::= { lte1 12 }	       		              		

	tx-bytes OBJECT-TYPE
		SYNTAX	Counter32
		MAX-ACCESS	read-only
		STATUS	current
		DESCRIPTION
			"Tx traffic consumed by the minute time interval"
		::= { lte1 13 }	       		              				

	rx-bandwidth OBJECT-TYPE
		SYNTAX	Counter32
		MAX-ACCESS	read-only
		STATUS	current
		DESCRIPTION
			"Rx bandwidth (kbps)"
		::= { lte1 14 }	       		              				

	tx-bandwidth OBJECT-TYPE
		SYNTAX	Counter32
		MAX-ACCESS	read-only
		STATUS	current
		DESCRIPTION
			"tx bandwidth (kbps)"
		::= { lte1 15 }	       		              				

	conn-time OBJECT-TYPE
		SYNTAX	DisplayString 
		MAX-ACCESS	read-only
		STATUS	current
		DESCRIPTION
			"connection time"
		::= { lte1 16 }		

	conn-time-int OBJECT-TYPE
		SYNTAX	Integer32
		MAX-ACCESS	read-only
		STATUS	current
		DESCRIPTION
			"connection time Integer"
		::= { lte1 17 }				

	CQI OBJECT-TYPE
		SYNTAX	Integer32
		MAX-ACCESS	read-only
		STATUS	current
		DESCRIPTION
			"LTE CQI"
		::= { lte1 18 }						

	RI OBJECT-TYPE
		SYNTAX	Integer32
		MAX-ACCESS	read-only
		STATUS	current
		DESCRIPTION
			"LTE RI"
		::= { lte1 19 }								

	DL-MCS OBJECT-TYPE
		SYNTAX	Integer32
		MAX-ACCESS	read-only
		STATUS	current
		DESCRIPTION
			"LTE DL_MCS"
		::= { lte1 20 }								
		
---
---  act
---
	reboot OBJECT-TYPE
		SYNTAX	Integer32 
		MAX-ACCESS	read-write
		STATUS	current
		DESCRIPTION
			"device reboot"
		::= { act 1 }	  		

	lte1-on OBJECT-TYPE
		SYNTAX	Integer32 
		MAX-ACCESS	read-write
		STATUS	current
		DESCRIPTION
			"lte on"
		::= { act 2 }	 
 		
	lte1-off OBJECT-TYPE
		SYNTAX	Integer32 
		MAX-ACCESS	read-write
		STATUS	current
		DESCRIPTION
			"lte off"
		::= { act 3 }	  		

---
---  info
---
	cpu-usage OBJECT-TYPE
		SYNTAX	Integer32 
		MAX-ACCESS	read-only
		STATUS	current
		DESCRIPTION
			"cpu usage"
		::= { info 1 }	
		
	gps-longitude OBJECT-TYPE
		SYNTAX	DisplayString 
		MAX-ACCESS	read-only
		STATUS	current
		DESCRIPTION
			"gps longitude"
		::= { info 2 }				

	gps-latitude OBJECT-TYPE
		SYNTAX	DisplayString 
		MAX-ACCESS	read-only
		STATUS	current
		DESCRIPTION
			"gps latitude"
		::= { info 3 }		
END
