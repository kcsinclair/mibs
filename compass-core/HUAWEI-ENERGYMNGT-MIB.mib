-- ============================================================================
-- Copyright (C) by  HUAWEI TECHNOLOGIES. All rights reserved.
-- Description: This mib is used for defining huawei's energy management MIB objects
-- Reference: None
-- Version:   V0.10
-- ============================================================================
       HUAWEI-ENERGYMNGT-MIB DEFINITIONS ::= BEGIN
       IMPORTS
            IpAddress, Integer32, Counter64, OBJECT-TYPE, MODULE-IDENTITY,
            NOTIFICATION-TYPE
                FROM SNMPv2-SMI
            DisplayString, DateAndTime, TruthValue, RowStatus
                FROM SNMPv2-TC
            huaweiUtility
                FROM HUAWEI-MIB;

hwEnergyMngt MODULE-IDENTITY
       LAST-UPDATED "201008060000Z"
       ORGANIZATION "Huawei Technologies Co.,Ltd."
       CONTACT-INFO
              " Floor 5 ,Block 4, R&D Building,
                Huawei Longgang Production Base,
                Shenzhen,  P.R.C.
                http://www.huawei.com
                Zip:518129
                Email:support@huawei.com
              "
            DESCRIPTION "huawei energy management MIB."

            REVISION    "201008060000Z"
            DESCRIPTION "V0.10, modify hwBoardIndex."

            REVISION    "201008050000Z"
            DESCRIPTION "V0.09, modify hwBoardType."

            REVISION    "201008030000Z"
            DESCRIPTION "V0.08, modify watt to milliwatt.
                         Modify enumeration of hwEnergySavingMode.
                         Add boardType and boardDescription."

            REVISION    "201007120000Z"
            DESCRIPTION "V0.08, modify hwPowerStatPeriod."

            REVISION    "201007070000Z"
            DESCRIPTION "V0.06, modify hwPowerStatPeriod."

            REVISION    "201006290000Z"
            DESCRIPTION "V0.05, modify hwEnergySavingMethodEnable value list.
                         Delete hwEnergySavingParameterTable first index 'hwEnergySavingMethodIndex'"

            REVISION    "201006230000Z"
            DESCRIPTION "V0.05, modify hwEnergySavingCapabilityMngtEntry, modify hwEnergySavingMethodTable"

            REVISION    "201006180000Z"
            DESCRIPTION "V0.04, modify hwEnergySavingCapabilityMngtEntry"

            REVISION    "201006170000Z"
            DESCRIPTION "V0.03, modify description for all MIB table"

            REVISION    "201006080000Z"
            DESCRIPTION "V0.02, add hwEnergySavingMethodEntry, add hwEnergySavingCapabilityMngt"

            REVISION    "201005240000Z"
            DESCRIPTION "V0.01 mib initial"

        ::= { huaweiUtility 157 }


    
--
-- Node definitions
--
    
        -- 1.1
        hwSysPowerMgnt OBJECT IDENTIFIER ::= { hwEnergyMngt 1 }

        
        -- 1.1.1
        hwPowerConsumption OBJECT-TYPE
            SYNTAX Counter64
            MAX-ACCESS read-only
            STATUS current
            DESCRIPTION
                "NE total power consumtion, counted from equipment first used.
                Joule(Watt * second)."
            ::= { hwSysPowerMgnt 1 }

        
        -- 1.1.2
        hwPowerStatPeriod OBJECT-TYPE
            SYNTAX INTEGER
               {
                fifteenMinutes(1),
                thirtyMinutes(2),
                oneHour(3),
                oneDay(4),
                oneWeek(5),
                oneMonth(6)
               }
            MAX-ACCESS read-write
            STATUS current
            DESCRIPTION
                "NE power statistics period: 
                fifteenMinutes(1):  The power statistics generated every 15 minutes.
                thirtyMinutes(2):   The power statistics generated every 30 minutes.
                oneHour(3):         The power statistics generated every hour. 
                oneDay(4):          The power statistics generated every day.
                oneWeek(5):         The power statistics generated every week.
                oneMonth(6):        The power statistics generated every month.
                The defaut statistics intervalue is one hour."
            ::= { hwSysPowerMgnt 2 }

        
        -- 1.1.3
        hwAveragePower OBJECT-TYPE
            SYNTAX Integer32
            MAX-ACCESS read-only
            STATUS current
            DESCRIPTION
                "NE average power consumtion during a period: milliwatt"
            ::= { hwSysPowerMgnt 3 }

        
        -- 1.1.4
        hwRatedPower OBJECT-TYPE
            SYNTAX Integer32
            MAX-ACCESS read-only
            STATUS current
            DESCRIPTION
                "NE rated power: milliwatt"
            ::= { hwSysPowerMgnt 4 }

        
        -- 1.1.5
        hwThresholdOfPower OBJECT-TYPE
            SYNTAX Integer32
            MAX-ACCESS read-write
            STATUS current
            DESCRIPTION
                "NE threshold power: milliwatt"
            ::= { hwSysPowerMgnt 5 }

        
        -- 1.1.6
        hwCurrentPower OBJECT-TYPE
            SYNTAX Integer32
            MAX-ACCESS read-only
            STATUS current
            DESCRIPTION
                "NE current power: milliwatt"
            ::= { hwSysPowerMgnt 6 }




        -- 1.2
        hwBoardPowerMngt OBJECT IDENTIFIER ::= { hwEnergyMngt 2 }

        
        -- 1.2.1
        hwBoardPowerMngtTable OBJECT-TYPE
            SYNTAX SEQUENCE OF HwBoardPowerMngtEntry
            MAX-ACCESS not-accessible
            STATUS current
            DESCRIPTION
                "This table describes current power and rated power of boards. The index is hwBoardIndex."
            ::= { hwBoardPowerMngt 1 }

        
        -- 1.2.1.1
        hwBoardPowerMngtEntry OBJECT-TYPE
            SYNTAX HwBoardPowerMngtEntry
            MAX-ACCESS not-accessible
            STATUS current
            DESCRIPTION
                "The entry of hwBoardPowerMngtTable."
            INDEX { hwBoardIndex }
            ::= { hwBoardPowerMngtTable 1 }

        
        HwBoardPowerMngtEntry ::=
            SEQUENCE { 
                hwBoardIndex
                    Integer32,
                hwBoardType
                    DisplayString,
                hwBoardName
                    DisplayString,
                hwBoardCurrentPower
                    Integer32,
                hwBoardRatedPower
                    Integer32,
                hwBoardThresholdOfPower
                    Integer32
                    }

        -- 1.2.1.1.1
        hwBoardIndex OBJECT-TYPE
            SYNTAX Integer32
            MAX-ACCESS read-only
            STATUS current
            DESCRIPTION
                "Index: reserved/shelf/frame/slot.
                The index is format by 4 bytes(8bit for 1 byte): reservedByte(0xFF), shelfID, frameID, slotID.
                e.g. shlef=1, frame=2, slot=17, the index is 0xFF010211((integer)-16711151).
                If no shelfID or frameID, the corresponding byte is set to be 0xFF.
                e.g. no shlefID, no frameID, slot=17, the index is 0xFFFFFF11((integer)-239).
                "
            ::= { hwBoardPowerMngtEntry 1 }


        -- 1.2.1.1.2
        hwBoardType OBJECT-TYPE
            SYNTAX DisplayString
            MAX-ACCESS read-only
            STATUS current
            DESCRIPTION
                "hwBoardType describes main type of board: LPU/SFU/ADSL/PSTN, etc.
                "
            ::= { hwBoardPowerMngtEntry 2 }


        -- 1.2.1.1.3
        hwBoardName OBJECT-TYPE
            SYNTAX DisplayString
            MAX-ACCESS read-only
            STATUS current
            DESCRIPTION
                "hwBoardName describes full name of board: CR52LPUA/CR57SFU40A/H805ADGG, etc.
                "
            ::= { hwBoardPowerMngtEntry 3 }


        -- 1.2.1.1.4
        hwBoardCurrentPower OBJECT-TYPE
            SYNTAX Integer32
            MAX-ACCESS read-only
            STATUS current
            DESCRIPTION
                "current power of board(slot): milliwatt"
            ::= { hwBoardPowerMngtEntry 4 }

        
        -- 1.2.1.1.5
        hwBoardRatedPower OBJECT-TYPE
            SYNTAX Integer32
            MAX-ACCESS read-only
            STATUS current
            DESCRIPTION
                "rated power of board(slot): milliwatt"
            ::= { hwBoardPowerMngtEntry 5 }


        -- 1.2.1.1.6
        hwBoardThresholdOfPower OBJECT-TYPE
            SYNTAX Integer32
            MAX-ACCESS read-write
            STATUS current
            DESCRIPTION
                "Threshold power of board(slot): milliwatt"
            ::= { hwBoardPowerMngtEntry 6 }



        
        -- 1.3
        hwEnergySavingMngt OBJECT IDENTIFIER ::= { hwEnergyMngt 3 }

        
        -- 1.3.1
        hwEnergySavingMode OBJECT-TYPE
            SYNTAX INTEGER
                {
                userDefined(1),
                standard(2),
                basic(3),
                deep(4)
                }
            MAX-ACCESS read-write
            STATUS current
            DESCRIPTION
                "Power saving mode:
                 UserDefined(1): UserDined energy-saving mode, user can define energy-saving strategy.
                 Standard(2): standard energy-saving mode
                 Basic(3): basic energy-saving mode, many basic energy-saving strategy included.
                 Deep(4): Deep energy-saving mode, many complex energy-saving strategy included, which may effect service.
                "
            ::= { hwEnergySavingMngt 1 }

        
        -- 1.3.2
        hwEnergySavingMethodTable OBJECT-TYPE
            SYNTAX SEQUENCE OF HwEnergySavingMethodEntry
            MAX-ACCESS not-accessible
            STATUS current
            DESCRIPTION
                "hwEnergySavingMethodTable defines energy-saving Method for all mode.
                User can set a method with its parameter.
                The index of this table is hwEnergySavingMethodIndex.
                "
            ::= { hwEnergySavingMngt 2 }

        
        -- 1.3.2.1
        hwEnergySavingMethodEntry OBJECT-TYPE
            SYNTAX HwEnergySavingMethodEntry
            MAX-ACCESS not-accessible
            STATUS current
            DESCRIPTION
                "Entry of energy-saveing method table."
            INDEX { hwEnergySavingMethodIndex }
            ::= { hwEnergySavingMethodTable 1 }

        
        HwEnergySavingMethodEntry ::=
            SEQUENCE { 
                hwEnergySavingMethodIndex
                    Integer32,
                hwEnergySavingMethodEnable
                    INTEGER
                }

        -- 1.3.2.1.1
        hwEnergySavingMethodIndex OBJECT-TYPE
            SYNTAX Integer32
            MAX-ACCESS read-only
            STATUS current
            DESCRIPTION
                "The index of method in use.
                "
            ::= { hwEnergySavingMethodEntry 1 }

        -- 1.3.2.1.2
        hwEnergySavingMethodEnable OBJECT-TYPE
            SYNTAX INTEGER
            {
                enable(1),
                disable(2)
            }
            MAX-ACCESS read-write
            STATUS current
            DESCRIPTION
                "hwEnergySaveingMethodEnable describes the status of energy-saving method: enableed or disabled.
                "
            ::= { hwEnergySavingMethodEntry 2 }


        
        -- 1.3.3
        hwEnergySavingParameterTable OBJECT-TYPE
            SYNTAX SEQUENCE OF HwEnergySavingParameterEntry
            MAX-ACCESS not-accessible
            STATUS current
            DESCRIPTION
                "hwEnergySavingParameterTable defines parameters for all energy-saving methods.
                User can set parameter for a method.
                The index of this table: hwEnergySavingMethodIndex, hwEnergySavingParameterIndex."
            ::= { hwEnergySavingMngt 3 }

        
        -- 1.3.3.1
        hwEnergySavingParameterEntry OBJECT-TYPE
            SYNTAX HwEnergySavingParameterEntry
            MAX-ACCESS not-accessible
            STATUS current
            DESCRIPTION
                "Entry of energy-saveing parameter table."
            INDEX { hwEnergySavingMethodIndex, hwEnergySavingParameterIndex }
            ::= { hwEnergySavingParameterTable 1 }

        
        HwEnergySavingParameterEntry ::=
            SEQUENCE { 
                hwEnergySavingParameterIndex
                    Integer32,
                hwEnergySavingParameterValue
                    DisplayString (SIZE (0..64))
             }

        -- 1.3.3.1.1
        hwEnergySavingParameterIndex OBJECT-TYPE
            SYNTAX Integer32
            MAX-ACCESS read-only
            STATUS current
            DESCRIPTION
                "The second index of hwEnergySavingParameterTable.
                An energy-saving method might have more than one parameter.
                This index is used to identify the parameter for a method."
            ::= { hwEnergySavingParameterEntry 1 }

        -- 1.3.3.1.2
        hwEnergySavingParameterValue OBJECT-TYPE
            SYNTAX DisplayString
            MAX-ACCESS read-write
            STATUS current
            DESCRIPTION
                "The value of an energy-saveing method's parameter.
                 The parameter is a format string. 
                 When NMS sets integer 12 as a parameter for a energy-saving method, the value is a string '12'.
                "
            ::= { hwEnergySavingParameterEntry 2 }

            

        -- 1.3.4
        hwEnergySavingCapabilityMngtTable OBJECT-TYPE
            SYNTAX SEQUENCE OF HwEnergySavingCapabilityMngtEntry
            MAX-ACCESS not-accessible
            STATUS current
            DESCRIPTION
                "This table describes the energy-saving capability, including energy-saving methods and parameters.
                The index is hwEnergySavingCapabilityDescIndex.
                "
            ::= { hwEnergySavingMngt 4 }

        
        -- 1.3.4.1
        hwEnergySavingCapabilityMngtEntry OBJECT-TYPE
            SYNTAX HwEnergySavingCapabilityMngtEntry
            MAX-ACCESS not-accessible
            STATUS current
            DESCRIPTION
                "The entry of hwBoardPowerMngtTable."
            INDEX { hwEnergySavingCapabilityDescIndex }
            ::= { hwEnergySavingCapabilityMngtTable 1 }

        
        HwEnergySavingCapabilityMngtEntry ::=
            SEQUENCE { 
                hwEnergySavingCapabilityDescIndex
                    Integer32,
                hwEnergySavingCapabilityDescLanguage
                    DisplayString (SIZE (0..64)),
                hwEnergySavingCapabilityDesc
                    OCTET STRING
                    }
        
        -- 1.3.4.1.1
        hwEnergySavingCapabilityDescIndex OBJECT-TYPE
            SYNTAX Integer32 
            MAX-ACCESS read-only
            STATUS current
            DESCRIPTION
                "The index of hwEnergySavingCapabilityMngtTable.
                "
            ::= { hwEnergySavingCapabilityMngtEntry 1 }

        -- 1.3.4.1.2
        hwEnergySavingCapabilityDescLanguage OBJECT-TYPE
            SYNTAX DisplayString 
            MAX-ACCESS read-only
            STATUS current
            DESCRIPTION
                "The language of EnergySavingCapabilityDescription file.
                'en-gb'(English-GreatBraitain)
                'zh-cn'(Chinese)
                "
            ::= { hwEnergySavingCapabilityMngtEntry 2 }

        -- 1.3.4.1.3
        hwEnergySavingCapabilityDesc OBJECT-TYPE
            SYNTAX OCTET STRING (SIZE (0..10240)) 
            MAX-ACCESS read-only
            STATUS current
            DESCRIPTION
                "User can get the description string from hwEnergySavingCapabilityDesc.
                An XML file which is compressed by ZIP to less than 10240 bytes,
                describes the energy-saving capability, including all energy-saving methods and parameters.
                "
            ::= { hwEnergySavingCapabilityMngtEntry 3 }

    hwEnergyTrapObjects OBJECT IDENTIFIER ::= { hwEnergyMngt 10 }
    
    hwEnergyDevId OBJECT-TYPE
			SYNTAX Integer32
			MAX-ACCESS accessible-for-notify
			STATUS current
			DESCRIPTION
				"This object identifies the device ID."
			::= { hwEnergyTrapObjects 1 }       
    
    
    hwEnergyNotification OBJECT IDENTIFIER ::= { hwEnergyMngt 11 }
    
    hwEnergyDevChangeToSleep NOTIFICATION-TYPE
			OBJECTS { hwEnergyDevId }
			STATUS current
			DESCRIPTION 
				"This notification indicates device entering in the sleeping status."
			::= { hwEnergyNotification 1 }        
    
    
    END

--
-- HUAWEI-ENERGYMNGT-MIB
--
