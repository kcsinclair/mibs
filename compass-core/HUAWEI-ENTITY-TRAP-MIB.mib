HUAWEI-ENTITY-TRAP-MIB DEFINITIONS ::= BEGIN
 
		IMPORTS
			entPhysicalIndex, entPhysicalName			
				FROM ENTITY-MIB			
			hwBaseTrapSeverity, hwBaseTrapProbableCause, hwBaseTrapEventType			
				FROM HUAWEI-BASE-TRAP-MIB			
			ifIndex, ifName			
				FROM IF-MIB			
			hwDatacomm			
				FROM HUAWEI-MIB			
			IANAItuProbableCause			
				FROM IANA-ITU-ALARM-TC-MIB			
			OBJECT-GROUP, MODULE-COMPLIANCE, NOTIFICATION-GROUP			
				FROM SNMPv2-CONF			
			Integer32, OBJECT-TYPE, MODULE-IDENTITY, NOTIFICATION-TYPE			
				FROM SNMPv2-SMI;
	
	
--   January 17, 2007 at 00:00 GMT
-- 1.3.6.1.4.1.2011.5.25.219
-- January 17, 2007 at 00:00 GMT
		-- 1.3.6.1.4.1.2011.5.25.219
		hwEntityTrapMIB MODULE-IDENTITY 
			LAST-UPDATED "200701170000Z"		-- January 17, 2007 at 00:00 GMT
			ORGANIZATION 
				"Huawei Technologies co.,Ltd."
			CONTACT-INFO 
				" R&D BeiJing, Huawei Technologies co.,Ltd.
				Huawei Bld.,NO.3 Xinxi Rd., 
				Shang-Di Information Industry Base,
				    Hai-Dian District Beijing P.R. China
				Zip:100085 
				Http://www.huawei.com			               
				E-mail:support@huawei.com "
			DESCRIPTION 
				"This is the base trap definition for DataCom."
			::= { hwDatacomm 219 }

		
	
	
--
-- Node definitions
--
	
--  Node definitions
-- 
-- Node definitions
-- 
-- 1.3.6.1.4.1.2011.5.25.219.1
		-- 1.3.6.1.4.1.2011.5.25.219.1
		hwEntityTrapObject OBJECT IDENTIFIER ::= { hwEntityTrapMIB 1 }

		
--  1.3.6.1.4.1.2011.5.25.219.1.1
		-- 1.3.6.1.4.1.2011.5.25.219.1.1
		hwEntityPhysicalIndex OBJECT-TYPE
			SYNTAX Integer32
			MAX-ACCESS read-write
			STATUS current
			DESCRIPTION
				"The index of physical."
			::= { hwEntityTrapObject 1 }

		
--  1.3.6.1.4.1.2011.5.25.219.1.2
		-- 1.3.6.1.4.1.2011.5.25.219.1.2
		hwEntityTrapEntType OBJECT-TYPE
			SYNTAX INTEGER
				{
				mpu(1),
				lpu(2),
				sfu(3),
				pic(4),
				cfcard(5),
				ofc(6)
				}
			MAX-ACCESS read-write
			STATUS current
			DESCRIPTION
				"The entity type."
			::= { hwEntityTrapObject 2 }

		
--  1.3.6.1.4.1.2011.5.25.219.1.3
		-- 1.3.6.1.4.1.2011.5.25.219.1.3
		hwEntityTrapFaultID OBJECT-TYPE
			SYNTAX IANAItuProbableCause
			MAX-ACCESS accessible-for-notify
			STATUS current
			DESCRIPTION
				"To describe the fault id of trap."
			::= { hwEntityTrapObject 3 }

		
--  1.3.6.1.4.1.2011.5.25.219.1.4
		-- 1.3.6.1.4.1.2011.5.25.219.1.4
		hwEntityCommunicateType OBJECT-TYPE
			SYNTAX INTEGER
				{
				controlChannel(1),
				monitorChannel(2),
				clockChannel(3),
				dataChannel(4)
				}
			MAX-ACCESS read-write
			STATUS current
			DESCRIPTION
				"The communicate type."
			::= { hwEntityTrapObject 4 }

		
--  1.3.6.1.4.1.2011.5.25.219.1.5
		-- 1.3.6.1.4.1.2011.5.25.219.1.5
		hwEntityThresholdTable OBJECT-TYPE
			SYNTAX SEQUENCE OF HwEntityThresholdEntry
			MAX-ACCESS not-accessible
			STATUS current
			DESCRIPTION
				"A table to config the threshold of each sensor."
			::= { hwEntityTrapObject 5 }

		
--  1.3.6.1.4.1.2011.5.25.219.1.5.1
		-- 1.3.6.1.4.1.2011.5.25.219.1.5.1
		hwEntityThresholdEntry OBJECT-TYPE
			SYNTAX HwEntityThresholdEntry
			MAX-ACCESS not-accessible
			STATUS current
			DESCRIPTION
				"The entry of threshold table."
			INDEX { entPhysicalIndex }
			::= { hwEntityThresholdTable 1 }

		
		HwEntityThresholdEntry ::=
			SEQUENCE { 
				hwEntityThresholdType
					INTEGER,
				hwEntityThresholdValue
					Integer32,
				hwEntityThresholdCurrent
					Integer32,
				hwEntityThresholdCritical
					Integer32,
				hwEntityThresholdWarning
					Integer32
			 }

--  1.3.6.1.4.1.2011.5.25.219.1.5.1.1
		-- 1.3.6.1.4.1.2011.5.25.219.1.5.1.1
		hwEntityThresholdType OBJECT-TYPE
			SYNTAX INTEGER
				{
				riseOver(1),
				fallBelow(2)
				}
			MAX-ACCESS read-only
			STATUS current
			DESCRIPTION
				"The abnormal type for temperature, voltage, humidity......"
			::= { hwEntityThresholdEntry 1 }

		
--  1.3.6.1.4.1.2011.5.25.219.1.5.1.2
		-- 1.3.6.1.4.1.2011.5.25.219.1.5.1.2
		hwEntityThresholdValue OBJECT-TYPE
			SYNTAX Integer32
			MAX-ACCESS read-write
			STATUS current
			DESCRIPTION
				"The threshold value of temperature, humidity ,fog ......"
			::= { hwEntityThresholdEntry 2 }

		
--  1.3.6.1.4.1.2011.5.25.219.1.5.1.3
		-- 1.3.6.1.4.1.2011.5.25.219.1.5.1.3
		hwEntityThresholdCurrent OBJECT-TYPE
			SYNTAX Integer32
			MAX-ACCESS read-only
			STATUS current
			DESCRIPTION
				"The current value that been measured."
			::= { hwEntityThresholdEntry 3 }

		
--  1.3.6.1.4.1.2011.5.25.219.1.5.1.4
		-- 1.3.6.1.4.1.2011.5.25.219.1.5.1.4
		hwEntityThresholdCritical OBJECT-TYPE
			SYNTAX Integer32
			MAX-ACCESS read-write
			STATUS current
			DESCRIPTION
				"The critical alarm threshold for critical alarm. It could be used
				for a more dangerous instance than hwEntityThresholdCritical."
			::= { hwEntityThresholdEntry 4 }

		
--  1.3.6.1.4.1.2011.5.25.219.1.5.1.5
		-- 1.3.6.1.4.1.2011.5.25.219.1.5.1.5
		hwEntityThresholdWarning OBJECT-TYPE
			SYNTAX Integer32
			MAX-ACCESS read-write
			STATUS current
			DESCRIPTION
				"The warning alarm threshold for warning alarm. It could be used
				for a more dangerous instance than hwEntityThresholdWarning."
			::= { hwEntityThresholdEntry 5 }
			

--  1.3.6.1.4.1.2011.5.25.219.1.5.1.6           
		-- 1.3.6.1.4.1.2011.5.25.219.1.6
		hwUserDefAlarmName OBJECT-TYPE
			SYNTAX OCTET STRING
			MAX-ACCESS read-only
			STATUS current
			DESCRIPTION
				"Description."
			::= { hwEntityTrapObject 6 }


--  1.3.6.1.4.1.2011.5.25.219.1.5.1.7
		-- 1.3.6.1.4.1.2011.5.25.219.1.7
		hwUserDefChannel OBJECT-TYPE
			SYNTAX Integer32
			MAX-ACCESS read-write
			STATUS current
			DESCRIPTION
				"Description."
			::= { hwEntityTrapObject 7 }


--  1.3.6.1.4.1.2011.5.25.219.1.5.1.8
		--  1.3.6.1.4.1.2011.5.25.219.1.5.1.8
		hwSoftwareVersion OBJECT-TYPE
			SYNTAX OCTET STRING
			MAX-ACCESS accessible-for-notify
			STATUS current
			DESCRIPTION
				"Description."
			::= { hwEntityTrapObject 8 }


--  1.3.6.1.4.1.2011.5.25.219.1.5.1.9
		--  1.3.6.1.4.1.2011.5.25.219.1.5.1.9
		hwStartupSoftwareFileName OBJECT-TYPE
			SYNTAX OCTET STRING
			MAX-ACCESS accessible-for-notify
			STATUS current
			DESCRIPTION
				"Description."
			::= { hwEntityTrapObject 9 }


--  1.3.6.1.4.1.2011.5.25.219.1.5.1.10
		--  1.3.6.1.4.1.2011.5.25.219.1.5.1.10
		hwStorageDevName OBJECT-TYPE
			SYNTAX OCTET STRING
			MAX-ACCESS accessible-for-notify
			STATUS current
			DESCRIPTION
				"Description."
			::= { hwEntityTrapObject 10 }
		hwEntityTraps OBJECT IDENTIFIER ::= { hwEntityTrapMIB 2 }

		
--  1.3.6.1.4.1.2011.5.25.219.2.1
		-- 1.3.6.1.4.1.2011.5.25.219.2.1
		hwChassisTrap OBJECT IDENTIFIER ::= { hwEntityTraps 1 }

		
--  Frame has been removed.
-- 1.3.6.1.4.1.2011.5.25.219.2.1.1
		-- 1.3.6.1.4.1.2011.5.25.219.2.1.1
		hwChassisRemove NOTIFICATION-TYPE
			OBJECTS { hwEntityPhysicalIndex, entPhysicalName, hwEntityTrapFaultID }
			STATUS current
			DESCRIPTION 
				"Chassis has been removed."
			::= { hwChassisTrap 1 }

		
--  1.3.6.1.4.1.2011.5.25.219.2.1.2
		-- 1.3.6.1.4.1.2011.5.25.219.2.1.2
		hwChassisInsert NOTIFICATION-TYPE
			OBJECTS { hwEntityPhysicalIndex, entPhysicalName, hwEntityTrapFaultID }
			STATUS current
			DESCRIPTION 
				"Chassis has been inserted."
			::= { hwChassisTrap 2 }

		
--  1.3.6.1.4.1.2011.5.25.219.2.1.3
		-- 1.3.6.1.4.1.2011.5.25.219.2.1.3
		hwChassisFail NOTIFICATION-TYPE
			OBJECTS { hwEntityPhysicalIndex, entPhysicalName, hwEntityTrapFaultID }
			STATUS current
			DESCRIPTION 
				"Chassis become failure for some reason."
			::= { hwChassisTrap 3 }

		
--  1.3.6.1.4.1.2011.5.25.219.2.1.4
		-- 1.3.6.1.4.1.2011.5.25.219.2.1.4
		hwChassisFailResume NOTIFICATION-TYPE
			OBJECTS { hwEntityPhysicalIndex, entPhysicalName, hwEntityTrapFaultID }
			STATUS current
			DESCRIPTION 
				"Board resume from failure."
			::= { hwChassisTrap 4 }

		
--  1.3.6.1.4.1.2011.5.25.219.2.1.5
		-- 1.3.6.1.4.1.2011.5.25.219.2.1.5
		hwChassisInvalid NOTIFICATION-TYPE
			OBJECTS { hwEntityPhysicalIndex, entPhysicalName, hwEntityTrapFaultID }
			STATUS current
			DESCRIPTION 
				"Chassis is invalid for some reason."
			::= { hwChassisTrap 5 }

		
--  1.3.6.1.4.1.2011.5.25.219.2.1.6
		-- 1.3.6.1.4.1.2011.5.25.219.2.1.6
		hwChassisInvalidResume NOTIFICATION-TYPE
			OBJECTS { hwEntityPhysicalIndex, entPhysicalName, hwEntityTrapFaultID }
			STATUS current
			DESCRIPTION 
				"Chassis resume from invalid situation."
			::= { hwChassisTrap 6 }

		
--  1.3.6.1.4.1.2011.5.25.219.2.2
		-- 1.3.6.1.4.1.2011.5.25.219.2.2
		hwBoardTrap OBJECT IDENTIFIER ::= { hwEntityTraps 2 }

		
--  1.3.6.1.4.1.2011.5.25.219.2.2.1
		-- 1.3.6.1.4.1.2011.5.25.219.2.2.1
		hwBoardRemove NOTIFICATION-TYPE
			OBJECTS { hwEntityPhysicalIndex, entPhysicalName, hwEntityTrapEntType, hwEntityTrapFaultID }
			STATUS current
			DESCRIPTION 
				"Board has been removed."
			::= { hwBoardTrap 1 }

		
--  1.3.6.1.4.1.2011.5.25.219.2.2.2
		-- 1.3.6.1.4.1.2011.5.25.219.2.2.2
		hwBoardInsert NOTIFICATION-TYPE
			OBJECTS { hwEntityPhysicalIndex, entPhysicalName, hwEntityTrapEntType, hwEntityTrapFaultID }
			STATUS current
			DESCRIPTION 
				"Board has been inserted."
			::= { hwBoardTrap 2 }

		
--  1.3.6.1.4.1.2011.5.25.219.2.2.3
		-- 1.3.6.1.4.1.2011.5.25.219.2.2.3
		hwBoardFail NOTIFICATION-TYPE
			OBJECTS { hwEntityPhysicalIndex, entPhysicalName, hwEntityTrapEntType, hwEntityTrapFaultID }
			STATUS current
			DESCRIPTION 
				"Board become failure for some reason."
			::= { hwBoardTrap 3 }

		
--  1.3.6.1.4.1.2011.5.25.219.2.2.4
		-- 1.3.6.1.4.1.2011.5.25.219.2.2.4
		hwBoardFailResume NOTIFICATION-TYPE
			OBJECTS { hwEntityPhysicalIndex, entPhysicalName, hwEntityTrapEntType, hwEntityTrapFaultID }
			STATUS current
			DESCRIPTION 
				"Board resume from failure."
			::= { hwBoardTrap 4 }

		
--  1.3.6.1.4.1.2011.5.25.219.2.2.5
		-- 1.3.6.1.4.1.2011.5.25.219.2.2.5
		hwBoardInvalid NOTIFICATION-TYPE
			OBJECTS { hwEntityPhysicalIndex, entPhysicalName, hwEntityTrapEntType, hwEntityTrapFaultID }
			STATUS current
			DESCRIPTION 
				"Board is invalid for some reason."
			::= { hwBoardTrap 5 }

		
--  1.3.6.1.4.1.2011.5.25.219.2.2.6
		-- 1.3.6.1.4.1.2011.5.25.219.2.2.6
		hwBoardInvalidResume NOTIFICATION-TYPE
			OBJECTS { hwEntityPhysicalIndex, entPhysicalName, hwEntityTrapEntType, hwEntityTrapFaultID }
			STATUS current
			DESCRIPTION 
				"Board resume from invalid situation."
			::= { hwBoardTrap 6 }

		
--  1.3.6.1.4.1.2011.5.25.219.2.2.7
		-- 1.3.6.1.4.1.2011.5.25.219.2.2.7
		hwBoardLeaveMaster NOTIFICATION-TYPE
			OBJECTS { hwEntityPhysicalIndex, entPhysicalName, hwEntityTrapEntType, hwEntityTrapFaultID }
			STATUS current
			DESCRIPTION 
				"MPU leave master role."
			::= { hwBoardTrap 7 }

		
--  1.3.6.1.4.1.2011.5.25.219.2.2.8
		-- 1.3.6.1.4.1.2011.5.25.219.2.2.8
		hwBoardBecomeMaster NOTIFICATION-TYPE
			OBJECTS { hwEntityPhysicalIndex, entPhysicalName, hwEntityTrapEntType, hwEntityTrapFaultID }
			STATUS current
			DESCRIPTION 
				"MPU become master role."
			::= { hwBoardTrap 8 }


--  1.3.6.1.4.1.2011.5.25.219.2.2.9
		-- 1.3.6.1.4.1.2011.5.25.219.2.2.9
		hwUpMicroSwitchOpen NOTIFICATION-TYPE
			OBJECTS { hwEntityPhysicalIndex, entPhysicalName, hwEntityTrapEntType, hwEntityTrapFaultID }
			STATUS current
			DESCRIPTION 
				"Up micro switch open."
			::= { hwBoardTrap 9 }


--  1.3.6.1.4.1.2011.5.25.219.2.2.10
		-- 1.3.6.1.4.1.2011.5.25.219.2.2.10
		hwUpMicroSwitchClose NOTIFICATION-TYPE
			OBJECTS { hwEntityPhysicalIndex, entPhysicalName, hwEntityTrapEntType, hwEntityTrapFaultID }
			STATUS current
			DESCRIPTION 
				"Up micro switch close."
			::= { hwBoardTrap 10 }


--  1.3.6.1.4.1.2011.5.25.219.2.2.11
		-- 1.3.6.1.4.1.2011.5.25.219.2.2.9
		hwDownMicroSwitchOpen NOTIFICATION-TYPE
			OBJECTS { hwEntityPhysicalIndex, entPhysicalName, hwEntityTrapEntType, hwEntityTrapFaultID }
			STATUS current
			DESCRIPTION 
				"Down micro switch open."
			::= { hwBoardTrap 11 }


--  1.3.6.1.4.1.2011.5.25.219.2.2.12
		-- 1.3.6.1.4.1.2011.5.25.219.2.2.10
		hwDownMicroSwitchClose NOTIFICATION-TYPE
			OBJECTS { hwEntityPhysicalIndex, entPhysicalName, hwEntityTrapEntType, hwEntityTrapFaultID }
			STATUS current
			DESCRIPTION 
				"Down micro switch close."
			::= { hwBoardTrap 12 }

                
--  1.3.6.1.4.1.2011.5.25.219.2.3
		-- 1.3.6.1.4.1.2011.5.25.219.2.3
		hwCardTrap OBJECT IDENTIFIER ::= { hwEntityTraps 3 }

		
--  1.3.6.1.4.1.2011.5.25.219.2.3.1
		-- 1.3.6.1.4.1.2011.5.25.219.2.3.1
		hwCardRemove NOTIFICATION-TYPE
			OBJECTS { hwEntityPhysicalIndex, entPhysicalName, hwEntityTrapEntType, hwEntityTrapFaultID }
			STATUS current
			DESCRIPTION 
				"Card has been removed."
			::= { hwCardTrap 1 }

		
--  1.3.6.1.4.1.2011.5.25.219.2.3.2
		-- 1.3.6.1.4.1.2011.5.25.219.2.3.2
		hwCardInsert NOTIFICATION-TYPE
			OBJECTS { hwEntityPhysicalIndex, entPhysicalName, hwEntityTrapEntType, hwEntityTrapFaultID }
			STATUS current
			DESCRIPTION 
				"Card has been inserted."
			::= { hwCardTrap 2 }

		
--  1.3.6.1.4.1.2011.5.25.219.2.3.3
		-- 1.3.6.1.4.1.2011.5.25.219.2.3.3
		hwCardFail NOTIFICATION-TYPE
			OBJECTS { hwEntityPhysicalIndex, entPhysicalName, hwEntityTrapEntType, hwEntityTrapFaultID }
			STATUS current
			DESCRIPTION 
				"Card become failure for some reason."
			::= { hwCardTrap 3 }

		
--  1.3.6.1.4.1.2011.5.25.219.2.3.4
		-- 1.3.6.1.4.1.2011.5.25.219.2.3.4
		hwCardFailResume NOTIFICATION-TYPE
			OBJECTS { hwEntityPhysicalIndex, entPhysicalName, hwEntityTrapEntType, hwEntityTrapFaultID }
			STATUS current
			DESCRIPTION 
				"Card resume from failure."
			::= { hwCardTrap 4 }

		
--  1.3.6.1.4.1.2011.5.25.219.2.3.5
		-- 1.3.6.1.4.1.2011.5.25.219.2.3.5
		hwCardInvalid NOTIFICATION-TYPE
			OBJECTS { hwEntityPhysicalIndex, entPhysicalName, hwEntityTrapEntType, hwEntityTrapFaultID }
			STATUS current
			DESCRIPTION 
				"Card is invalid for some reason."
			::= { hwCardTrap 5 }

		
--  1.3.6.1.4.1.2011.5.25.219.2.3.6
		-- 1.3.6.1.4.1.2011.5.25.219.2.3.6
		hwCardInvalidResume NOTIFICATION-TYPE
			OBJECTS { hwEntityPhysicalIndex, entPhysicalName, hwEntityTrapEntType, hwEntityTrapFaultID }
			STATUS current
			DESCRIPTION 
				"Card resume from invalid situation."
			::= { hwCardTrap 6 }

		
--  1.3.6.1.4.1.2011.5.25.219.2.4
		-- 1.3.6.1.4.1.2011.5.25.219.2.4
		hwOpticalTrap OBJECT IDENTIFIER ::= { hwEntityTraps 4 }

		
--  1.3.6.1.4.1.2011.5.25.219.2.4.1
		-- 1.3.6.1.4.1.2011.5.25.219.2.4.1
		hwOpticalRemove NOTIFICATION-TYPE
			OBJECTS { hwEntityPhysicalIndex, entPhysicalName, hwEntityTrapFaultID }
			STATUS current
			DESCRIPTION 
				"Optical Module has been removed."
			::= { hwOpticalTrap 1 }

		
--  1.3.6.1.4.1.2011.5.25.219.2.4.2
		-- 1.3.6.1.4.1.2011.5.25.219.2.4.2
		hwOpticalInsert NOTIFICATION-TYPE
			OBJECTS { hwEntityPhysicalIndex, entPhysicalName, hwEntityTrapFaultID }
			STATUS current
			DESCRIPTION 
				"Optical Module has been inserted."
			::= { hwOpticalTrap 2 }

		
--  1.3.6.1.4.1.2011.5.25.219.2.4.3
		-- 1.3.6.1.4.1.2011.5.25.219.2.4.3
		hwOpticalFail NOTIFICATION-TYPE
			OBJECTS { hwEntityPhysicalIndex, entPhysicalName, hwEntityTrapFaultID }
			STATUS current
			DESCRIPTION 
				"Optical Module become failure for some reason."
			::= { hwOpticalTrap 3 }

		
--  1.3.6.1.4.1.2011.5.25.219.2.4.4
		-- 1.3.6.1.4.1.2011.5.25.219.2.4.4
		hwOpticalFailResume NOTIFICATION-TYPE
			OBJECTS { hwEntityPhysicalIndex, entPhysicalName, hwEntityTrapFaultID }
			STATUS current
			DESCRIPTION 
				"Optical Module resume from failure."
			::= { hwOpticalTrap 4 }

		
--  1.3.6.1.4.1.2011.5.25.219.2.4.5
		-- 1.3.6.1.4.1.2011.5.25.219.2.4.5
		hwOpticalInvalid NOTIFICATION-TYPE
			OBJECTS { hwEntityPhysicalIndex, entPhysicalName, hwEntityTrapFaultID }
			STATUS current
			DESCRIPTION 
				"Optical Module is invalid for some reason."
			::= { hwOpticalTrap 5 }

		
--  1.3.6.1.4.1.2011.5.25.219.2.4.6
		-- 1.3.6.1.4.1.2011.5.25.219.2.4.6
		hwOpticalInvalidResume NOTIFICATION-TYPE
			OBJECTS { hwEntityPhysicalIndex, entPhysicalName, hwEntityTrapFaultID }
			STATUS current
			DESCRIPTION 
				"Optical Module resume from invalid situation."
			::= { hwOpticalTrap 6 }

        
--  1.3.6.1.4.1.2011.5.25.219.2.4.7
		--  1.3.6.1.4.1.2011.5.25.219.2.4.7
		hwOpticalPowerAlarm NOTIFICATION-TYPE
			OBJECTS { entPhysicalName, hwUserDefAlarmName, hwEntityTrapFaultID }
			STATUS current
			DESCRIPTION 
				"Temperature rise over or fall below the warning alarm threshold.
				Only indicate the temperature of board,card or optical module."
			::= { hwOpticalTrap 7 }

        
--  1.3.6.1.4.1.2011.5.25.219.2.4.8
		--  1.3.6.1.4.1.2011.5.25.219.2.4.8
		hwOpticalPowerAlarmResume NOTIFICATION-TYPE
			OBJECTS { entPhysicalName, hwUserDefAlarmName, hwEntityTrapFaultID }
			STATUS current
			DESCRIPTION 
				"Temperature rise over or fall below the warning alarm threshold.
				Only indicate the temperature of board,card or optical module."
			::= { hwOpticalTrap 8 }

        
--  1.3.6.1.4.1.2011.5.25.219.2.5
		-- 1.3.6.1.4.1.2011.5.25.219.2.5
		hwPowerTrap OBJECT IDENTIFIER ::= { hwEntityTraps 5 }

		
--  1.3.6.1.4.1.2011.5.25.219.2.5.1
		-- 1.3.6.1.4.1.2011.5.25.219.2.5.1
		hwPowerRemove NOTIFICATION-TYPE
			OBJECTS { hwEntityPhysicalIndex, entPhysicalName, hwEntityTrapFaultID }
			STATUS current
			DESCRIPTION 
				"Power has been removed."
			::= { hwPowerTrap 1 }

		
--  1.3.6.1.4.1.2011.5.25.219.2.5.2
		-- 1.3.6.1.4.1.2011.5.25.219.2.5.2
		hwPowerInsert NOTIFICATION-TYPE
			OBJECTS { hwEntityPhysicalIndex, entPhysicalName, hwEntityTrapFaultID }
			STATUS current
			DESCRIPTION 
				"Power has been inserted."
			::= { hwPowerTrap 2 }

		
--  1.3.6.1.4.1.2011.5.25.219.2.5.3
		-- 1.3.6.1.4.1.2011.5.25.219.2.5.3
		hwPowerFail NOTIFICATION-TYPE
			OBJECTS { hwEntityPhysicalIndex, entPhysicalName, hwEntityTrapFaultID }
			STATUS current
			DESCRIPTION 
				"Power become failure for some reason."
			::= { hwPowerTrap 3 }

		
--  1.3.6.1.4.1.2011.5.25.219.2.5.4
		-- 1.3.6.1.4.1.2011.5.25.219.2.5.4
		hwPowerFailResume NOTIFICATION-TYPE
			OBJECTS { hwEntityPhysicalIndex, entPhysicalName, hwEntityTrapFaultID }
			STATUS current
			DESCRIPTION 
				"Power resume from failure."
			::= { hwPowerTrap 4 }

		
--  1.3.6.1.4.1.2011.5.25.219.2.5.5
		-- 1.3.6.1.4.1.2011.5.25.219.2.5.5
		hwPowerInvalid NOTIFICATION-TYPE
			OBJECTS { hwEntityPhysicalIndex, entPhysicalName, hwEntityTrapFaultID }
			STATUS current
			DESCRIPTION 
				"Power is invalid for some reason."
			::= { hwPowerTrap 5 }

		
--  1.3.6.1.4.1.2011.5.25.219.2.5.6
		-- 1.3.6.1.4.1.2011.5.25.219.2.5.6
		hwPowerInvalidResume NOTIFICATION-TYPE
			OBJECTS { hwEntityPhysicalIndex, entPhysicalName, hwEntityTrapFaultID }
			STATUS current
			DESCRIPTION 
				"Power resume from invalid situation."
			::= { hwPowerTrap 6 }

		
--  1.3.6.1.4.1.2011.5.25.219.2.5.7
		-- 1.3.6.1.4.1.2011.5.25.219.2.5.7
		hwPowerUnusable NOTIFICATION-TYPE
			OBJECTS { hwEntityPhysicalIndex, entPhysicalName, hwEntityTrapFaultID }
			STATUS current
			DESCRIPTION 
				"Power change to unusable status."
			::= { hwPowerTrap 7 }

		
--  1.3.6.1.4.1.2011.5.25.219.2.5.8
		-- 1.3.6.1.4.1.2011.5.25.219.2.5.8
		hwPowerUnusableResume NOTIFICATION-TYPE
			OBJECTS { hwEntityPhysicalIndex, entPhysicalName, hwEntityTrapFaultID }
			STATUS current
			DESCRIPTION 
				"Power change to usable status."
			::= { hwPowerTrap 8 }

		
--  1.3.6.1.4.1.2011.5.25.219.2.6
		-- 1.3.6.1.4.1.2011.5.25.219.2.6
		hwFanTrap OBJECT IDENTIFIER ::= { hwEntityTraps 6 }

		
--  1.3.6.1.4.1.2011.5.25.219.2.6.1
		-- 1.3.6.1.4.1.2011.5.25.219.2.6.1
		hwFanRemove NOTIFICATION-TYPE
			OBJECTS { hwEntityPhysicalIndex, entPhysicalName, hwEntityTrapFaultID }
			STATUS current
			DESCRIPTION 
				"Fan has been removed."
			::= { hwFanTrap 1 }

		
--  1.3.6.1.4.1.2011.5.25.219.2.6.2
		-- 1.3.6.1.4.1.2011.5.25.219.2.6.2
		hwFanInsert NOTIFICATION-TYPE
			OBJECTS { hwEntityPhysicalIndex, entPhysicalName, hwEntityTrapFaultID }
			STATUS current
			DESCRIPTION 
				"Fan has been inserted."
			::= { hwFanTrap 2 }

		
--  1.3.6.1.4.1.2011.5.25.219.2.6.3
		-- 1.3.6.1.4.1.2011.5.25.219.2.6.3
		hwFanFail NOTIFICATION-TYPE
			OBJECTS { hwEntityPhysicalIndex, entPhysicalName, hwEntityTrapFaultID }
			STATUS current
			DESCRIPTION 
				"Fan become failure for some reason."
			::= { hwFanTrap 3 }

		
--  1.3.6.1.4.1.2011.5.25.219.2.6.4
		-- 1.3.6.1.4.1.2011.5.25.219.2.6.4
		hwFanFailResume NOTIFICATION-TYPE
			OBJECTS { hwEntityPhysicalIndex, entPhysicalName, hwEntityTrapFaultID }
			STATUS current
			DESCRIPTION 
				"Fan resume from failure."
			::= { hwFanTrap 4 }

		
--  1.3.6.1.4.1.2011.5.25.219.2.6.5
		-- 1.3.6.1.4.1.2011.5.25.219.2.6.5
		hwFanInvalid NOTIFICATION-TYPE
			OBJECTS { hwEntityPhysicalIndex, entPhysicalName, hwEntityTrapFaultID }
			STATUS current
			DESCRIPTION 
				"Fan is invalid for some reason."
			::= { hwFanTrap 5 }

		
--  1.3.6.1.4.1.2011.5.25.219.2.6.6
		-- 1.3.6.1.4.1.2011.5.25.219.2.6.6
		hwFanInvalidResume NOTIFICATION-TYPE
			OBJECTS { hwEntityPhysicalIndex, entPhysicalName, hwEntityTrapFaultID }
			STATUS current
			DESCRIPTION 
				"Fan resume from invalid situation."
			::= { hwFanTrap 6 }

		
--  1.3.6.1.4.1.2011.5.25.219.2.6.7
		-- 1.3.6.1.4.1.2011.5.25.219.2.6.7
		hwFanUnusable NOTIFICATION-TYPE
			OBJECTS { hwEntityPhysicalIndex, entPhysicalName, hwEntityTrapFaultID }
			STATUS current
			DESCRIPTION 
				"Fan change to unusable status."
			::= { hwFanTrap 7 }

		
--  1.3.6.1.4.1.2011.5.25.219.2.6.8
		-- 1.3.6.1.4.1.2011.5.25.219.2.6.8
		hwFanUnusableResume NOTIFICATION-TYPE
			OBJECTS { hwEntityPhysicalIndex, entPhysicalName, hwEntityTrapFaultID }
			STATUS current
			DESCRIPTION 
				"Fan change to usable status."
			::= { hwFanTrap 8 }

		
--  1.3.6.1.4.1.2011.5.25.219.2.7
		-- 1.3.6.1.4.1.2011.5.25.219.2.7
		hwLcdTrap OBJECT IDENTIFIER ::= { hwEntityTraps 7 }

		
--  1.3.6.1.4.1.2011.5.25.219.2.7.1
		-- 1.3.6.1.4.1.2011.5.25.219.2.7.1
		hwLcdRemove NOTIFICATION-TYPE
			OBJECTS { hwEntityPhysicalIndex, entPhysicalName, hwEntityTrapFaultID }
			STATUS current
			DESCRIPTION 
				"Lcd has been removed."
			::= { hwLcdTrap 1 }

		
--  1.3.6.1.4.1.2011.5.25.219.2.7.2
		-- 1.3.6.1.4.1.2011.5.25.219.2.7.2
		hwLcdInsert NOTIFICATION-TYPE
			OBJECTS { hwEntityPhysicalIndex, entPhysicalName, hwEntityTrapFaultID }
			STATUS current
			DESCRIPTION 
				"Lcd has been inserted."
			::= { hwLcdTrap 2 }

		
--  1.3.6.1.4.1.2011.5.25.219.2.7.3
		-- 1.3.6.1.4.1.2011.5.25.219.2.7.3
		hwLcdInvalid NOTIFICATION-TYPE
			OBJECTS { hwEntityPhysicalIndex, entPhysicalName, hwEntityTrapFaultID }
			STATUS current
			DESCRIPTION 
				"Lcd is invalid for some reason."
			::= { hwLcdTrap 3 }

		
--  1.3.6.1.4.1.2011.5.25.219.2.7.4
		-- 1.3.6.1.4.1.2011.5.25.219.2.7.4
		hwLcdInvalidResume NOTIFICATION-TYPE
			OBJECTS { hwEntityPhysicalIndex, entPhysicalName, hwEntityTrapFaultID }
			STATUS current
			DESCRIPTION 
				"Lcd resume from invalid situation."
			::= { hwLcdTrap 4 }

		
--  1.3.6.1.4.1.2011.5.25.219.2.7.5
		-- 1.3.6.1.4.1.2011.5.25.219.2.7.5
		hwLcdUnusable NOTIFICATION-TYPE
			OBJECTS { hwEntityPhysicalIndex, entPhysicalName, hwEntityTrapFaultID }
			STATUS current
			DESCRIPTION 
				"Lcd change to unusable status."
			::= { hwLcdTrap 5 }

		
--  1.3.6.1.4.1.2011.5.25.219.2.7.6
		-- 1.3.6.1.4.1.2011.5.25.219.2.7.6
		hwLcdUnusableResume NOTIFICATION-TYPE
			OBJECTS { hwEntityPhysicalIndex, entPhysicalName, hwEntityTrapFaultID }
			STATUS current
			DESCRIPTION 
				"Lcd change to usable status."
			::= { hwLcdTrap 6 }

		
--  1.3.6.1.4.1.2011.5.25.219.2.8
		-- 1.3.6.1.4.1.2011.5.25.219.2.8
		hwCmuTrap OBJECT IDENTIFIER ::= { hwEntityTraps 8 }

		
--  1.3.6.1.4.1.2011.5.25.219.2.8.1
		-- 1.3.6.1.4.1.2011.5.25.219.2.8.1
		hwCmuRemove NOTIFICATION-TYPE
			OBJECTS { hwEntityPhysicalIndex, entPhysicalName, hwEntityTrapFaultID }
			STATUS current
			DESCRIPTION 
				"Cmu has been removed."
			::= { hwCmuTrap 1 }

		
--  1.3.6.1.4.1.2011.5.25.219.2.8.2
		-- 1.3.6.1.4.1.2011.5.25.219.2.8.2
		hwCmuInsert NOTIFICATION-TYPE
			OBJECTS { hwEntityPhysicalIndex, entPhysicalName, hwEntityTrapFaultID }
			STATUS current
			DESCRIPTION 
				"Cmu has been inserted."
			::= { hwCmuTrap 2 }

		
--  1.3.6.1.4.1.2011.5.25.219.2.8.3
		-- 1.3.6.1.4.1.2011.5.25.219.2.8.3
		hwCmuInvalid NOTIFICATION-TYPE
			OBJECTS { hwEntityPhysicalIndex, entPhysicalName, hwEntityTrapFaultID }
			STATUS current
			DESCRIPTION 
				"Cmu is invalid for some reason."
			::= { hwCmuTrap 3 }

		
--  1.3.6.1.4.1.2011.5.25.219.2.8.4
		-- 1.3.6.1.4.1.2011.5.25.219.2.8.4
		hwCmuInvalidResume NOTIFICATION-TYPE
			OBJECTS { hwEntityPhysicalIndex, entPhysicalName, hwEntityTrapFaultID }
			STATUS current
			DESCRIPTION 
				"Cmu reusme from invalid situation."
			::= { hwCmuTrap 4 }

		
--  1.3.6.1.4.1.2011.5.25.219.2.8.5
		-- 1.3.6.1.4.1.2011.5.25.219.2.8.5
		hwCmuUnusable NOTIFICATION-TYPE
			OBJECTS { hwEntityPhysicalIndex, entPhysicalName, hwEntityTrapFaultID }
			STATUS current
			DESCRIPTION 
				"Cmu change to unusable status."
			::= { hwCmuTrap 5 }

		
--  1.3.6.1.4.1.2011.5.25.219.2.8.6
		-- 1.3.6.1.4.1.2011.5.25.219.2.8.6
		hwCmuUnusableResume NOTIFICATION-TYPE
			OBJECTS { hwEntityPhysicalIndex, entPhysicalName, hwEntityTrapFaultID }
			STATUS current
			DESCRIPTION 
				"Cmu change to usable status."
			::= { hwCmuTrap 6 }

		
--  1.3.6.1.4.1.2011.5.25.219.2.9
		-- 1.3.6.1.4.1.2011.5.25.219.2.9
		hwCommunicateTrap OBJECT IDENTIFIER ::= { hwEntityTraps 9 }

		
--  1.3.6.1.4.1.2011.5.25.219.2.9.1
		-- 1.3.6.1.4.1.2011.5.25.219.2.9.1
		hwCommunicateError NOTIFICATION-TYPE
			OBJECTS { hwEntityPhysicalIndex, entPhysicalName, hwEntityTrapEntType, hwEntityTrapFaultID, hwEntityCommunicateType
				 }
			STATUS current
			DESCRIPTION 
				"Communication error has been detected."
			::= { hwCommunicateTrap 1 }

		
--  1.3.6.1.4.1.2011.5.25.219.2.9.2
		-- 1.3.6.1.4.1.2011.5.25.219.2.9.2
		hwCommunicateResume NOTIFICATION-TYPE
			OBJECTS { hwEntityPhysicalIndex, entPhysicalName, hwEntityTrapEntType, hwEntityTrapFaultID, hwEntityCommunicateType
				 }
			STATUS current
			DESCRIPTION 
				"Resume from communication error situation."
			::= { hwCommunicateTrap 2 }

		
--  1.3.6.1.4.1.2011.5.25.219.2.10
		-- 1.3.6.1.4.1.2011.5.25.219.2.10
		hwEnvironmentTrap OBJECT IDENTIFIER ::= { hwEntityTraps 10 }

		
--  1.3.6.1.4.1.2011.5.25.219.2.10.1
		-- 1.3.6.1.4.1.2011.5.25.219.2.10.1
		hwTempAlarm NOTIFICATION-TYPE
			OBJECTS { hwEntityThresholdType, hwEntityThresholdValue, hwEntityThresholdCurrent, 
				hwEntityTrapFaultID }
			STATUS current
			DESCRIPTION 
				"Temperature rise over or fall below the alarm threshold."
			::= { hwEnvironmentTrap 1 }

		
--  1.3.6.1.4.1.2011.5.25.219.2.10.2
		-- 1.3.6.1.4.1.2011.5.25.219.2.10.2
		hwTempResume NOTIFICATION-TYPE
			OBJECTS { hwEntityThresholdType, hwEntityThresholdValue, hwEntityThresholdCurrent, 
				hwEntityTrapFaultID }
			STATUS current
			DESCRIPTION 
				"Temperature back to normal level."
			::= { hwEnvironmentTrap 2 }

		
--  1.3.6.1.4.1.2011.5.25.219.2.10.3
		-- 1.3.6.1.4.1.2011.5.25.219.2.10.3
		hwHumidityAlarm NOTIFICATION-TYPE
			OBJECTS { hwEntityThresholdType, hwEntityThresholdValue, hwEntityThresholdCurrent,
			    hwEntityTrapFaultID}
			STATUS current
			DESCRIPTION 
				"Humidity rise over or fall below the alarm threshold."
			::= { hwEnvironmentTrap 3 }

		
--  1.3.6.1.4.1.2011.5.25.219.2.10.4
		-- 1.3.6.1.4.1.2011.5.25.219.2.10.4
		hwHumidityResume NOTIFICATION-TYPE
			OBJECTS { hwEntityThresholdType, hwEntityThresholdValue, hwEntityThresholdCurrent, 
				hwEntityTrapFaultID }
			STATUS current
			DESCRIPTION 
				"Humidity back to normal level."
			::= { hwEnvironmentTrap 4 }

		
--  1.3.6.1.4.1.2011.5.25.219.2.10.5
		-- 1.3.6.1.4.1.2011.5.25.219.2.10.5
		hwVoltAlarm NOTIFICATION-TYPE
			OBJECTS { hwEntityThresholdType, hwEntityThresholdValue, hwEntityThresholdCurrent, 
				hwEntityTrapFaultID }
			STATUS current
			DESCRIPTION 
				"Voltage of power rise over or fall below the alarm threshold."
			::= { hwEnvironmentTrap 5 }

		
--  1.3.6.1.4.1.2011.5.25.219.2.10.6
		-- 1.3.6.1.4.1.2011.5.25.219.2.10.6
		hwVoltResume NOTIFICATION-TYPE
			OBJECTS { hwEntityThresholdType, hwEntityThresholdValue, hwEntityThresholdCurrent, 
				hwEntityTrapFaultID }
			STATUS current
			DESCRIPTION 
				"Voltage back to normal level."
			::= { hwEnvironmentTrap 6 }

		
--  1.3.6.1.4.1.2011.5.25.219.2.10.7
		-- 1.3.6.1.4.1.2011.5.25.219.2.10.7
		hwGateAlarm NOTIFICATION-TYPE
			OBJECTS { hwEntityThresholdType, hwEntityThresholdValue, hwEntityThresholdCurrent, 
				hwEntityTrapFaultID }
			STATUS current
			DESCRIPTION 
				"Gate switch to the alarm status."
			::= { hwEnvironmentTrap 7 }

		
--  1.3.6.1.4.1.2011.5.25.219.2.10.8
		-- 1.3.6.1.4.1.2011.5.25.219.2.10.8
		hwGateResume NOTIFICATION-TYPE
			OBJECTS { hwEntityThresholdType, hwEntityThresholdValue, hwEntityThresholdCurrent, 
				hwEntityTrapFaultID }
			STATUS current
			DESCRIPTION 
				"Gate switch to normal status."
			::= { hwEnvironmentTrap 8 }

		
--  1.3.6.1.4.1.2011.5.25.219.2.10.9
		-- 1.3.6.1.4.1.2011.5.25.219.2.10.9
		hwFogAlarm NOTIFICATION-TYPE
			OBJECTS { hwEntityThresholdType, hwEntityThresholdValue, hwEntityThresholdCurrent, 
				hwEntityTrapFaultID }
			STATUS current
			DESCRIPTION 
				"Fog rise over alarm threshold."
			::= { hwEnvironmentTrap 9 }

		
--  1.3.6.1.4.1.2011.5.25.219.2.10.10
		-- 1.3.6.1.4.1.2011.5.25.219.2.10.10
		hwFogResume NOTIFICATION-TYPE
			OBJECTS { hwEntityThresholdType, hwEntityThresholdValue, hwEntityThresholdCurrent, 
				hwEntityTrapFaultID }
			STATUS current
			DESCRIPTION 
				"Fog back to normal level."
			::= { hwEnvironmentTrap 10 }

		
--  1.3.6.1.4.1.2011.5.25.219.2.10.11
		-- 1.3.6.1.4.1.2011.5.25.219.2.10.11
		hwUnstableAlarm NOTIFICATION-TYPE
			OBJECTS { hwEntityPhysicalIndex, entPhysicalName, hwEntityTrapEntType, hwEntityTrapFaultID }
			STATUS current
			DESCRIPTION 
				"Entity has been inserted but position unstable."
			::= { hwEnvironmentTrap 11 }

		
--  1.3.6.1.4.1.2011.5.25.219.2.10.12
		-- 1.3.6.1.4.1.2011.5.25.219.2.10.12
		hwUnstableResume NOTIFICATION-TYPE
			OBJECTS { hwEntityPhysicalIndex, entPhysicalName, hwEntityTrapEntType, hwEntityTrapFaultID }
			STATUS current
			DESCRIPTION 
				"Resume from entity position unstable situation."
			::= { hwEnvironmentTrap 12 }

		
--  1.3.6.1.4.1.2011.5.25.219.2.10.13
		-- 1.3.6.1.4.1.2011.5.25.219.2.10.13
		hwBrdTempAlarm NOTIFICATION-TYPE
			OBJECTS { hwEntityPhysicalIndex, entPhysicalName, hwEntityThresholdType, hwEntityThresholdWarning, hwEntityThresholdCurrent, 
				hwEntityTrapFaultID }
			STATUS current
			DESCRIPTION 
				"Temperature rise over or fall below the warning alarm threshold.
				Only indicate the temperature of board,card or optical module."
			::= { hwEnvironmentTrap 13 }

		
--  1.3.6.1.4.1.2011.5.25.219.2.10.14
		-- 1.3.6.1.4.1.2011.5.25.219.2.10.14
		hwBrdTempResume NOTIFICATION-TYPE
			OBJECTS { hwEntityPhysicalIndex, entPhysicalName, hwEntityThresholdType, hwEntityThresholdWarning, hwEntityThresholdCurrent, 
				hwEntityTrapFaultID }
			STATUS current
			DESCRIPTION 
				"Temperature back to normal level.
				Only indicate the temperature of board,card or optical module."
			::= { hwEnvironmentTrap 14 }

		
--  1.3.6.1.4.1.2011.5.25.219.2.10.15
		-- 1.3.6.1.4.1.2011.5.25.219.2.10.15
		hwBrdTempFatalAlarm NOTIFICATION-TYPE
			OBJECTS { hwEntityPhysicalIndex, entPhysicalName, hwEntityThresholdType, hwEntityThresholdCritical, hwEntityThresholdCurrent, 
				hwEntityTrapFaultID }
			STATUS current
			DESCRIPTION 
				"Temperature rise over or fall below the critical alarm threshold.
				Only indicate the temperature of board,card or optical module."
			::= { hwEnvironmentTrap 15 }

		
--  1.3.6.1.4.1.2011.5.25.219.2.10.16
		-- 1.3.6.1.4.1.2011.5.25.219.2.10.16
		hwBrdTempFatalResume NOTIFICATION-TYPE
			OBJECTS { hwEntityPhysicalIndex, entPhysicalName, hwEntityThresholdType, hwEntityThresholdCritical, hwEntityThresholdCurrent, 
				hwEntityTrapFaultID }
			STATUS current
			DESCRIPTION 
				"Temperature back to normal level.
				Only indicate the temperature of board,card or optical module."
			::= { hwEnvironmentTrap 16 }

--  1.3.6.1.4.1.2011.5.25.219.2.10.17
		-- 1.3.6.1.4.1.2011.5.25.219.2.10.17
		hwPowerFailureAlarm NOTIFICATION-TYPE
			STATUS current
			DESCRIPTION 
				"Power supply failed."
			::= { hwEnvironmentTrap 17 }


--  1.3.6.1.4.1.2011.5.25.219.2.10.18
		-- 1.3.6.1.4.1.2011.5.25.219.2.10.18
		hwPowerFailureResume NOTIFICATION-TYPE
			STATUS current
			DESCRIPTION 
				"Power supply resumed."
			::= { hwEnvironmentTrap 18 }

--  1.3.6.1.4.1.2011.5.25.219.2.11
		-- 1.3.6.1.4.1.2011.5.25.219.2.11
		hwSystemConfigTrap OBJECT IDENTIFIER ::= { hwEntityTraps 11 }

		
--  1.3.6.1.4.1.2011.5.25.219.2.11.1
		-- 1.3.6.1.4.1.2011.5.25.219.2.11.1
		hwSystemConfigError NOTIFICATION-TYPE
			OBJECTS { hwEntityTrapFaultID }
			STATUS current
			DESCRIPTION 
				"System configuration error has been detected."
			::= { hwSystemConfigTrap 1 }

		
--  1.3.6.1.4.1.2011.5.25.219.2.11.2
		-- 1.3.6.1.4.1.2011.5.25.219.2.11.2
		hwSystemConfigResume NOTIFICATION-TYPE
			OBJECTS { hwEntityTrapFaultID }
			STATUS current
			DESCRIPTION 
				"Resume from system configuration error situation."
			::= { hwSystemConfigTrap 2 }

-- 1.3.6.1.4.1.2011.5.25.219.2.11.3
		-- 1.3.6.1.4.1.2011.5.25.219.2.11.3
		hwSystemRollback NOTIFICATION-TYPE
			OBJECTS { hwEntityTrapFaultID, hwSoftwareVersion, hwStartupSoftwareFileName }
			STATUS current
			DESCRIPTION 
				"System configuration error has been detected."
			::= { hwSystemConfigTrap 3 }
 
--  1.3.6.1.4.1.2011.5.25.219.2.12
		-- 1.3.6.1.4.1.2011.5.25.219.2.12
		hwPortTrap OBJECT IDENTIFIER ::= { hwEntityTraps 12 }

--  1.3.6.1.4.1.2011.5.25.219.2.12.1
		-- 1.3.6.1.4.1.2011.5.25.219.2.12.1
		hwPortDown NOTIFICATION-TYPE
			OBJECTS { hwEntityPhysicalIndex, entPhysicalName, hwEntityTrapFaultID }
			STATUS current
			DESCRIPTION 
				"One of the port physical connect down."
			::= { hwPortTrap 1 }

                
--  1.3.6.1.4.1.2011.5.25.219.2.12.2
		-- 1.3.6.1.4.1.2011.5.25.219.2.12.2
 		hwPortUp NOTIFICATION-TYPE
			OBJECTS { hwEntityPhysicalIndex, entPhysicalName, hwEntityTrapFaultID }
			STATUS current
			DESCRIPTION 
				"One of the port physical connect up."
			::= { hwPortTrap 2 }


--  1.3.6.1.4.1.2011.5.25.219.2.13
		-- 1.3.6.1.4.1.2011.5.25.219.2.13
 		hwUserDefTrap OBJECT IDENTIFIER ::= { hwEntityTraps 13 }


--  1.3.6.1.4.1.2011.5.25.219.2.13.1
		-- 1.3.6.1.4.1.2011.5.25.219.2.13.1
		hwUserDefAlarm NOTIFICATION-TYPE
			OBJECTS { hwEntityPhysicalIndex, entPhysicalName, hwUserDefAlarmName, hwUserDefChannel }
			STATUS current
			DESCRIPTION 
				"User defined alarm has been detected."
			::= { hwUserDefTrap 1 }

                
--  1.3.6.1.4.1.2011.5.25.219.2.13.2
		-- 1.3.6.1.4.1.2011.5.25.219.2.13.2
		hwUserDefResume NOTIFICATION-TYPE
			OBJECTS { hwEntityPhysicalIndex, entPhysicalName, hwUserDefAlarmName, hwUserDefChannel }
			STATUS current
			DESCRIPTION 
				"Resume from User defined alarm."
			::= { hwUserDefTrap 2 }

        
--   1.3.6.1.4.1.2011.5.25.219.2.14
		-- 1.3.6.1.4.1.2011.5.25.219.2.14
		hwCPUTrap OBJECT IDENTIFIER ::= { hwEntityTraps 14 }

        
--   1.3.6.1.4.1.2011.5.25.219.2.14.1
		-- 1.3.6.1.4.1.2011.5.25.219.2.14.1
		hwCPUUtilizationRising NOTIFICATION-TYPE
			OBJECTS { hwEntityPhysicalIndex, entPhysicalName, hwEntityThresholdType, hwEntityThresholdWarning, hwEntityThresholdCurrent, 
			hwEntityTrapFaultID }
			STATUS current
			DESCRIPTION 
				"CPU utilization overrun."
			::= { hwCPUTrap 1 }

        
--   1.3.6.1.4.1.2011.5.25.219.2.14.2
		-- 1.3.6.1.4.1.2011.5.25.219.2.14.2
		hwCPUUtilizationResume NOTIFICATION-TYPE
			OBJECTS { hwEntityPhysicalIndex, entPhysicalName, hwEntityThresholdType, hwEntityThresholdWarning, hwEntityThresholdCurrent, 
			hwEntityTrapFaultID }
			STATUS current
			DESCRIPTION 
				"CPU utilization back to normal level"
			::= { hwCPUTrap 2 }

        
--   1.3.6.1.4.1.2011.5.25.219.2.15
		-- 1.3.6.1.4.1.2011.5.25.219.2.15
		hwMemoryTrap OBJECT IDENTIFIER ::= { hwEntityTraps 15 }

        
--   1.3.6.1.4.1.2011.5.25.219.2.15.1
		-- 1.3.6.1.4.1.2011.5.25.219.2.15.1
		hwMemUtilizationRising NOTIFICATION-TYPE
			OBJECTS { hwEntityPhysicalIndex, entPhysicalName, hwEntityThresholdType, hwEntityThresholdWarning, hwEntityThresholdCurrent, 
			hwEntityTrapFaultID }
			STATUS current
			DESCRIPTION 
				"Memory utilization overrun."
			::= { hwMemoryTrap 1 }

        
--   1.3.6.1.4.1.2011.5.25.219.2.15.2
		-- 1.3.6.1.4.1.2011.5.25.219.2.15.2
		hwMemUtilizationResume NOTIFICATION-TYPE
			OBJECTS { hwEntityPhysicalIndex, entPhysicalName, hwEntityThresholdType, hwEntityThresholdWarning, hwEntityThresholdCurrent, 
			hwEntityTrapFaultID }
			STATUS current
			DESCRIPTION 
				"Memory utilization back to normal level"
			::= { hwMemoryTrap 2 }


--   1.3.6.1.4.1.2011.5.25.219.2.16
		-- 1.3.6.1.4.1.2011.5.25.219.2.16     
		hwStorageDevTrap OBJECT IDENTIFIER ::= { hwEntityTraps 16 }

        
--     1.3.6.1.4.1.2011.5.25.219.2.16.1
		-- 1.3.6.1.4.1.2011.5.25.219.2.16.1
		hwStorageDevRemove NOTIFICATION-TYPE
			OBJECTS { entPhysicalName, hwStorageDevName, hwEntityTrapFaultID }
			STATUS current
			DESCRIPTION 
				"Memory utilization overrun."
			::= { hwStorageDevTrap 1 }

        
--     1.3.6.1.4.1.2011.5.25.219.2.16.2
		-- 1.3.6.1.4.1.2011.5.25.219.2.16.2
		hwStorageDevInsert NOTIFICATION-TYPE
			OBJECTS { entPhysicalName, hwStorageDevName, hwEntityTrapFaultID }
			STATUS current
			DESCRIPTION 
				"Memory utilization back to normal level"
			::= { hwStorageDevTrap 2 } 


--   1.3.6.1.4.1.2011.5.25.219.2.17
		-- 1.3.6.1.4.1.2011.5.25.219.2.17
		hwPppTrap OBJECT IDENTIFIER ::= { hwEntityTraps 17 }


--   1.3.6.1.4.1.2011.5.25.219.2.17.1
		-- 1.3.6.1.4.1.2011.5.25.219.2.17.1     
		hwPppLoopbackDetect NOTIFICATION-TYPE
			OBJECTS { hwBaseTrapSeverity, hwBaseTrapProbableCause, hwBaseTrapEventType, ifIndex, ifName }
			STATUS current
			DESCRIPTION 
				"The interface Loopback is detected."
			::= { hwPppTrap 1 }


--   1.3.6.1.4.1.2011.5.25.219.2.17.2
		-- 1.3.6.1.4.1.2011.5.25.219.2.17.2        
		hwPppLoopbackDetResume NOTIFICATION-TYPE
			OBJECTS { hwBaseTrapSeverity, hwBaseTrapProbableCause, hwBaseTrapEventType, ifIndex, ifName }
			STATUS current
			DESCRIPTION 
				"The interface is recovered from Loopback."
			::= { hwPppTrap 2 }       


--   1.3.6.1.4.1.2011.5.25.219.2.18
		-- 1.3.6.1.4.1.2011.5.25.219.2.18
		hwFileStatusTrap OBJECT IDENTIFIER ::= { hwEntityTraps 18 }
	

-- 1.3.6.1.4.1.2011.5.25.219.2.18.1
		-- 1.3.6.1.4.1.2011.5.25.219.2.18.1
		hwFileError NOTIFICATION-TYPE
			OBJECTS { entPhysicalName, hwStorageDevName, hwEntityTrapFaultID }
			STATUS current
			DESCRIPTION 
				"Memory utilization overrun."
			::= { hwFileStatusTrap 1 }


-- 1.3.6.1.4.1.2011.5.25.219.2.18.2
		-- 1.3.6.1.4.1.2011.5.25.219.2.18.2
		hwFileErrorResume NOTIFICATION-TYPE
			OBJECTS { entPhysicalName, hwStorageDevName, hwEntityTrapFaultID }
			STATUS current
			DESCRIPTION 
				"Memory utilization back to normal level"
			::= { hwFileStatusTrap 2 }


--   1.3.6.1.4.1.2011.5.25.219.2.19
-- 1.3.6.1.4.1.2011.5.25.219.2.19
		-- 1.3.6.1.4.1.2011.5.25.219.2.19
		hwUSBTrap OBJECT IDENTIFIER ::= { hwEntityTraps 19 }


-- 1.3.6.1.4.1.2011.5.25.219.2.19.1
		-- 1.3.6.1.4.1.2011.5.25.219.2.19.1
		hwUSBInsert NOTIFICATION-TYPE
			OBJECTS { hwEntityPhysicalIndex, entPhysicalName, hwEntityTrapEntType, hwEntityTrapFaultID }
			STATUS current
			DESCRIPTION 
				"The USB device has been inserted."
			::= { hwUSBTrap 1 }


-- 1.3.6.1.4.1.2011.5.25.219.2.19.2
		-- 1.3.6.1.4.1.2011.5.25.219.2.19.2
		hwUSBRemove NOTIFICATION-TYPE
			OBJECTS { hwEntityPhysicalIndex, entPhysicalName, hwEntityTrapEntType, hwEntityTrapFaultID }
			STATUS current
			DESCRIPTION 
				"The USB device has been removed."
			::= { hwUSBTrap 2 }       
			
			     
--  1.3.6.1.4.1.2011.5.25.219.3
		-- 1.3.6.1.4.1.2011.5.25.219.3
		hwEntityTrapConformance OBJECT IDENTIFIER ::= { hwEntityTrapMIB 3 }

		
--  1.3.6.1.4.1.2011.5.25.219.3.1
		-- 1.3.6.1.4.1.2011.5.25.219.3.1
		hwEntityTrapCompliances OBJECT IDENTIFIER ::= { hwEntityTrapConformance 1 }

		
--   this module
-- 1.3.6.1.4.1.2011.5.25.219.3.1.1
-- this module
		-- 1.3.6.1.4.1.2011.5.25.219.3.1.1
		hwEntityTrapCompliance MODULE-COMPLIANCE
			STATUS current
			DESCRIPTION 
				"Compliance statement for agents that provide full support for 
				hwBaseTrapMIB."
			MODULE -- this module
				MANDATORY-GROUPS { hwEntityObjectGroup }
			::= { hwEntityTrapCompliances 1 }

		
--  1.3.6.1.4.1.2011.5.25.219.3.2
		-- 1.3.6.1.4.1.2011.5.25.219.3.2
		hwEntityTrapGroups OBJECT IDENTIFIER ::= { hwEntityTrapConformance 2 }

		
--  1.3.6.1.4.1.2011.5.25.219.3.2.1
		-- 1.3.6.1.4.1.2011.5.25.219.3.2.1
		hwEntityObjectGroup OBJECT-GROUP
			OBJECTS { hwEntityPhysicalIndex, hwEntityTrapEntType, hwEntityTrapFaultID, hwEntityCommunicateType, hwEntityThresholdType, 
				hwEntityThresholdValue, hwEntityThresholdCurrent, hwEntityThresholdCritical, hwEntityThresholdWarning, hwUserDefAlarmName, 
				hwUserDefChannel, hwSoftwareVersion, hwStartupSoftwareFileName, hwStorageDevName }
			STATUS current
			DESCRIPTION 
				"Group for base trap objects."
			::= { hwEntityTrapGroups 1 }

		
--  1.3.6.1.4.1.2011.5.25.219.3.2.2
		-- 1.3.6.1.4.1.2011.5.25.219.3.2.2
		hwEntityTrapGroup NOTIFICATION-GROUP
			NOTIFICATIONS { hwChassisRemove, hwChassisInsert, hwChassisFail, hwChassisFailResume, hwChassisInvalid, 
				hwChassisInvalidResume, hwBoardRemove, hwBoardInsert, hwBoardFail, hwBoardFailResume, 
				hwBoardInvalid, hwBoardInvalidResume, hwBoardLeaveMaster, hwBoardBecomeMaster, hwCardRemove, 
				hwCardInsert, hwCardFail, hwCardFailResume, hwCardInvalid, hwCardInvalidResume, 
				hwOpticalRemove, hwOpticalInsert, hwOpticalFail, hwOpticalFailResume, hwOpticalInvalid, 
				hwOpticalInvalidResume, hwPowerRemove, hwPowerInsert, hwPowerFail, hwPowerFailResume, 
				hwPowerInvalid, hwPowerInvalidResume, hwPowerUnusable, hwPowerUnusableResume, hwFanRemove, 
				hwFanInsert, hwFanFail, hwFanFailResume, hwFanInvalid, hwFanInvalidResume, 
				hwFanUnusable, hwFanUnusableResume, hwLcdRemove, hwLcdInsert, hwLcdInvalid, 
				hwLcdInvalidResume, hwLcdUnusable, hwLcdUnusableResume, hwCmuRemove, hwCmuInsert, 
				hwCmuInvalid, hwCmuInvalidResume, hwCmuUnusable, hwCmuUnusableResume, hwCommunicateError, 
				hwCommunicateResume, hwTempAlarm, hwTempResume, hwHumidityAlarm, hwHumidityResume, 
				hwVoltAlarm, hwVoltResume, hwGateAlarm, hwGateResume, hwFogAlarm, 
				hwFogResume, hwUnstableAlarm, hwUnstableResume, hwBrdTempAlarm, hwBrdTempResume, 
				hwBrdTempFatalAlarm, hwBrdTempFatalResume, hwPowerFailureAlarm, hwPowerFailureResume, 
				hwSystemConfigError, hwSystemConfigResume, hwPortDown, 
				hwPortUp, hwUserDefAlarm, hwUserDefResume, hwCPUUtilizationRising, hwCPUUtilizationResume, 
				hwMemUtilizationRising, hwMemUtilizationResume, hwStorageDevRemove, hwStorageDevInsert, hwSystemRollback, 
				hwUpMicroSwitchOpen, hwUpMicroSwitchClose, hwDownMicroSwitchOpen, hwDownMicroSwitchClose, hwOpticalPowerAlarm, 
				hwOpticalPowerAlarmResume }
			STATUS current
			DESCRIPTION 
				"Group for all base traps."
			::= { hwEntityTrapGroups 2 }

		
	
	END

--
-- HUAWEI-ENTITY-TRAP-MIB.my
--
