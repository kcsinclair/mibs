--==================================================================
-- Copyright (C) 2006 by  HUAWEI TECHNOLOGIES. All rights reserved.
-- 
-- Description: HUAWEI NAP MIB
-- Reference:
-- Version: V1.0
-- History:
-- <author>,  <date>,  <contents>
-- fengchong   2009-07-29
-- ==================================================================

-- ==================================================================
-- 
-- Variables and types are imported
--
-- ==================================================================

    HUAWEI-NAP-MIB DEFINITIONS ::= BEGIN
 
        IMPORTS
            hwDatacomm          
                FROM HUAWEI-MIB         
            OBJECT-GROUP, MODULE-COMPLIANCE, NOTIFICATION-GROUP         
                FROM SNMPv2-CONF            
            TimeTicks, Integer32, Gauge32, OBJECT-TYPE, MODULE-IDENTITY, 
            NOTIFICATION-TYPE, TEXTUAL-CONVENTION
                FROM SNMPv2-SMI         
            RowStatus           
                FROM SNMPv2-TC;
    
    
        hwNap MODULE-IDENTITY 
            LAST-UPDATED "200903171027Z"        
            ORGANIZATION 
                "Huawei Technologies Co.,Ltd."
            CONTACT-INFO 
                "VRP Team Huawei Technologies Co.,Ltd.
                Huawei Bld.,NO.3 Xinxi Rd., 
                Shang-Di Information Industry Base,
                Hai-Dian District Beijing P.R. China
                http://www.huawei.com
                Zip:100085
                "
            DESCRIPTION 
                "The MIB module for nap between host and netmanager."
                        REVISION "200903171027Z"        
            DESCRIPTION 
                "The initial revision of this MIB module ."
            ::= { hwDatacomm 206 }

        DateAndTime ::= TEXTUAL-CONVENTION
            DISPLAY-HINT "2d-1d-1d,1d:1d:1d.1d,1a1d:1d"
            STATUS       current
            DESCRIPTION
            "A date-time specification.

            field  octets  contents                  range
            -----  ------  --------                  -----
              1      1-2   year*                     0..65536
              2       3    month                     1..12
              3       4    day                       1..31
              4       5    hour                      0..23
              5       6    minutes                   0..59
              6       7    seconds                   0..60
                           (use 60 for leap-second)
              7       8    deci-seconds              0..9
              8       9    direction from UTC        '+' / '-'
              9      10    hours from UTC*           0..13
             10      11    minutes from UTC          0..59

            * Notes:
            - the value of year is in network-byte order
            - daylight saving time in New Zealand is +13

            For example, Tuesday May 26, 1992 at 1:30:15 PM EDT would be
            displayed as:

                             1992-5-26,13:30:15.0,-4:0
            Note that if only local time is known, then timezone
            information (fields 8-10) is not present."
            SYNTAX       OCTET STRING (SIZE (8 | 11))
--
-- Node definitions
--
    
--  ==================================================================
-- 
-- ======================= definition begin =========================
-- 
-- ==================================================================  
        hwNapScalarObjects OBJECT IDENTIFIER ::= { hwNap 1 }
        hwNapTableObjects OBJECT IDENTIFIER ::= { hwNap 2 }
        hwNapNotifications OBJECT IDENTIFIER ::= { hwNap 3 }
        
        hwNapNeighborNum OBJECT-TYPE
            SYNTAX Integer32
            MAX-ACCESS read-only
            STATUS current
            DESCRIPTION
                "current configed nap neighbor num."
            ::= { hwNapScalarObjects 1 }
               
        hwNapNeighborTable OBJECT-TYPE
            SYNTAX SEQUENCE OF HwNapNeighborEntry
            MAX-ACCESS not-accessible
            STATUS current
            DESCRIPTION
                "This table contains the records of configed nap neighbor."
            ::= { hwNapTableObjects 1 }


        hwNapNeighborEntry OBJECT-TYPE
            SYNTAX HwNapNeighborEntry
            MAX-ACCESS not-accessible
            STATUS current
            DESCRIPTION
                "Entry of hwNapNeighborTable."
            INDEX { hwNapNeighborIndex }
            ::= { hwNapNeighborTable 1 }

        
        HwNapNeighborEntry::=
            SEQUENCE { 
                hwNapNeighborIndex
                     Integer32,
                hwNapLocalPortName
                    OCTET STRING,
                hwNapNeighborStatus
                    INTEGER,
                hwNapNeighborAbnormalReason
                    INTEGER       
 }  
        hwNapNeighborIndex OBJECT-TYPE
            SYNTAX Integer32(1..8)
            MAX-ACCESS read-only
            STATUS current
            DESCRIPTION
                "Index of nap neighbor table."
            ::= { hwNapNeighborEntry 1 }  
            
        hwNapLocalPortName OBJECT-TYPE
            SYNTAX OCTET STRING
            MAX-ACCESS read-only
            STATUS current
            DESCRIPTION
                "The local port name of nap neighbor."
            ::= { hwNapNeighborEntry 2 }  
      
        hwNapNeighborStatus OBJECT-TYPE
            SYNTAX INTEGER 
                           {detecting(1),
                            established(2),
                            ipAssigned(3),
                            abnormal(4)
                          }
            MAX-ACCESS read-only
            STATUS current
            DESCRIPTION
                "The status of nap neighbor."
            ::= { hwNapNeighborEntry 3 }
            
        hwNapNeighborAbnormalReason OBJECT-TYPE
            SYNTAX INTEGER 
                           {normal(0),
                            portNotSupport(1),
                            slaveDisable(2),
                            masterIpAssignError(3),
                            slaveIpAssignError(4)
                           } 
            MAX-ACCESS read-only
            STATUS current
            DESCRIPTION
                "The abnormal reason for nap neighbor."
            ::= { hwNapNeighborEntry 4 }
         
        hwNapStatusNotify NOTIFICATION-TYPE
        OBJECTS {hwNapLocalPortName, hwNapNeighborStatus,hwNapNeighborAbnormalReason }
        STATUS current
        DESCRIPTION 
            "If the system configuration is changed in given time,
            a notification will be generated."
        ::= { hwNapNotifications 1 }                     
                             
    END

--
-- HUAWEI-NAP-MIB.mib
--
