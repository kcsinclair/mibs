-- ============================================================================
-- Copyright (C) 2003 by  HUAWEI TECHNOLOGIES. All rights reserved.
--
-- DESCRIPTION:  HUAWEI-IPPOOL-MIB
-- Reference:  
-- Version: V3.00
-- History:
--         v3.01
--         modified by huangjun 2009-12-08
-- ============================================================================
    HUAWEI-IPPOOL-MIB DEFINITIONS ::= BEGIN

        IMPORTS
            huaweiUtility
                FROM HUAWEI-MIB
            IpAddress,Integer32,OBJECT-TYPE, MODULE-IDENTITY,NOTIFICATION-TYPE,
            MODULE-COMPLIANCE,OBJECT-GROUP,NOTIFICATION-GROUP
                FROM SNMPv2-SMI
            DisplayString, RowStatus, TruthValue
                FROM SNMPv2-TC
            Ipv6Address, Ipv6AddressIfIdentifier, Ipv6AddressPrefix
                FROM IPV6-TC;

        hwIPpool MODULE-IDENTITY
            LAST-UPDATED "200408300900Z"
            ORGANIZATION "Fix-Net Dept, Huawei Technologies Co.,Ltd."
            CONTACT-INFO 
                "Floor 5, Block 4, R&D Building,
                Huawei Longgang Production Base,
                Shenzhen,  P.R.C.
                http://www.huawei.com
                ZIP:518057
                "
            DESCRIPTION 
                "The MIB contains objects of module IPPOOL."
            ::= { huaweiUtility 8 }
        hwIPPoolMibObjects OBJECT IDENTIFIER ::= { hwIPpool 1 }

        hwIPPoolTable OBJECT-TYPE
            SYNTAX SEQUENCE OF HwIPPoolEntry
            MAX-ACCESS not-accessible
            STATUS current
            DESCRIPTION
                "The configuration table of IP address pool."
            ::= { hwIPPoolMibObjects 1 }

        hwIPPoolEntry OBJECT-TYPE
            SYNTAX HwIPPoolEntry
            MAX-ACCESS not-accessible
            STATUS current
            DESCRIPTION
                "The configuration list of IP address pool, which is used to configure the relevant attributes of the IP address pool inside the device."
            INDEX { hwIPPoolIndex }
            ::= { hwIPPoolTable 1 }

        HwIPPoolEntry ::=
            SEQUENCE {
                hwIPPoolIndex
                    Integer32,
                hwIPPoolName
                    DisplayString,
                hwIPPoolRouterIPAddr
                    IpAddress,
                hwIPPoolRouterIPMask
                    IpAddress,
                hwIPPoolPriDNSIPAddr
                    IpAddress,
                hwIPPoolSecDNSIPAddr
                    IpAddress,
                hwIPPoolPriNBNSIPAddr
                    IpAddress,
                hwIPPoolSecNBNSIPAddr
                    IpAddress,
                hwIPPoolIPAddrLease
                    Integer32,
                hwIPPoolStatus
                    RowStatus,
                hwIPPoolVPNInstance
                    DisplayString,
                hwIPPoolType
                    INTEGER,
                hwIPPoolNetwork
                    IpAddress,
                hwIPPoolNetworkMask
                    IpAddress,
                hwIPPoolIPTotalNum
                    Integer32,    
                hwIPPoolIPUsedNum
                    Integer32,
                hwIPPoolIPConflictNum
                    Integer32, 
                hwIPPoolIPExcludeNum
                    Integer32, 
                hwIPPoolIPIdleNum
                    Integer32,
                hwIPPoolIPUsedPercent
                    Integer32,
                hwIPPoolDNSIPAddrString
                    OCTET STRING,  
                hwIPPoolDNSIPAddrStringUndo
                    OCTET STRING,
                hwIPPoolNBNSIPAddrString
                    OCTET STRING,
                hwIPPoolNBNSIPAddrStringUndo
                    OCTET STRING,
                hwIPPoolRouterUnnumberedIfName 
                    OCTET STRING,
                hwIPPoolConflictAutoRecycleInterval 
                    Integer32
             }

        hwIPPoolIndex OBJECT-TYPE
            SYNTAX Integer32 (0..4095)
            MAX-ACCESS read-only
            STATUS current
            DESCRIPTION
                "Exclusive index of address pool."
            ::= { hwIPPoolEntry 1 }

        hwIPPoolName OBJECT-TYPE
            SYNTAX DisplayString (SIZE (1..35))
            MAX-ACCESS read-create
            STATUS current
            DESCRIPTION
                "IP address pool name, the service module guarantees the exclusiveness of the name."
            ::= { hwIPPoolEntry 2 }

        hwIPPoolRouterIPAddr OBJECT-TYPE
            SYNTAX IpAddress
            MAX-ACCESS read-create
            STATUS current
            DESCRIPTION
                "Gateway IP address.
                By default, the mask is 255.255.255.255."
            ::= { hwIPPoolEntry 3 }

        hwIPPoolRouterIPMask OBJECT-TYPE
            SYNTAX IpAddress
            MAX-ACCESS read-create
            STATUS current
            DESCRIPTION
                "Gateway mask.
                By default, the mask is 255.255.255.255."
            ::= { hwIPPoolEntry 4 }

        hwIPPoolPriDNSIPAddr OBJECT-TYPE
            SYNTAX IpAddress
            MAX-ACCESS read-create
            STATUS current
            DESCRIPTION
                "Primary DNS IP address.
                By default, it is 255.255.255.255."
            ::= { hwIPPoolEntry 5 }

        hwIPPoolSecDNSIPAddr OBJECT-TYPE
            SYNTAX IpAddress
            MAX-ACCESS read-create
            STATUS current
            DESCRIPTION
                "Second DNS IP address.
                By default, it is 255.255.255.255."
            ::= { hwIPPoolEntry 6 }

        hwIPPoolPriNBNSIPAddr OBJECT-TYPE
            SYNTAX IpAddress
            MAX-ACCESS read-create
            STATUS current
            DESCRIPTION
                "Primary Netbios IP address.
                By default, it is 255.255.255.255."
            ::= { hwIPPoolEntry 7 }

        hwIPPoolSecNBNSIPAddr OBJECT-TYPE
            SYNTAX IpAddress
            MAX-ACCESS read-create
            STATUS current
            DESCRIPTION
                "Second Netbios IP address.
                By default, it is 255.255.255.255."
            ::= { hwIPPoolEntry 8 }

        hwIPPoolIPAddrLease OBJECT-TYPE
            SYNTAX Integer32
            MAX-ACCESS read-create
            STATUS current
            DESCRIPTION
                "IP address lease: 0~(1000*24*60-1)(m)  unit: minute. It is allowed not to specify the lease during the adding. The default value is 3*24*60(m)."
            ::= { hwIPPoolEntry 9 }

        hwIPPoolStatus OBJECT-TYPE
            SYNTAX RowStatus
            MAX-ACCESS read-create
            STATUS current
            DESCRIPTION
                "Row admin status, either Add or Delete.
                Supports adding and deletion."
            ::= { hwIPPoolEntry 10 }

        hwIPPoolVPNInstance OBJECT-TYPE
            SYNTAX DisplayString(SIZE (1..31))
            MAX-ACCESS read-create
            STATUS current
            DESCRIPTION
                "IP VPN-instance name."
            ::= { hwIPPoolEntry 11 }

        hwIPPoolType OBJECT-TYPE
            SYNTAX INTEGER {local(1),relay(2),server(3)}
            MAX-ACCESS read-create
            STATUS current
            DESCRIPTION
                "Value indicates the type of pool, 1--local, 2--relay, 3--server."
            ::= { hwIPPoolEntry 12 }
            
        hwIPPoolNetwork OBJECT-TYPE
            SYNTAX IpAddress
            MAX-ACCESS read-create
            STATUS current
            DESCRIPTION
                "Network ip address of a DHCP Server global pool. 
            To delete a configured network ip, please set
            hwDHCPSGlobalPoolConfigUndoFlag to 1"
            ::= { hwIPPoolEntry 13 }
    
    hwIPPoolNetworkMask OBJECT-TYPE
        SYNTAX IpAddress
        MAX-ACCESS read-create
        STATUS current
        DESCRIPTION
            "Net mask of a DHCP Server global pool(network).
            The SET operation to this object ought to be with
            the SET of hwDHCPSGlobalPoolNetwork together, and
            any SET operation alone to this object will be
            regarded as an invalid operation.
            When a network ip of a DHCP server global pool was 
            deleted, the net mask would also be deleted
            automatically, and no further operation needed"
        ::= { hwIPPoolEntry 14 }   
 
    hwIPPoolIPTotalNum OBJECT-TYPE
            SYNTAX Integer32  
            MAX-ACCESS read-only
            STATUS current
            DESCRIPTION
                "the number of total addresses."
            ::= { hwIPPoolEntry 15 }
            
        hwIPPoolIPUsedNum OBJECT-TYPE
            SYNTAX Integer32
            MAX-ACCESS read-only
            STATUS current
            DESCRIPTION
                "the number of used addresses."
            ::= { hwIPPoolEntry 16 }
            
        hwIPPoolIPConflictNum OBJECT-TYPE
            SYNTAX Integer32
            MAX-ACCESS read-only
            STATUS current
            DESCRIPTION
                "the number of conflict addresses."
            ::= { hwIPPoolEntry 17 }
        
        hwIPPoolIPExcludeNum OBJECT-TYPE
            SYNTAX Integer32
            MAX-ACCESS read-only
            STATUS current
            DESCRIPTION
                "the number of exclude addresses."
            ::= { hwIPPoolEntry 18 }
            
        hwIPPoolIPIdleNum OBJECT-TYPE
            SYNTAX Integer32
            MAX-ACCESS read-only
            STATUS current
            DESCRIPTION
                "the number of idle addresses."
            ::= { hwIPPoolEntry 19 }
            
        hwIPPoolIPUsedPercent OBJECT-TYPE
            SYNTAX Integer32 (0..100)
            MAX-ACCESS read-only
            STATUS current
            DESCRIPTION
                "used percent."
            ::= { hwIPPoolEntry 20 } 
       
        hwIPPoolDNSIPAddrString OBJECT-TYPE
            SYNTAX OCTET STRING (SIZE (0..129))
            MAX-ACCESS read-write
            STATUS current
            DESCRIPTION
                "String of DNS server ip addresses for DHCP clients.
            Since mostly 8 ip addresses can be configured for a pool
            totally, a string is defined to get or configure 8
            ip addresses at a time"
            ::= { hwIPPoolEntry 21 } 

        hwIPPoolDNSIPAddrStringUndo OBJECT-TYPE
            SYNTAX OCTET STRING (SIZE (0..129))
            MAX-ACCESS read-write
            STATUS current
            DESCRIPTION
                "A DNS server ip address to be deleted. This object
            is only for deleting a given ip address of DNS server."
            ::= { hwIPPoolEntry 22 }

        hwIPPoolNBNSIPAddrString OBJECT-TYPE
            SYNTAX OCTET STRING (SIZE (0..129))
            MAX-ACCESS read-write
            STATUS current
            DESCRIPTION
                 "String of NetBIOS server ip addresses for DHCP
            clients. Since mostly 8 ip addresses can be configured for
            a pool totally, so a string is defined to get or
            configure 8 ip addresses at a time"
            ::= {  hwIPPoolEntry 23 }     

        hwIPPoolNBNSIPAddrStringUndo OBJECT-TYPE
            SYNTAX OCTET STRING (SIZE (0..129))
            MAX-ACCESS read-write
            STATUS current
            DESCRIPTION
                "A NetBIOS server ip address to delete. This
            object is only for deleting a given ip address of NetBIOS
            server"
        ::= {  hwIPPoolEntry 24 }
        
        hwIPPoolRouterUnnumberedIfName OBJECT-TYPE
            SYNTAX OCTET STRING (SIZE (1..64))
            MAX-ACCESS read-create
            STATUS current
            DESCRIPTION
                "unnumbered interface name."
            ::= { hwIPPoolEntry 25 }
            
        hwIPPoolConflictAutoRecycleInterval  OBJECT-TYPE
            SYNTAX Integer32 (0 | 30..1440)
            MAX-ACCESS read-create
            STATUS current
            DESCRIPTION
                "The flag indicates whether funtion of conflict auto recycle is enabled."
            ::= { hwIPPoolEntry 26 }
                    

        hwIPSectionTable OBJECT-TYPE
            SYNTAX SEQUENCE OF HwIPSectionEntry
            MAX-ACCESS not-accessible
            STATUS current
            DESCRIPTION
                "The configuration table of IP section."
            ::= { hwIPPoolMibObjects 2 }

        hwIPSectionEntry OBJECT-TYPE
            SYNTAX HwIPSectionEntry
            MAX-ACCESS not-accessible
            STATUS current
            DESCRIPTION
                "IPSection Entry.
                IP section configuration table, used to manage the IP address of user.
                There are at most eight address sections to each address pool. Its indexes are   hwIPPoolIndex (from the external) and HwIPSectionIndex."
            INDEX { hwIPPoolIndex, hwIPSectionIndex }
            ::= { hwIPSectionTable 1 }

        HwIPSectionEntry ::=
            SEQUENCE {
                hwIPSectionIndex
                    Integer32,
                hwIPSectionDesc
                    DisplayString,
                hwIPSectionLowAddr
                    IpAddress,
                hwIPSectionHighAddr
                    IpAddress,
                hwIPSectionLength
                    Integer32,
                hwIPSectionUsedNum
                    Integer32,
                hwIPSectionConflict
                    Integer32,
                hwIPSectionInvalid
                    Integer32,
                hwIPSectionAvailableNum
                    Integer32,
                hwIPSectionRowStatus
                    RowStatus
             }

        hwIPSectionIndex OBJECT-TYPE
            SYNTAX Integer32 (0..7)
            MAX-ACCESS read-only
            STATUS current
            DESCRIPTION
                "Index of address section."
            ::= { hwIPSectionEntry 1 }

        hwIPSectionDesc OBJECT-TYPE
            SYNTAX DisplayString (SIZE (1..32))
            MAX-ACCESS read-create
            STATUS current
            DESCRIPTION
                "IP section DESCRIPTION, which can be empty."
            ::= { hwIPSectionEntry 2 }

        hwIPSectionLowAddr OBJECT-TYPE
            SYNTAX IpAddress
            MAX-ACCESS read-create
            STATUS current
            DESCRIPTION
                "Start of address."
            ::= { hwIPSectionEntry 3 }

        hwIPSectionHighAddr OBJECT-TYPE
            SYNTAX IpAddress
            MAX-ACCESS read-create
            STATUS current
            DESCRIPTION
                "End of address."
            ::= { hwIPSectionEntry 4 }

        hwIPSectionLength OBJECT-TYPE
            SYNTAX Integer32 (0..65536)
            MAX-ACCESS read-only
            STATUS current
            DESCRIPTION
                "IP section's length."
            ::= { hwIPSectionEntry 5 }

        hwIPSectionUsedNum OBJECT-TYPE
            SYNTAX Integer32 (0..65536)
            MAX-ACCESS read-only
            STATUS current
            DESCRIPTION
                "The number of Used addresses."
            ::= { hwIPSectionEntry 6 }

        hwIPSectionConflict OBJECT-TYPE
            SYNTAX Integer32 (0..65536)
            MAX-ACCESS read-only
            STATUS current
            DESCRIPTION
                "The number of conflict addresses."
            ::= { hwIPSectionEntry 7 }

        hwIPSectionInvalid OBJECT-TYPE
            SYNTAX Integer32 (0..65536)
            MAX-ACCESS read-only
            STATUS current
            DESCRIPTION
                "The number of invalid addresses."
            ::= { hwIPSectionEntry 8 }

        hwIPSectionAvailableNum OBJECT-TYPE
            SYNTAX Integer32 (0..65536)
            MAX-ACCESS read-only
            STATUS current
            DESCRIPTION
                "The number of available addresses."
            ::= { hwIPSectionEntry 9 }

        hwIPSectionRowStatus OBJECT-TYPE
            SYNTAX RowStatus
            MAX-ACCESS read-create
            STATUS current
            DESCRIPTION
                "Row admin status, either Add or Delete."
            ::= { hwIPSectionEntry 10 }

        hwIPPoolExtTable OBJECT-TYPE
            SYNTAX SEQUENCE OF HwIPPoolExtEntry
            MAX-ACCESS not-accessible
            STATUS current
            DESCRIPTION
                "Extend table of the local address pool.
                 When IP addresses are allocated by the built-in DHCP servers, you need to configure the lease and option."
            ::= { hwIPPoolMibObjects 3 }
        
        hwIPPoolExtEntry OBJECT-TYPE
            SYNTAX HwIPPoolExtEntry
            MAX-ACCESS not-accessible
            STATUS current
            DESCRIPTION
                "DESCRIPTION."
            INDEX { hwIPPoolIndex }
            ::= { hwIPPoolExtTable 1 }
        
        HwIPPoolExtEntry ::=
            SEQUENCE { 
                hwIPPoolAvailableStatus
                    Integer32,
                hwIPDhcpOptionId1
                    Integer32,
                hwIPDhcpOption1
                    DisplayString,
                hwIPDhcpOptionId2
                    Integer32,
                hwIPDhcpOption2
                    DisplayString,
                hwIPDhcpOptionId3
                    Integer32,
                hwIPDhcpOption3
                    DisplayString,
                hwIPDhcpOptionId4
                    Integer32,
                hwIPDhcpOption4
                    DisplayString,
                hwIPDnsSuffix
                    DisplayString,
                hwIPDhcpSvrIPRsv
                    Integer32,
                hwIPPoolIpAddrRenewal
                    Integer32,
                hwIPPoolIpAddrRebinding
                    Integer32,
                hwIPPoolSIPAddr1
                    IpAddress,
                hwIPPoolSIPAddr2
                    IpAddress,
                hwIPPoolSIPName1
                    DisplayString,
                hwIPPoolSIPName2
                    DisplayString
                 }

        hwIPPoolAvailableStatus OBJECT-TYPE
            SYNTAX Integer32(0..1)
            MAX-ACCESS read-write
            STATUS current
            DESCRIPTION
                "Whether the address is prohibited."
            ::= { hwIPPoolExtEntry 1 }

        hwIPDhcpOptionId1 OBJECT-TYPE
            SYNTAX Integer32 (128..255)
            MAX-ACCESS read-write
            STATUS current
            DESCRIPTION
                "Option ID.
                 When IP addresses are allocated by the built-in DHCP sever, the option is a configuration parameter, which needs to be defined and explained by the carrier."
            ::= { hwIPPoolExtEntry 2 }
        
        hwIPDhcpOption1 OBJECT-TYPE
            SYNTAX DisplayString (SIZE (0..32))
            MAX-ACCESS read-write
            STATUS current
            DESCRIPTION
                "Value of the option."
            ::= { hwIPPoolExtEntry 3 }
        

        hwIPDhcpOptionId2 OBJECT-TYPE
            SYNTAX Integer32 (128..255)
            MAX-ACCESS read-write
            STATUS current
            DESCRIPTION
                "Option ID.
                 When IP addresses are allocated by the built-in DHCP sever, the option is a configuration parameter, which needs to be defined and explained by the carrier."
            ::= { hwIPPoolExtEntry 4 }
        
        hwIPDhcpOption2 OBJECT-TYPE
            SYNTAX DisplayString (SIZE (0..32))
            MAX-ACCESS read-write
            STATUS current
            DESCRIPTION
                "Value of the option."
            ::= { hwIPPoolExtEntry 5 }
            
        hwIPDhcpOptionId3 OBJECT-TYPE
            SYNTAX Integer32 (128..255)
            MAX-ACCESS read-write
            STATUS current
            DESCRIPTION
                "Option ID.
                 When IP addresses are allocated by the built-in DHCP sever, the option is a configuration parameter, which needs to be defined and explained by the carrier."
            ::= { hwIPPoolExtEntry 6 }
        
        hwIPDhcpOption3 OBJECT-TYPE
            SYNTAX DisplayString (SIZE (0..32))
            MAX-ACCESS read-write
            STATUS current
            DESCRIPTION
                "Value of the option."
            ::= { hwIPPoolExtEntry 7 }
            
        hwIPDhcpOptionId4 OBJECT-TYPE
            SYNTAX Integer32 (128..255)
            MAX-ACCESS read-write
            STATUS current
            DESCRIPTION
                "Option ID.
                 When IP addresses are allocated by the built-in DHCP sever, the option is a configuration parameter, which needs to be defined and explained by the carrier."
            ::= { hwIPPoolExtEntry 8 }
        
        hwIPDhcpOption4 OBJECT-TYPE
            SYNTAX DisplayString (SIZE (0..32))
            MAX-ACCESS read-write
            STATUS current
            DESCRIPTION
                "Value of the option."
            ::= { hwIPPoolExtEntry 9 }

        hwIPDnsSuffix OBJECT-TYPE
            SYNTAX DisplayString (SIZE(0..50))
            MAX-ACCESS read-write
            STATUS current
            DESCRIPTION
                "DNS suffix, a string of 0-50 characters.
                If the value is 0, it indicates that the suffix is deleted."
            ::= { hwIPPoolExtEntry 10 }

        hwIPDhcpSvrIPRsv OBJECT-TYPE
            SYNTAX Integer32 (0..255)
            MAX-ACCESS read-write
            STATUS current
            DESCRIPTION
                "mode of IP addresses reserving. 1 indicates leasing management, 2 indicates MAC binding, and other values are invalid.  "
            ::= { hwIPPoolExtEntry 11 }

        hwIPPoolIpAddrRenewal OBJECT-TYPE
            SYNTAX Integer32
            MAX-ACCESS read-create
            STATUS current
            DESCRIPTION
                "ip address renewal: 0~(1000*24*60-1)(m)  unit: minute. It is allowed not to  specify the renewal during the adding. The default value is 2160(m)"
            ::= { hwIPPoolExtEntry 12 }

        hwIPPoolIpAddrRebinding OBJECT-TYPE
            SYNTAX Integer32
            MAX-ACCESS read-create
            STATUS current
            DESCRIPTION
                "ip address rebinding: 0~(1000*24*60-1)(m)  unit: minute. It is allowed not to specify the renewal during the adding. The default value is 3780(m)"
            ::= { hwIPPoolExtEntry 13 }

        hwIPPoolSIPAddr1 OBJECT-TYPE
            SYNTAX IpAddress
            MAX-ACCESS read-create
            STATUS current
            DESCRIPTION
                "SIP Server IP address"
            ::= { hwIPPoolExtEntry 14 }

        hwIPPoolSIPAddr2 OBJECT-TYPE
            SYNTAX IpAddress
            MAX-ACCESS read-create
            STATUS current
            DESCRIPTION
                "SIP Server IP address"
            ::= { hwIPPoolExtEntry 15 }

        hwIPPoolSIPName1 OBJECT-TYPE
            SYNTAX DisplayString (SIZE(0..63))
            MAX-ACCESS read-write
            STATUS current
            DESCRIPTION
                "The name of SIP server. 0 indicates to delete the SIP server. "
            ::= { hwIPPoolExtEntry 16 }

        hwIPPoolSIPName2 OBJECT-TYPE
            SYNTAX DisplayString (SIZE(0..63))
            MAX-ACCESS read-write
            STATUS current
            DESCRIPTION
                "The name of SIP server. 0 indicates to delete the SIP server. "
            ::= { hwIPPoolExtEntry 17 }

        hwIPAddressStatusTable OBJECT-TYPE
            SYNTAX SEQUENCE OF HwIPAddressStatusEntry
            MAX-ACCESS not-accessible
            STATUS current
            DESCRIPTION
                "Address status table.
                 It supports the query and setting of status of the local address pool. 
                 It does not support the query and setting of status of the remote address pool for the following reasons:
                  1. The status of the remote address pool cannot be set.
                  2. The remote and local address pools map different status tables, with different indexes.
                  3. The remote address pool is managed by the remote equipment, rather than the local equipment. The local equipment displays only the approximate status of the remote address pool."
            ::= { hwIPPoolMibObjects 4 }
        
        hwIPAddressStatusEntry OBJECT-TYPE
            SYNTAX HwIPAddressStatusEntry
            MAX-ACCESS not-accessible
            STATUS current
            DESCRIPTION
                "DESCRIPTION."
            INDEX { hwIPPoolIndex, hwIPSectionIndex, hwIPAddress }
            ::= { hwIPAddressStatusTable 1 }
        
        HwIPAddressStatusEntry ::=
            SEQUENCE { 
                hwIPAddress
                    IpAddress,
                hwIPAddressStatus
                    INTEGER ,
                hwPoolName
                    DisplayString
                    }

        hwIPAddress OBJECT-TYPE
            SYNTAX IpAddress
            MAX-ACCESS read-only
            STATUS current
            DESCRIPTION
                "IP address."
            ::= { hwIPAddressStatusEntry 1 }       
    

        hwIPAddressStatus OBJECT-TYPE
            SYNTAX INTEGER
                {
                    idle(0),
                    occupied(1),
                    prohibitive(2),
                    conflictive(3)
                }
            MAX-ACCESS read-write
            STATUS current
            DESCRIPTION
                "Status of the address."
            ::= { hwIPAddressStatusEntry 2 }       
        
        
        hwPoolName OBJECT-TYPE
            SYNTAX DisplayString (SIZE (1..32))
            MAX-ACCESS read-only
            STATUS current
            DESCRIPTION
                "IP address pool name."
            ::= { hwIPAddressStatusEntry 3 }


        hwDhcpSvrGroupTable OBJECT-TYPE
            SYNTAX SEQUENCE OF HwDhcpSvrGroupEntry
            MAX-ACCESS not-accessible
            STATUS current
            DESCRIPTION
                "Configuration table of the DHCP server group.
                 To monitor the status of the remote DHCP server, you need to configure the local DHCP server.
                 You can configure a maximum of 4094 DHCP server groups.
                 Each server group consists of two DHCP servers. Select the server based on the server status."
            ::= { hwIPPoolMibObjects 5 }
        
        hwDhcpSvrGroupEntry OBJECT-TYPE
            SYNTAX HwDhcpSvrGroupEntry
            MAX-ACCESS not-accessible
            STATUS current
            DESCRIPTION
                "DESCRIPTION."
            INDEX { hwIPPoolDhcpSvrGroupIndex }
            ::= { hwDhcpSvrGroupTable 1 }
        
        HwDhcpSvrGroupEntry ::=
            SEQUENCE { 
                hwIPPoolDhcpSvrGroupIndex
                    Integer32,
                hwIPPoolDhcpSvrGroupName
                    DisplayString,
                hwIPDhcpSvrPriAddr
                    IpAddress,
                hwIPDhcpSvrScdiAddr
                    IpAddress,
                hwIPDhcpSvrPriState
                    INTEGER,
                hwIPDhcpScdPriState
                    INTEGER,
                hwIPDhcpSvrAutoRelease
                    TruthValue,
                hwIPDhcpSvrRefCount
                    Integer32,
                hwIPDhcpSvrRowStatus
                    RowStatus,  
                hwIPDhcpSvrPriVpnInstance
                    DisplayString,
                hwIPDhcpSvrScdVpnInstance
                    DisplayString,
                hwIPDhcpSvrSouce
                    OCTET STRING    
             }

        hwIPPoolDhcpSvrGroupIndex OBJECT-TYPE
            SYNTAX Integer32 (0..4095)
            MAX-ACCESS read-only
            STATUS current
            DESCRIPTION
                "Index of a DHCP server group.
                 When you create an address pool, the equipment adds the hwIPPoolDhcpSvrGroupIndex entry by default and sends it to the NMS."
            ::= { hwDhcpSvrGroupEntry 1 }
        
        hwIPPoolDhcpSvrGroupName OBJECT-TYPE
            SYNTAX DisplayString (SIZE (1..32))
            MAX-ACCESS read-create
            STATUS current
            DESCRIPTION
                "Name of the DHCP server group."
            ::= { hwDhcpSvrGroupEntry 2 }
        
        hwIPDhcpSvrPriAddr OBJECT-TYPE
            SYNTAX IpAddress
            MAX-ACCESS read-write
            STATUS current
            DESCRIPTION
                "Primary IP address of the DHCP server group."
            ::= { hwDhcpSvrGroupEntry 3 }
        
        hwIPDhcpSvrScdiAddr OBJECT-TYPE
            SYNTAX IpAddress
            MAX-ACCESS read-write
            STATUS current
            DESCRIPTION
                "Secondary IP address of the DHCP server group."
            ::= { hwDhcpSvrGroupEntry 4 }
        
        hwIPDhcpSvrPriState OBJECT-TYPE  
            SYNTAX INTEGER
                {
                stop(0),
                use(1)
                }
            MAX-ACCESS read-only
            STATUS current
            DESCRIPTION
                "Status of the primary DHCP server."
            ::= { hwDhcpSvrGroupEntry 5 }
        
        hwIPDhcpScdPriState OBJECT-TYPE
            SYNTAX INTEGER
                {
                stop(0),
                use(1)
                }
            MAX-ACCESS read-only
            STATUS current
            DESCRIPTION
                "Status of the secondary DHCP server."
            ::= { hwDhcpSvrGroupEntry 6 }
        
        hwIPDhcpSvrAutoRelease OBJECT-TYPE
            SYNTAX TruthValue
            MAX-ACCESS read-write
            STATUS current
            DESCRIPTION
                "Whether the server supports the Release packet."
            ::= { hwDhcpSvrGroupEntry 7 }
        
        hwIPDhcpSvrRefCount OBJECT-TYPE
            SYNTAX Integer32 (0..4096)
            MAX-ACCESS read-only
            STATUS current
            DESCRIPTION
                "Number of times the server group is referenced."
            ::= { hwDhcpSvrGroupEntry 8 }
        
        hwIPDhcpSvrRowStatus OBJECT-TYPE
            SYNTAX RowStatus
            MAX-ACCESS read-create
            STATUS current
            DESCRIPTION
                "DHCP server row status."
            ::= { hwDhcpSvrGroupEntry 9 }  
            
        hwIPDhcpSvrPriVpnInstance OBJECT-TYPE 
            SYNTAX DisplayString (SIZE (1..31))
            MAX-ACCESS read-create
            STATUS current
            DESCRIPTION
                "VPN instance of the primary DHCP server."
            ::= { hwDhcpSvrGroupEntry 10 }  
         
         hwIPDhcpSvrScdVpnInstance OBJECT-TYPE 
            SYNTAX DisplayString (SIZE (1..31))
            MAX-ACCESS read-create
            STATUS current
            DESCRIPTION
                "VPN instance of the secondary DHCP server."
            ::= { hwDhcpSvrGroupEntry 11 } 

         hwIPDhcpSvrSouce OBJECT-TYPE 
            SYNTAX OCTET STRING (SIZE (1..47))
            MAX-ACCESS read-create
            STATUS current
            DESCRIPTION
                "DHCP source interface address."
            ::= { hwDhcpSvrGroupEntry 12 } 
        
        hwRemotePoolTable OBJECT-TYPE
            SYNTAX SEQUENCE OF HwRemotePoolEntry
            MAX-ACCESS not-accessible
            STATUS current
            DESCRIPTION
                "Configuration table of the remote address pool.
                 The remote address pool must be configured on the local equipment in the following cases:
                   Users obtain IP addresses through the built-in DHCP client and need to renew the addresses.
                   The equipment needs to record the IP addresses to be renewed.
                   The equipment needs to report the routes of the users."
            ::= { hwIPPoolMibObjects 6 }
        
        hwRemotePoolEntry OBJECT-TYPE
            SYNTAX HwRemotePoolEntry
            MAX-ACCESS not-accessible
            STATUS current
            DESCRIPTION
                "DESCRIPTION."
            INDEX { hwRemoteIPPoolIndex }
            ::= { hwRemotePoolTable 1 }
        
        HwRemotePoolEntry ::=
            SEQUENCE { 
                hwRemoteIPPoolIndex
                    Integer32,
                hwRemoteIPPoolName
                    DisplayString,
                hwRemoteIPPoolRouterIPAddr
                    IpAddress,
                hwRemoteIPPoolRouterIPMask
                    IpAddress,
                hwRemoteIPPoolDhcpSvrGroupID
                    Integer32,
                hwRemoteIPPoolAvailableStatus
                    INTEGER,
                hwRemoteIPPoolRowStatus
                    RowStatus,
                hwRemoteIPPoolPriDNSIPAddress
                    IpAddress,
                hwRemoteIPPoolSecDNSIPAddress
                    IpAddress,
                hwRemoteIPPoolPriNBNSIPAddress
                    IpAddress,
                hwRemoteIPPoolSecNBNSIPAddress
                    IpAddress,
                hwRemoteIPPoolVPNInstance
                    DisplayString,
                hwRemoteIPPoolDhcpGroupName
                    DisplayString
             }

        hwRemoteIPPoolIndex OBJECT-TYPE
            SYNTAX Integer32 (0..4095)
            MAX-ACCESS read-only
            STATUS current
            DESCRIPTION
                "Index of an address pool.
                 When you create an address pool, the equipment adds the hwRemoteIPPoolIndex x entry by default and sends it the NMS.
                "
            ::= { hwRemotePoolEntry 1 }
        
        hwRemoteIPPoolName OBJECT-TYPE
            SYNTAX DisplayString (SIZE (1..32))
            MAX-ACCESS read-create
            STATUS current
            DESCRIPTION
                "Name of an address pool.
                 The service module ensures that the name is unique."
            ::= { hwRemotePoolEntry 2 }
        
        hwRemoteIPPoolRouterIPAddr OBJECT-TYPE
            SYNTAX IpAddress
            MAX-ACCESS read-write
            STATUS current
            DESCRIPTION
                "IP address of the gateway."
            ::= { hwRemotePoolEntry 3 }
        
        hwRemoteIPPoolRouterIPMask OBJECT-TYPE
            SYNTAX IpAddress
            MAX-ACCESS read-write
            STATUS current
            DESCRIPTION
                "IP address mask."
            ::= { hwRemotePoolEntry 4 }
        
        hwRemoteIPPoolDhcpSvrGroupID OBJECT-TYPE
            SYNTAX Integer32 (0..4096)
            MAX-ACCESS read-write
            STATUS current
            DESCRIPTION
                "Name of the associated DHCP server group."
            ::= { hwRemotePoolEntry 5 }
        
        hwRemoteIPPoolAvailableStatus OBJECT-TYPE
            SYNTAX INTEGER
                {
                 locked(0),
                 unlocked(1)
                }
            MAX-ACCESS read-write
            STATUS current
            DESCRIPTION
                "Whether the address pool is locked, 0: locked, 1: not locked."
            ::= { hwRemotePoolEntry 6 }

        hwRemoteIPPoolRowStatus OBJECT-TYPE
            SYNTAX RowStatus
            MAX-ACCESS read-create
            STATUS current
            DESCRIPTION
                 "
                 Row status of IP pool.  
                 "
            ::= { hwRemotePoolEntry 7 }
            
        hwRemoteIPPoolPriDNSIPAddress OBJECT-TYPE
            SYNTAX IpAddress
            MAX-ACCESS read-write
            STATUS current
            DESCRIPTION
                "IP address of the active DNS server."
            ::= { hwRemotePoolEntry 8 }

        hwRemoteIPPoolSecDNSIPAddress OBJECT-TYPE
            SYNTAX IpAddress
            MAX-ACCESS read-write
            STATUS current
            DESCRIPTION
                "IP address of the standby DNS server."
            ::= { hwRemotePoolEntry 9 }

        hwRemoteIPPoolPriNBNSIPAddress OBJECT-TYPE
            SYNTAX IpAddress
            MAX-ACCESS read-write
            STATUS current
            DESCRIPTION
                "IP address of the active NBNS server."
            ::= { hwRemotePoolEntry 10 }

        hwRemoteIPPoolSecNBNSIPAddress OBJECT-TYPE
            SYNTAX IpAddress
            MAX-ACCESS read-write
            STATUS current
            DESCRIPTION
                "IP address of the standby NBNS server."
            ::= { hwRemotePoolEntry 11 }

        hwRemoteIPPoolVPNInstance OBJECT-TYPE
            SYNTAX DisplayString (SIZE (1..31))
            MAX-ACCESS read-write
            STATUS current
            DESCRIPTION
                "IP VPN-instance name."
            ::= { hwRemotePoolEntry 12 }
            
        hwRemoteIPPoolDhcpGroupName OBJECT-TYPE
            SYNTAX DisplayString (SIZE (1..32))
            MAX-ACCESS read-only
            STATUS current
            DESCRIPTION
                "DHCP server group name."
            ::= { hwRemotePoolEntry 13 }



--Statistics of address pool usage
        hwIPPoolStatistic OBJECT IDENTIFIER ::= { hwIPPoolMibObjects 7 }
        
        hwIPPoolNum OBJECT-TYPE
            SYNTAX Integer32
            MAX-ACCESS read-only
            STATUS current
            DESCRIPTION
                "Number of configured addresses pools."
            ::= { hwIPPoolStatistic 1 }

        hwIPIdleTotalNum OBJECT-TYPE
            SYNTAX Integer32
            MAX-ACCESS read-only
            STATUS current
            DESCRIPTION
                "Number of idle addresses on the equipment."
            ::= { hwIPPoolStatistic 2 }

        hwIPUsedTotalNum OBJECT-TYPE
            SYNTAX Integer32
            MAX-ACCESS read-only
            STATUS current
            DESCRIPTION
                "Number of addresses in use on the equipment."
            ::= { hwIPPoolStatistic 3 }

        hwIPConflictTotalNum OBJECT-TYPE
            SYNTAX Integer32
            MAX-ACCESS read-only
            STATUS current
            DESCRIPTION
                "Number of conflicting addresses on the equipment."
            ::= { hwIPPoolStatistic 4 }
    
        hwIPExcludeTotalNum OBJECT-TYPE
            SYNTAX Integer32
            MAX-ACCESS read-only
            STATUS current
            DESCRIPTION
                "Number of excluded addresses on the equipment."
            ::= { hwIPPoolStatistic 5 }

        hwIPTotalNum OBJECT-TYPE
            SYNTAX Integer32
            MAX-ACCESS read-only
            STATUS current
            DESCRIPTION
                "The total number of IP address."
            ::= { hwIPPoolStatistic 6 }

        hwIPUsedPercent OBJECT-TYPE
            SYNTAX Integer32
            MAX-ACCESS read-only
            STATUS current
            DESCRIPTION
                "The percent of used IP address."
            ::= { hwIPPoolStatistic 7 }

        hwDhcpServerTable OBJECT-TYPE
            SYNTAX SEQUENCE OF HwDhcpServerEntry
            MAX-ACCESS not-accessible
            STATUS current
            DESCRIPTION
                "DHCP server configuration table."
            ::= { hwIPPoolMibObjects 8 }
        hwDhcpServerEntry OBJECT-TYPE
            SYNTAX HwDhcpServerEntry
            MAX-ACCESS not-accessible
            STATUS current
            DESCRIPTION
                "Description."
            INDEX { hwDhcpServerIndex }
            ::= { hwDhcpServerTable 1 }
        HwDhcpServerEntry ::=
            SEQUENCE { 
                 hwDhcpServerIndex
                     Integer32,
                 hwIPPoolDhcpServerIP
                     IpAddress,
                 hwIPPoolDhcpServerVRFName
                     OCTET STRING,
                 hwIPPoolDhcpServerState
                     INTEGER,
                 hwIPPoolDhcpServerSendDisvSpdNum
                     Integer32,
                 hwIPPoolDhcpServerSendDisvSpdSec
                     Integer32
                     }

        hwDhcpServerIndex OBJECT-TYPE
        SYNTAX Integer32 (0..4095)
            MAX-ACCESS read-only
            STATUS current
            DESCRIPTION
                "The index of DHCP server."
            ::= { hwDhcpServerEntry 1 }
        hwIPPoolDhcpServerIP OBJECT-TYPE
            SYNTAX IpAddress
            MAX-ACCESS read-only
            STATUS current
            DESCRIPTION
                "The IP address of DHCP server."
            ::= { hwDhcpServerEntry 2 }
        hwIPPoolDhcpServerVRFName OBJECT-TYPE 
            SYNTAX OCTET STRING (SIZE (1..31))
            MAX-ACCESS read-only
            STATUS current
            DESCRIPTION
                "The name of VPN instance for the master DHCP server.   "
            ::= { hwDhcpServerEntry 3 }   
        hwIPPoolDhcpServerState OBJECT-TYPE  
            SYNTAX INTEGER
            {
             down(0),
             up(1)
            }
            MAX-ACCESS read-only
            STATUS current
            DESCRIPTION
                "The state of DHCP server."
            ::= { hwDhcpServerEntry 4 }
        hwIPPoolDhcpServerSendDisvSpdNum OBJECT-TYPE
            SYNTAX Integer32 (0..65535)
            MAX-ACCESS read-write
            STATUS current
            DESCRIPTION
                "The send discovering speed number."
            ::= { hwDhcpServerEntry 5 }
        hwIPPoolDhcpServerSendDisvSpdSec OBJECT-TYPE
            SYNTAX Integer32 (0..255)
            MAX-ACCESS read-write
            STATUS current
            DESCRIPTION
                "The interval of discovery packets sent by DHCP server.  "
            ::= { hwDhcpServerEntry 6 }

         hwIPPoolOptionTable OBJECT-TYPE
            SYNTAX SEQUENCE OF HwIPPoolOptionEntry
            MAX-ACCESS not-accessible
            STATUS current
            DESCRIPTION
                "A table for configuring options to DHCP server pools,
               include option code type and value and so on ."
            ::= { hwIPPoolMibObjects 9 }
        
        hwIPPoolOptionEntry OBJECT-TYPE
            SYNTAX HwIPPoolOptionEntry
            MAX-ACCESS not-accessible
            STATUS current
            DESCRIPTION
                "DESCRIPTION."
            INDEX { hwIPPoolIndex,hwIPDhcpOptionId }
            ::= { hwIPPoolOptionTable 1 }
        
        HwIPPoolOptionEntry ::=
            SEQUENCE {  
                    hwIPDhcpOptionId
                        Integer32,
                    hwIPDhcpOption
                        OCTET STRING,
                    hwIPDhcpOptionRowStatus 
                        RowStatus          
                 }
                 
        hwIPDhcpOptionId OBJECT-TYPE
            SYNTAX Integer32 (2..254)
            MAX-ACCESS read-only
            STATUS current
            DESCRIPTION
                "Option ID.
                 When IP addresses are allocated by the built-in DHCP sever, the option is a configuration parameter, which needs to be defined and explained by the carrier."
            ::= { hwIPPoolOptionEntry 1 }           
            
        hwIPDhcpOption OBJECT-TYPE
            SYNTAX OCTET STRING(SIZE (0..64))
            MAX-ACCESS read-write
            STATUS current
            DESCRIPTION
                "Value of the option."
            ::= { hwIPPoolOptionEntry 2 }       

        hwIPDhcpOptionRowStatus OBJECT-TYPE
            SYNTAX RowStatus
            MAX-ACCESS read-create
            STATUS current
            DESCRIPTION
                "This object is used to configuration new rows in this
            table, modify existing rows, and to delete
            existing rows.Only three actions are used: active(1),
            createAndGo(4), destroy(6).
            while configuration new option, you must specify option type 
            and value"
            ::= { hwIPPoolOptionEntry 3 }                            
            
        hwIPPoolGroupTable OBJECT-TYPE
            SYNTAX SEQUENCE OF HwIPPoolGroupEntry
            MAX-ACCESS not-accessible
            STATUS current
            DESCRIPTION
                "Configuration table of the address Pool Group.
                 IP Pool Group support an aggregation of IP Pools. Many Ip Pools of different gateway can be referenced by IP Pool Group.
                 The max number of IP Pools referenced by an Ip Pool Group is 1024 "
            ::= { hwIPPoolMibObjects 10 }
        
        hwIPPoolGroupEntry OBJECT-TYPE
            SYNTAX HwIPPoolGroupEntry
            MAX-ACCESS not-accessible
            STATUS current
            DESCRIPTION
                "The configuration list of IP address pool group, which is used to configure the relevant attributes of the IP address pool group inside the device."
            INDEX { hwIPPoolGroupName }
            ::= { hwIPPoolGroupTable 1 }
        
        HwIPPoolGroupEntry ::=
            SEQUENCE { 
                hwIPPoolGroupName
                    OCTET STRING,
                hwIPPoolGroupVPNInstance
                    OCTET STRING,
                hwIPPoolGroupIncludeUndo
                    TruthValue,
                hwIPPoolGroupRowStatus
                    RowStatus
             }

        hwIPPoolGroupName OBJECT-TYPE
            SYNTAX OCTET STRING (SIZE (1..32))
            MAX-ACCESS read-only
            STATUS current
            DESCRIPTION
                "
                Name of an IP Pool Group.
                "
            ::= { hwIPPoolGroupEntry 1 }
        
        hwIPPoolGroupVPNInstance OBJECT-TYPE
            SYNTAX OCTET STRING (SIZE (1..31))
            MAX-ACCESS read-create
            STATUS current
            DESCRIPTION
                "
                Vpn instance of an address Pool Group.
                Vpn instance of All IP Pools must accord with the vpn instance of IP Pool Group.
                Use string '--' to undo vpn instance in Pool Group.
                "
            ::= { hwIPPoolGroupEntry 2 }
                             
        hwIPPoolGroupIncludeUndo OBJECT-TYPE
            SYNTAX TruthValue
            MAX-ACCESS read-create
            STATUS current
            DESCRIPTION
                "Whether dereference all IP Pools in Pool Group.
                 Only support dereference all IP Pools in this operation. If dereference Pool one by one is needed, please use IPPoolGroupExtTable.
                "
            ::= { hwIPPoolGroupEntry 3 }

        hwIPPoolGroupRowStatus OBJECT-TYPE
            SYNTAX RowStatus
            MAX-ACCESS read-create
            STATUS current
            DESCRIPTION
                 "
                 Row status of IP Pool Group. 
                 Support Active, CreateAndGo and Destroy. 
                 "
            ::= { hwIPPoolGroupEntry 4 }
            
            
        hwIPPoolGroupExtTable OBJECT-TYPE
            SYNTAX SEQUENCE OF HwIPPoolGroupExtEntry
            MAX-ACCESS not-accessible
            STATUS current
            DESCRIPTION
                "Configuration extension table of the address pool group.
                 The extension table can set the order of an IP pool in IP Pool Group.
                 The extension table can be used to dereference an IP pool in IP pool Group.
                 "
            ::= { hwIPPoolMibObjects 11 }
        
        hwIPPoolGroupExtEntry OBJECT-TYPE
            SYNTAX HwIPPoolGroupExtEntry
            MAX-ACCESS not-accessible
            STATUS current
            DESCRIPTION
                "The configuration list of IP address pool group extension table."
            INDEX { hwIPPoolGroupName,hwIPPoolGroupExtIncludePoolName }
            ::= { hwIPPoolGroupExtTable 1 }
        
        HwIPPoolGroupExtEntry ::=
            SEQUENCE { 
                hwIPPoolGroupExtIncludePoolName
                    OCTET STRING,
                hwIPPoolGroupExtIncludePoolMoveOrder
                    Integer32,
                hwIPPoolGroupExtRowStatus
                    RowStatus
             }

        hwIPPoolGroupExtIncludePoolName OBJECT-TYPE
            SYNTAX OCTET STRING (SIZE (1..32))
            MAX-ACCESS read-only
            STATUS current
            DESCRIPTION
                "
                The IP Pool referenced in IP Pool Group.
                "
            ::= { hwIPPoolGroupExtEntry 1 }
        
        hwIPPoolGroupExtIncludePoolMoveOrder OBJECT-TYPE
            SYNTAX Integer32 (1..1024)
            MAX-ACCESS read-create
            STATUS current
            DESCRIPTION
                "The order of IP Pool in IP Pool Group.
                 Specify the move order to adjust the order of the IP Pool in IP Pool Group.
                 Only supoort set operation."
            ::= { hwIPPoolGroupExtEntry 2 }
                             
        hwIPPoolGroupExtRowStatus OBJECT-TYPE
            SYNTAX RowStatus
            MAX-ACCESS read-create
            STATUS current
            DESCRIPTION
                 "
                 Row status of IP pool group extension. 
                 Support CreateAndGo and Destroy. 
                 "
            ::= { hwIPPoolGroupExtEntry 3 }
            
            
        hwIPPoolGroupDisplayTable OBJECT-TYPE
            SYNTAX SEQUENCE OF HwIPPoolGroupDisplayEntry
            MAX-ACCESS not-accessible
            STATUS current
            DESCRIPTION
                "
                Display table of the address pool group.
                "
            ::= { hwIPPoolMibObjects 12 }
        
        hwIPPoolGroupDisplayEntry OBJECT-TYPE
            SYNTAX HwIPPoolGroupDisplayEntry
            MAX-ACCESS not-accessible
            STATUS current
            DESCRIPTION
                "The configuration list of IP address pool display group table."
            INDEX { hwIPPoolGroupName }
            ::= { hwIPPoolGroupDisplayTable 1 }
        
        HwIPPoolGroupDisplayEntry ::=
            SEQUENCE { 
                hwIPPoolGroupIncludePoolNum
                    Integer32,
                hwIPPoolGroupBoundByDomainNum
                    Integer32,
                hwIPPoolGroupIPTotalNum
                    Integer32,
                hwIPPoolGroupIPUsedNum
                    Integer32,
                hwIPPoolGroupIPConflictedNum
                    Integer32,
                hwIPPoolGroupIPDisableNum
                    Integer32,
                hwIPPoolGroupIPDesignatedNum
                    Integer32,
                hwIPPoolGroupIPFreeNum
                    Integer32,
                hwIPPoolGroupIPUsedPercent
                    Integer32
             }

        hwIPPoolGroupIncludePoolNum OBJECT-TYPE
            SYNTAX Integer32 (0..1024)
            MAX-ACCESS read-only
            STATUS current
            DESCRIPTION
                "
                The number of IP Pools referenced in IP Pool Group.
                "
            ::= { hwIPPoolGroupDisplayEntry 1 }
        
        hwIPPoolGroupBoundByDomainNum OBJECT-TYPE
            SYNTAX Integer32 (0..1024)
            MAX-ACCESS read-only
            STATUS current
            DESCRIPTION
                "
                The number of IP Pool Groups referenced in domains.
                "
            ::= { hwIPPoolGroupDisplayEntry 2 }
            
        hwIPPoolGroupIPTotalNum OBJECT-TYPE
            SYNTAX Integer32 (0..1024)
            MAX-ACCESS read-only
            STATUS current
            DESCRIPTION
                "
                The Total number of IP in IP Pool Group.
                "
            ::= { hwIPPoolGroupDisplayEntry 3 }
            
        hwIPPoolGroupIPUsedNum OBJECT-TYPE
            SYNTAX Integer32 (0..1024)
            MAX-ACCESS read-only
            STATUS current
            DESCRIPTION
                "
                The Used number of IP in IP Pool Group.
                "
            ::= { hwIPPoolGroupDisplayEntry 4 }
            
        hwIPPoolGroupIPConflictedNum OBJECT-TYPE
            SYNTAX Integer32 (0..1024)
            MAX-ACCESS read-only
            STATUS current
            DESCRIPTION
                "
                The Conflicted number of IP in IP Pool Group.
                "
            ::= { hwIPPoolGroupDisplayEntry 5 }
            
        hwIPPoolGroupIPDisableNum OBJECT-TYPE
            SYNTAX Integer32 (0..1024)
            MAX-ACCESS read-only
            STATUS current
            DESCRIPTION
                "
                The Disable number of IP in IP Pool Group.
                "
            ::= { hwIPPoolGroupDisplayEntry 6 }
            
        hwIPPoolGroupIPDesignatedNum OBJECT-TYPE
            SYNTAX Integer32 (0..1024)
            MAX-ACCESS read-only
            STATUS current
            DESCRIPTION
                "
                The Designated number of IP in IP Pool Group.
                "
            ::= { hwIPPoolGroupDisplayEntry 7 }
            
        hwIPPoolGroupIPFreeNum OBJECT-TYPE
            SYNTAX Integer32 (0..1024)
            MAX-ACCESS read-only
            STATUS current
            DESCRIPTION
                "
                The Free number of IP in IP Pool Group.
                "
            ::= { hwIPPoolGroupDisplayEntry 8 }
            
        hwIPPoolGroupIPUsedPercent OBJECT-TYPE
            SYNTAX Integer32 (0..1024)
            MAX-ACCESS read-only
            STATUS current
            DESCRIPTION
                "
                The Used Percent of IP in IP Pool Group.
                "
            ::= { hwIPPoolGroupDisplayEntry 9 }
    
            --end
 --begin:added by w00175317 for option119
        hwIPPoolDomainSearchListTable OBJECT-TYPE
            SYNTAX SEQUENCE OF HwIPPoolDomainSearchListEntry
            MAX-ACCESS not-accessible
            STATUS current
            DESCRIPTION
                "
                Set the domain search list which is uesed to fill content of DHCP packet option 119.
                The option is passed from the DHCP Server to the DHCP Client to specify the domain 
                search list used when resolving hostnames using DNS.
                "
            ::= { hwIPPoolMibObjects 13 }

    hwIPv6PrefixTable OBJECT-TYPE
            SYNTAX SEQUENCE OF HwIPv6PrefixEntry
            MAX-ACCESS not-accessible
            STATUS current
            DESCRIPTION
                "
                The configuration table of IPv6 prefix pool.
                "
            ::= { hwIPPoolMibObjects 16 }

    hwIPv6PoolTable OBJECT-TYPE
            SYNTAX SEQUENCE OF HwIPv6PoolEntry
            MAX-ACCESS not-accessible
            STATUS current
            DESCRIPTION
                "
                The configuration table of IPv6 address pool.
                "
            ::= { hwIPPoolMibObjects 17 }

    hwIPv6PoolStatusTable OBJECT-TYPE
            SYNTAX SEQUENCE OF HwIPv6PoolStatusEntry
            MAX-ACCESS not-accessible
            STATUS current
            DESCRIPTION
                "
                The configuration table of IPv6 address pool's usage.
                "
            ::= { hwIPPoolMibObjects 18 }

    hwIPv6DuidBindPrefixTable OBJECT-TYPE
            SYNTAX SEQUENCE OF HwIPv6DuidBindPrefixEntry
            MAX-ACCESS not-accessible
            STATUS current
            DESCRIPTION
                "
                The binding of client DUID and prefix.
                "
            ::= { hwIPPoolMibObjects 19 }

    hwDhcpv6SvrGroupTable OBJECT-TYPE
            SYNTAX SEQUENCE OF HwDhcpv6SvrGroupEntry
            MAX-ACCESS not-accessible
            STATUS current
            DESCRIPTION
                "
                The configuration table of the DHCPv6 server group.
                "
            ::= { hwIPPoolMibObjects 20 }

    hwIPv6RemotePoolTable OBJECT-TYPE
            SYNTAX SEQUENCE OF HwIPv6RemotePoolEntry
            MAX-ACCESS not-accessible
            STATUS current
            DESCRIPTION
                "
                The configuration table of IPv6 remote address pool.
                "
            ::= { hwIPPoolMibObjects 21 }

        hwIPPoolDomainSearchListEntry OBJECT-TYPE
            SYNTAX HwIPPoolDomainSearchListEntry
            MAX-ACCESS not-accessible
            STATUS current
            DESCRIPTION
                "The configuration list of IP address pool DomainSearchList table."
            INDEX { hwIPPoolIndex, hwIPPoolDomainSearchList }
            ::= { hwIPPoolDomainSearchListTable 1 }
        
        
        HwIPPoolDomainSearchListEntry ::=
            SEQUENCE { 
                hwIPPoolDomainSearchList
                    OCTET STRING,
                hwIPPoolDomainSearchListRowStatus
                    RowStatus
             }

        hwIPPoolDomainSearchList OBJECT-TYPE
            SYNTAX OCTET STRING (SIZE (1..32))
            MAX-ACCESS read-only
            STATUS current
            DESCRIPTION
                "
                The domain search list which is used to fill content of DHCP packet option 119.
                "
            ::= { hwIPPoolDomainSearchListEntry 1 }
        
        hwIPPoolDomainSearchListRowStatus OBJECT-TYPE
            SYNTAX RowStatus
            MAX-ACCESS read-create
            STATUS current
            DESCRIPTION
                "
                Row status of IP pool DomainSearchList. 
                Support CreateAndGo and Destroy.
                "
            ::= { hwIPPoolDomainSearchListEntry 2 }

 --end:added by w00175317 for option119
 --begin:added by t00189639 for amv6
 hwIPv6PrefixEntry OBJECT-TYPE
            SYNTAX HwIPv6PrefixEntry
            MAX-ACCESS not-accessible
            STATUS current
            DESCRIPTION
                "The configuration list of IPv6 prefix pool."
            INDEX { hwIPv6PrefixIndex }
            ::= { hwIPv6PrefixTable 1 }

        hwIPv6PoolEntry OBJECT-TYPE
            SYNTAX HwIPv6PoolEntry
            MAX-ACCESS not-accessible
            STATUS current
            DESCRIPTION
                "The configuration list of IPv6 address pool."
            INDEX { hwIPv6PoolIndex }
            ::= { hwIPv6PoolTable 1 }

        hwIPv6PoolStatusEntry OBJECT-TYPE
            SYNTAX HwIPv6PoolStatusEntry
            MAX-ACCESS not-accessible
            STATUS current
            DESCRIPTION
                "The configuration list of IPv6 address pool's usage."
            INDEX { hwIPv6PoolIndex }
            ::= { hwIPv6PoolStatusTable 1 }

        hwIPv6DuidBindPrefixEntry OBJECT-TYPE
            SYNTAX HwIPv6DuidBindPrefixEntry
            MAX-ACCESS not-accessible
            STATUS current
            DESCRIPTION
                "The binding of client's DUID and prefix."
            INDEX { hwIPv6PrefixIndex, hwIPv6ClientDuid }
            ::= { hwIPv6DuidBindPrefixTable 1 }

        hwDhcpv6SvrGroupEntry OBJECT-TYPE
            SYNTAX HwDhcpv6SvrGroupEntry
            MAX-ACCESS not-accessible
            STATUS current
            DESCRIPTION
                "The configuration list of DHCPv6 server group."
            INDEX { hwDhcpv6SvrGroupIndex }
            ::= { hwDhcpv6SvrGroupTable 1 }

        hwIPv6RemotePoolEntry OBJECT-TYPE
            SYNTAX HwIPv6RemotePoolEntry
            MAX-ACCESS not-accessible
            STATUS current
            DESCRIPTION
                "The configuration list of IPv6 remote address pool."
            INDEX { hwIPv6RemotePoolIndex }
            ::= { hwIPv6RemotePoolTable 1 }

        HwIPPoolDomainSearchListEntry ::=
            SEQUENCE { 
                hwIPPoolDomainSearchList
                    OCTET STRING,
                hwIPPoolDomainSearchListRowStatus
                    RowStatus
             }

        HwIPv6PrefixEntry ::=
            SEQUENCE { 
                hwIPv6PrefixIndex
                    Integer32,
                hwIPv6PrefixName
                    OCTET STRING,
                hwIPv6PrefixType
                    INTEGER,
                hwIPv6Prefix
                    Ipv6AddressPrefix,
                hwIPv6PrefixLen
                    Integer32,
                hwIPv6PrefixDelegatingLen
                    Integer32,
                hwIPv6PrefixAdvPreferredLifetime
                    Integer32,
                hwIPv6PrefixAdvValidLifetime
                    Integer32,
                hwIPv6PrefixAvailableStatus
                    TruthValue,
                hwIPv6VPNInstance
                    OCTET STRING,
                hwIPv6PrefixReservedFlag
                    INTEGER,
                hwIPv6LinkAddress
                    Ipv6Address,
                hwIPv6SlaacUnsharedFlag
                    TruthValue,
                hwIPv6PrefixRowStatus
                    RowStatus
             }

        hwIPv6PrefixIndex OBJECT-TYPE
            SYNTAX Integer32 (0..1023)
            MAX-ACCESS read-only
            STATUS current
            DESCRIPTION
                "The index of IPv6 prefix pool."
            ::= { hwIPv6PrefixEntry 1 }

        hwIPv6PrefixName OBJECT-TYPE
            SYNTAX OCTET STRING (SIZE (1..32))
            MAX-ACCESS read-create
            STATUS current
            DESCRIPTION
                "The name of IPv6 prefix pool"
            ::= { hwIPv6PrefixEntry 2 }

        hwIPv6PrefixType OBJECT-TYPE
            SYNTAX INTEGER {local(1),delegation(2),remote(3)}
            MAX-ACCESS read-create
            STATUS current
            DESCRIPTION
                "The type of IPv6 prefix pool."
            ::= { hwIPv6PrefixEntry 3 }

        hwIPv6Prefix OBJECT-TYPE
            SYNTAX Ipv6AddressPrefix
            MAX-ACCESS read-create
            STATUS current
            DESCRIPTION
                "The prefix of IPv6 prefix pool. This node is valid only for local and delegation prefix pool."
            ::= { hwIPv6PrefixEntry 4 }

        hwIPv6PrefixLen OBJECT-TYPE
            SYNTAX Integer32 (0..128)
            MAX-ACCESS read-create
            STATUS current
            DESCRIPTION
                "The prefix length of IPv6 prefix pool. Note that 0 is not a configurable value."
            ::= { hwIPv6PrefixEntry 5 }

        hwIPv6PrefixDelegatingLen OBJECT-TYPE
            SYNTAX Integer32 (0..128)
            MAX-ACCESS read-create
            STATUS current
            DESCRIPTION
                "The delegating prefix length of IPv6 prefix pool. Note that 0 is not a configurable value. This node is valid only for local and delegation prefix pool."
            ::= { hwIPv6PrefixEntry 6 }

        hwIPv6PrefixAdvPreferredLifetime OBJECT-TYPE
            SYNTAX Integer32
            MAX-ACCESS read-create
            STATUS current
            DESCRIPTION
                "The preferred lifetime(seconds) of IPv6 prefix pool."
            ::= { hwIPv6PrefixEntry 7 }

        hwIPv6PrefixAdvValidLifetime OBJECT-TYPE
            SYNTAX Integer32
            MAX-ACCESS read-create
            STATUS current
            DESCRIPTION
                "The valid lifetime(seconds) of the IPv6 prefix."
            ::= { hwIPv6PrefixEntry 8 }

        hwIPv6PrefixAvailableStatus OBJECT-TYPE
            SYNTAX TruthValue
            MAX-ACCESS read-create
            STATUS current
            DESCRIPTION
                "The flag indicating whether the IPv6 prefix pool is locked."
            ::= { hwIPv6PrefixEntry 9 }

        hwIPv6VPNInstance OBJECT-TYPE
            SYNTAX OCTET STRING (SIZE (1..31))
            MAX-ACCESS read-create
            STATUS current
            DESCRIPTION
                "The vpn instance name of the IPv6 prefix pool."
            ::= { hwIPv6PrefixEntry 10 }

        hwIPv6PrefixReservedFlag OBJECT-TYPE
            SYNTAX INTEGER { noneReserved(0), macReserved(1), macPlusLeaseReserved(2), duidReserved(3), duidPlusLeaseReserved(4)}
            MAX-ACCESS read-create
            STATUS current
            DESCRIPTION
                "The reserved flag of the IPv6 prefix pool. 0-none reserved, 1-mac reserved, 2-mac plus lease reserved, 3-duid reserved, 4-duid plus lease reserved."
            ::= { hwIPv6PrefixEntry 11 }

        hwIPv6LinkAddress OBJECT-TYPE
            SYNTAX Ipv6Address
            MAX-ACCESS read-create
            STATUS current
            DESCRIPTION
                "The link address of the IPv6 remote prefix pool. This node is valid only for remote prefix pool."
            ::= { hwIPv6PrefixEntry 12 }

        hwIPv6SlaacUnsharedFlag OBJECT-TYPE
            SYNTAX TruthValue
            MAX-ACCESS read-create
            STATUS current
            DESCRIPTION
                "The flag indicates whether prefix pool is used in unshared-mode. The node is valid only for delegation prefix pool."
            ::= { hwIPv6PrefixEntry 13 }

        hwIPv6PrefixRowStatus OBJECT-TYPE
            SYNTAX RowStatus 
            MAX-ACCESS read-create
            STATUS current
            DESCRIPTION
                "Row admin status. Support adding, modification and deletion."
            ::= { hwIPv6PrefixEntry 14 }

        HwIPv6PoolEntry ::=
            SEQUENCE {
                hwIPv6PoolIndex
                    Integer32,
                hwIPv6PoolName
                    OCTET STRING,
                hwIPv6PoolType
                    INTEGER,
                hwIPv6PoolPrefixName
                    OCTET STRING,
                hwIPv6PoolDnsIPAddr
                    OCTET STRING,
                hwIPv6PoolDnsSearchList
                    OCTET STRING,
                hwIPv6PoolPreference
                    Integer32,
                hwIPv6PoolAvailableStatus
                    TruthValue,
                hwIPv6PoolRenewPercent
                    Integer32,
                hwIPv6PoolRebindingPercent
                    Integer32,
                hwIPv6PoolRapidCommitFlag
                    TruthValue,
                hwIPv6PoolUnicastOption
                    TruthValue,
                hwIPv6PoolAFTRName
                    OCTET STRING,
                hwIPv6PoolRowStatus
                    RowStatus
             }

        HwIPv6PoolStatusEntry ::=
            SEQUENCE {
                hwIPv6FreeAddressNum
                    Integer32,
                hwIPv6UsedAddressNum
                    Integer32,
                hwIPv6FreePrefixNum
                    Integer32,
                hwIPv6UsedPrefixNum
                    Integer32,
                hwIPv6AddressTotalNum
                    Integer32,
                hwIPv6AddressUsedNum
                    Integer32,
                hwIPv6AddressFreeNum
                    Integer32,
                hwIPv6AddressConflictNum
                    Integer32,
                hwIPv6AddressExcludeNum
                    Integer32,
                hwIPv6AddressUsedPercent
                    Integer32,
                hwIPv6NDRAPrefixTotalNum
                    Integer32,
                hwIPv6NDRAPrefixUsedNum
                    Integer32,
                hwIPv6NDRAPrefixFreeNum
                    Integer32,
                hwIPv6NDRAPrefixConflictNum
                    Integer32,
                hwIPv6NDRAPrefixExcludeNum
                    Integer32,
                hwIPv6NDRAPrefixUsedPercent
                    Integer32,
                hwIPv6PDPrefixTotalNum
                    Integer32,
                hwIPv6PDPrefixUsedNum
                    Integer32,
                hwIPv6PDPrefixFreeNum
                    Integer32,
                hwIPv6PDPrefixConflictNum
                    Integer32,
                hwIPv6PDPrefixExcludeNum
                    Integer32,
                hwIPv6PDPrefixUsedPercent
                    Integer32
             }

        HwIPv6DuidBindPrefixEntry ::=
            SEQUENCE {
                hwIPv6ClientDuid
                    OCTET STRING,
                hwIPv6BindPrefix
                    Ipv6AddressPrefix,
                hwIPv6DuidBindPrefixRowStatus
                    RowStatus
             }

        HwDhcpv6SvrGroupEntry ::=
            SEQUENCE {
                hwDhcpv6SvrGroupIndex
                    Integer32,
                hwDhcpv6SvrGroupName
                    OCTET STRING,
                hwIPDhcpv6SvrAddr1
                    Ipv6Address,
                hwIPDhcpv6SvrAddr2
                    Ipv6Address,
                hwIPDhcpv6PriSvrState
                    INTEGER,
                hwIPDhcpv6ScdSvrState
                    INTEGER,
                hwIPDhcpv6SvrAutoRelease
                    TruthValue,
                hwIPDhcpv6SvrGroupRefCount
                    Integer32,
                hwDhcpv6SvrInterface1
                    DisplayString,
                hwDhcpv6SvrInterface2
                    DisplayString,
                hwDhcpv6SvrAlgorithm
                    INTEGER,
                hwDhcpv6SvrWeight1
                    Integer32,
                hwDhcpv6SvrWeight2
                    Integer32,
                hwIPDhcpv6Svr1VrfName
                    OCTET STRING,
                hwIPDhcpv6Svr2VrfName
                    OCTET STRING,
                hwDhcpv6SvrGroupRowStatus
                    RowStatus
             }

        HwIPv6RemotePoolEntry ::=
            SEQUENCE {
                hwIPv6RemotePoolIndex
                    Integer32,
                hwIPv6RemotePoolName
                    OCTET STRING,
                hwIPv6RemotePoolPrefixName
                    OCTET STRING,
                hwIPv6RemotePoolDhcpv6SvrGroupName
                    OCTET STRING,
                hwIPv6RemotePoolAvailableStatus
                    TruthValue,
                hwIPv6RemotePoolExportHostRouteFlag
                    TruthValue,
                hwIPv6RemotePoolRowStatus
                    RowStatus
             }
             
                hwIPv6PoolIndex OBJECT-TYPE
            SYNTAX Integer32 (0..1023)
            MAX-ACCESS read-only
            STATUS current
            DESCRIPTION
                "The index of IPv6 addres pool."
            ::= { hwIPv6PoolEntry 1 }

        hwIPv6PoolName OBJECT-TYPE
            SYNTAX OCTET STRING (SIZE (1..32))
            MAX-ACCESS read-create
            STATUS current
            DESCRIPTION
                "The name of IPv6 addres pool."
            ::= { hwIPv6PoolEntry 2 }

        hwIPv6PoolType OBJECT-TYPE
            SYNTAX INTEGER {local(1),delegation(2),relay(3)}
            MAX-ACCESS read-create
            STATUS current
            DESCRIPTION
                "The type of IPv6 addres pool."
            ::= { hwIPv6PoolEntry 3 }

        hwIPv6PoolPrefixName OBJECT-TYPE
            SYNTAX OCTET STRING (SIZE (1..32))
            MAX-ACCESS read-create
            STATUS current
            DESCRIPTION
                "The prefix pool name of IPv6 addres pool."
            ::= { hwIPv6PoolEntry 4 }

        hwIPv6PoolDnsIPAddr OBJECT-TYPE
            SYNTAX OCTET STRING (SIZE (1..81))
            MAX-ACCESS read-create
            STATUS current
            DESCRIPTION
                "The DNS of IPv6 addres pool. The format to set value is : operator+space+primary DNS+space+secondary DNS. operator: 1-Add, 2-Delete."
            ::= { hwIPv6PoolEntry 5 }

        hwIPv6PoolDnsSearchList OBJECT-TYPE
            SYNTAX OCTET STRING (SIZE (1..32))
            MAX-ACCESS read-create
            STATUS current
            DESCRIPTION
                "The DNS search list of IPv6 addres pool."
            ::= { hwIPv6PoolEntry 6 }

        hwIPv6PoolPreference OBJECT-TYPE
            SYNTAX Integer32 (0..255)
            MAX-ACCESS read-create
            STATUS current
            DESCRIPTION
                "The preference of IPv6 addres pool."
            ::= { hwIPv6PoolEntry 7 }

        hwIPv6PoolAvailableStatus OBJECT-TYPE
            SYNTAX TruthValue
            MAX-ACCESS read-create
            STATUS current
            DESCRIPTION
                "The flag indicating whether IPv6 address pool is locked."
            ::= { hwIPv6PoolEntry 8 }

        hwIPv6PoolRenewPercent OBJECT-TYPE
            SYNTAX Integer32 (10..99)
            MAX-ACCESS read-create
            STATUS current
            DESCRIPTION
                "The renew time percent of IPv6 addres pool. When hwIPv6PoolRenewPercent is specified, you need also specify hwIPv6PoolRebindingPercent."
            ::= { hwIPv6PoolEntry 9 }

        hwIPv6PoolRebindingPercent OBJECT-TYPE
            SYNTAX Integer32 (10..99)
            MAX-ACCESS read-create
            STATUS current
            DESCRIPTION
                "The rebinding time percent of IPv6 addres pool. When hwIPv6PoolRebindingPercent is specified, you need also specify hwIPv6PoolRenewPercent."
            ::= { hwIPv6PoolEntry 10 }

        hwIPv6PoolRapidCommitFlag OBJECT-TYPE
            SYNTAX TruthValue
            MAX-ACCESS read-create
            STATUS current
            DESCRIPTION
                "The flag indicating whether DHCPv6 rapid-commit is enabled."
            ::= { hwIPv6PoolEntry 11 }

        hwIPv6PoolUnicastOption OBJECT-TYPE
            SYNTAX TruthValue
            MAX-ACCESS read-create
            STATUS current
            DESCRIPTION
                "The flag indicating whether DHCPv6 server unicast option is enabled."
            ::= { hwIPv6PoolEntry 12 }

        hwIPv6PoolAFTRName OBJECT-TYPE
            SYNTAX OCTET STRING (SIZE (1..63))
            MAX-ACCESS read-create
            STATUS current
            DESCRIPTION
                "Configure the name of Address Family Transition Router."
            ::= { hwIPv6PoolEntry 13 }

        hwIPv6PoolRowStatus OBJECT-TYPE
            SYNTAX RowStatus 
            MAX-ACCESS read-create
            STATUS current
            DESCRIPTION
                "Row admin status. Support adding, modification and deletion."
            ::= { hwIPv6PoolEntry 14 }

        hwIPv6FreeAddressNum OBJECT-TYPE
            SYNTAX Integer32
            MAX-ACCESS read-only
            STATUS current
            DESCRIPTION
                "The free address number of IPv6 addres pool."
            ::= { hwIPv6PoolStatusEntry 1 }

        hwIPv6UsedAddressNum OBJECT-TYPE
            SYNTAX Integer32
            MAX-ACCESS read-only
            STATUS current
            DESCRIPTION
                "The used address number of IPv6 addres pool."
            ::= { hwIPv6PoolStatusEntry 2 }

        hwIPv6FreePrefixNum OBJECT-TYPE
            SYNTAX Integer32
            MAX-ACCESS read-only
            STATUS current
            DESCRIPTION
                "The free prefix number of IPv6 addres pool."
            ::= { hwIPv6PoolStatusEntry 3 }

        hwIPv6UsedPrefixNum OBJECT-TYPE
            SYNTAX Integer32
            MAX-ACCESS read-only
            STATUS current
            DESCRIPTION
                "The used prefix number of IPv6 addres pool."
            ::= { hwIPv6PoolStatusEntry 4 }

        hwIPv6AddressTotalNum OBJECT-TYPE
            SYNTAX Integer32
            MAX-ACCESS read-only
            STATUS current
            DESCRIPTION
                "The total IPv6 address number of IPv6 address pool."
            ::= { hwIPv6PoolStatusEntry 5 }

        hwIPv6AddressUsedNum OBJECT-TYPE
            SYNTAX Integer32
            MAX-ACCESS read-only
            STATUS current
            DESCRIPTION
                "The used IPv6 address number of IPv6 address pool."
            ::= { hwIPv6PoolStatusEntry 6 }
            
        hwIPv6AddressFreeNum OBJECT-TYPE
            SYNTAX Integer32
            MAX-ACCESS read-only
            STATUS current
            DESCRIPTION
                "The free IPv6 address number of IPv6 address pool."
            ::= { hwIPv6PoolStatusEntry 7 }
            
        hwIPv6AddressConflictNum OBJECT-TYPE
            SYNTAX Integer32
            MAX-ACCESS read-only
            STATUS current
            DESCRIPTION
                "The conflict IPv6 address number of IPv6 address pool."
            ::= { hwIPv6PoolStatusEntry 8 }

        hwIPv6AddressExcludeNum OBJECT-TYPE
            SYNTAX Integer32
            MAX-ACCESS read-only
            STATUS current
            DESCRIPTION
                "The excluded IPv6 address number of IPv6 address pool."
            ::= { hwIPv6PoolStatusEntry 9 }  
            
        hwIPv6AddressUsedPercent OBJECT-TYPE
            SYNTAX Integer32
            MAX-ACCESS read-only
            STATUS current
            DESCRIPTION
                "The percent of used IPv6 addressof IPv6 address pool."
            ::= { hwIPv6PoolStatusEntry 10 }  
            
        hwIPv6NDRAPrefixTotalNum OBJECT-TYPE
            SYNTAX Integer32
            MAX-ACCESS read-only
            STATUS current
            DESCRIPTION
                "The total NDRA prefix number of IPv6 address pool."
            ::= { hwIPv6PoolStatusEntry 11 } 
            
        hwIPv6NDRAPrefixUsedNum OBJECT-TYPE
            SYNTAX Integer32
            MAX-ACCESS read-only
            STATUS current
            DESCRIPTION
                "The used NDRA prefix number of IPv6 address pool."
            ::= { hwIPv6PoolStatusEntry 12 } 
            
        hwIPv6NDRAPrefixFreeNum OBJECT-TYPE
            SYNTAX Integer32
            MAX-ACCESS read-only
            STATUS current
            DESCRIPTION
                "The free NDRA prefix number of IPv6 address pool."
            ::= { hwIPv6PoolStatusEntry 13 }  
            
        hwIPv6NDRAPrefixConflictNum OBJECT-TYPE
            SYNTAX Integer32
            MAX-ACCESS read-only
            STATUS current
            DESCRIPTION
                "The conflict NDRA prefix number of IPv6 address pool."
            ::= { hwIPv6PoolStatusEntry 14 }                      
            
        hwIPv6NDRAPrefixExcludeNum OBJECT-TYPE
            SYNTAX Integer32
            MAX-ACCESS read-only
            STATUS current
            DESCRIPTION
                "The excluded NDRA prefix number of IPv6 address pool."
            ::= { hwIPv6PoolStatusEntry 15 }
            
        hwIPv6NDRAPrefixUsedPercent OBJECT-TYPE
            SYNTAX Integer32
            MAX-ACCESS read-only
            STATUS current
            DESCRIPTION
                "The percent of used IPv6 NDRA prefix of IPv6 address pool."
            ::= { hwIPv6PoolStatusEntry 16 }
            
        hwIPv6PDPrefixTotalNum OBJECT-TYPE
            SYNTAX Integer32
            MAX-ACCESS read-only
            STATUS current
            DESCRIPTION
                "The total PD prefix number of IPv6 address pool."
            ::= { hwIPv6PoolStatusEntry 17 }

        hwIPv6PDPrefixUsedNum OBJECT-TYPE
            SYNTAX Integer32
            MAX-ACCESS read-only
            STATUS current
            DESCRIPTION
                "The used PD prefix number of IPv6 address pool."
            ::= { hwIPv6PoolStatusEntry 18 }
            
        hwIPv6PDPrefixFreeNum OBJECT-TYPE
            SYNTAX Integer32
            MAX-ACCESS read-only
            STATUS current
            DESCRIPTION
                "The free PD prefix number of IPv6 address pool."
            ::= { hwIPv6PoolStatusEntry 19 } 
            
        hwIPv6PDPrefixConflictNum OBJECT-TYPE
            SYNTAX Integer32
            MAX-ACCESS read-only
            STATUS current
            DESCRIPTION
                "The conflict PD prefix number of IPv6 address pool."
            ::= { hwIPv6PoolStatusEntry 20 } 
            
        hwIPv6PDPrefixExcludeNum OBJECT-TYPE
            SYNTAX Integer32
            MAX-ACCESS read-only
            STATUS current
            DESCRIPTION
                "The excluded PD prefix number of IPv6 address pool."
            ::= { hwIPv6PoolStatusEntry 21 } 
            
        hwIPv6PDPrefixUsedPercent OBJECT-TYPE
            SYNTAX Integer32
            MAX-ACCESS read-only
            STATUS current
            DESCRIPTION
                "The percent of used IPv6 PD prefix of IPv6 address pool."
            ::= { hwIPv6PoolStatusEntry 22 } 

        hwIPv6ClientDuid OBJECT-TYPE
            SYNTAX OCTET STRING (SIZE (8..28))
            MAX-ACCESS read-create
            STATUS current
            DESCRIPTION
                "The client duid."
            ::= { hwIPv6DuidBindPrefixEntry 1 }

        hwIPv6BindPrefix OBJECT-TYPE
            SYNTAX Ipv6AddressPrefix
            MAX-ACCESS read-create
            STATUS current
            DESCRIPTION
                "The binding prefix of client."
            ::= { hwIPv6DuidBindPrefixEntry 2 }

        hwIPv6DuidBindPrefixRowStatus OBJECT-TYPE
            SYNTAX RowStatus 
            MAX-ACCESS read-create
            STATUS current
            DESCRIPTION
                "Row admin status. Support adding and deletion."
            ::= { hwIPv6DuidBindPrefixEntry 3 }

        hwDhcpv6SvrGroupIndex OBJECT-TYPE
            SYNTAX Integer32 (0..4095)
            MAX-ACCESS read-only
            STATUS current
            DESCRIPTION
                "The index of DHCPv6 server group."
            ::= { hwDhcpv6SvrGroupEntry 1 }

        hwDhcpv6SvrGroupName OBJECT-TYPE
            SYNTAX OCTET STRING (SIZE (1..32))
            MAX-ACCESS read-create
            STATUS current
            DESCRIPTION
                "The name of DHCPv6 server group."
            ::= { hwDhcpv6SvrGroupEntry 2 }

        hwIPDhcpv6SvrAddr1 OBJECT-TYPE
            SYNTAX Ipv6Address
            MAX-ACCESS read-create
            STATUS current
            DESCRIPTION
                "The primary DNS address."
            ::= { hwDhcpv6SvrGroupEntry 3 }

        hwIPDhcpv6SvrAddr2 OBJECT-TYPE
            SYNTAX Ipv6Address
            MAX-ACCESS read-create
            STATUS current
            DESCRIPTION
                "The seconday DNS address."
            ::= { hwDhcpv6SvrGroupEntry 4 }

        hwIPDhcpv6PriSvrState OBJECT-TYPE
            SYNTAX INTEGER {down(0), up(1)}
            MAX-ACCESS read-only
            STATUS current
            DESCRIPTION
                "The status of primary DNS."
            ::= { hwDhcpv6SvrGroupEntry 5 }

        hwIPDhcpv6ScdSvrState OBJECT-TYPE
            SYNTAX INTEGER {down(0), up(1)}
            MAX-ACCESS read-only
            STATUS current
            DESCRIPTION
                "The status of secondary DNS."
            ::= { hwDhcpv6SvrGroupEntry 6 }

        hwIPDhcpv6SvrAutoRelease OBJECT-TYPE
            SYNTAX TruthValue
            MAX-ACCESS read-create
            STATUS current
            DESCRIPTION
                "The flag indicating whether server will automaticly send DHCPv6 release packet."
            ::= { hwDhcpv6SvrGroupEntry 7 }

        hwIPDhcpv6SvrGroupRefCount OBJECT-TYPE
            SYNTAX Integer32 (0..4096)
            MAX-ACCESS read-only
            STATUS current
            DESCRIPTION
                "The referenced count of DHCPv6 server group."
            ::= { hwDhcpv6SvrGroupEntry 8 }

        hwDhcpv6SvrInterface1 OBJECT-TYPE
            SYNTAX DisplayString
            MAX-ACCESS read-create
            STATUS current
            DESCRIPTION
                "The outer interface of primary DHCPv6 server."
            ::= { hwDhcpv6SvrGroupEntry 9 }

        hwDhcpv6SvrInterface2 OBJECT-TYPE
            SYNTAX DisplayString
            MAX-ACCESS read-create
            STATUS current
            DESCRIPTION
                "The outer interface of secondary DHCPv6 server."
            ::= { hwDhcpv6SvrGroupEntry 10 }

        hwDhcpv6SvrAlgorithm OBJECT-TYPE
            SYNTAX INTEGER {master-backup(1), loading-share(2)}
            MAX-ACCESS read-create
            STATUS current
            DESCRIPTION
                "The algorithm of selecting DHCPv6 server."
            ::= { hwDhcpv6SvrGroupEntry 11 }

        hwDhcpv6SvrWeight1 OBJECT-TYPE
            SYNTAX Integer32 (0..100)
            MAX-ACCESS read-create
            STATUS current
            DESCRIPTION
                "The weight of primary DHCPv6 server."
            ::= { hwDhcpv6SvrGroupEntry 12 }

        hwDhcpv6SvrWeight2 OBJECT-TYPE
            SYNTAX Integer32 (0..100)
            MAX-ACCESS read-create
            STATUS current
            DESCRIPTION
                "The weight of secondary DHCPv6 server."
            ::= { hwDhcpv6SvrGroupEntry 13 }

        hwIPDhcpv6Svr1VrfName OBJECT-TYPE
            SYNTAX OCTET STRING (SIZE (1..31))
            MAX-ACCESS read-create
            STATUS current
            DESCRIPTION
                "The vpn instance name of primary DHCPv6 server."
            ::= { hwDhcpv6SvrGroupEntry 14 }

        hwIPDhcpv6Svr2VrfName OBJECT-TYPE
            SYNTAX OCTET STRING (SIZE (1..31))
            MAX-ACCESS read-create
            STATUS current
            DESCRIPTION
                "The vpn instance name of secondary DHCPv6 server."
            ::= { hwDhcpv6SvrGroupEntry 15 }

        hwDhcpv6SvrGroupRowStatus OBJECT-TYPE
            SYNTAX RowStatus 
            MAX-ACCESS read-create
            STATUS current
            DESCRIPTION
                "Row admin status. Support adding, modification and deletion."
            ::= { hwDhcpv6SvrGroupEntry 16 }

        hwIPv6RemotePoolIndex OBJECT-TYPE
            SYNTAX Integer32 (0..1023)
            MAX-ACCESS read-only
            STATUS current
            DESCRIPTION
                "The index of remote address pool."
            ::= { hwIPv6RemotePoolEntry 1 }

        hwIPv6RemotePoolName OBJECT-TYPE
            SYNTAX OCTET STRING (SIZE (1..32))
            MAX-ACCESS read-create
            STATUS current
            DESCRIPTION
                "The name of remote address pool."
            ::= { hwIPv6RemotePoolEntry 2 }

        hwIPv6RemotePoolPrefixName OBJECT-TYPE
            SYNTAX OCTET STRING (SIZE (1..32))
            MAX-ACCESS read-create
            STATUS current
            DESCRIPTION
                "The prefix pool name of remote address pool."
            ::= { hwIPv6RemotePoolEntry 3 }

        hwIPv6RemotePoolDhcpv6SvrGroupName OBJECT-TYPE
            SYNTAX OCTET STRING (SIZE (1..32))
            MAX-ACCESS read-create
            STATUS current
            DESCRIPTION
                "The DHCPv6 server group name of remote address pool."
            ::= { hwIPv6RemotePoolEntry 4 }

        hwIPv6RemotePoolAvailableStatus OBJECT-TYPE
            SYNTAX TruthValue
            MAX-ACCESS read-create
            STATUS current
            DESCRIPTION
                "The flag indicating whether remote address pool is locked."
            ::= { hwIPv6RemotePoolEntry 5 }

        hwIPv6RemotePoolExportHostRouteFlag OBJECT-TYPE
            SYNTAX TruthValue
            MAX-ACCESS read-create
            STATUS current
            DESCRIPTION
                "The flag indicating whether to export host route."
            ::= { hwIPv6RemotePoolEntry 6 }

        hwIPv6RemotePoolRowStatus OBJECT-TYPE
            SYNTAX RowStatus 
            MAX-ACCESS read-create
            STATUS current
            DESCRIPTION
                "Row admin status. Support adding, modification and deletion."
            ::= { hwIPv6RemotePoolEntry 7 }

--Statistics of ipv6 address pool usage: added by b00174290
        hwIPv6PoolStatistic OBJECT IDENTIFIER ::= { hwIPPoolMibObjects 22 }
        
        hwIpv6PoolNum OBJECT-TYPE
            SYNTAX Integer32
            MAX-ACCESS read-only
            STATUS current
            DESCRIPTION
                "Number of configured IPv6 address pools."
            ::= { hwIPv6PoolStatistic 1 }

        hwIpv6AddressIdleTotalNum OBJECT-TYPE
            SYNTAX Integer32
            MAX-ACCESS read-only
            STATUS current
            DESCRIPTION
                "Number of idle IPv6 addresses on the equipment."
            ::= { hwIPv6PoolStatistic 2 }

        hwIpv6PrefixIdleTotalNum OBJECT-TYPE
            SYNTAX Integer32
            MAX-ACCESS read-only
            STATUS current
            DESCRIPTION
                "Number of idle IPv6 prefixes on the equipment."
            ::= { hwIPv6PoolStatistic 3 }

        hwIpv6AddressUsedTotalNum OBJECT-TYPE
            SYNTAX Integer32
            MAX-ACCESS read-only
            STATUS current
            DESCRIPTION
                "Number of IPv6 addresses in use on the equipment."
            ::= { hwIPv6PoolStatistic 4 }
    
        hwIpv6PrefixUsedTotalNum OBJECT-TYPE
            SYNTAX Integer32
            MAX-ACCESS read-only
            STATUS current
            DESCRIPTION
                "Number of IPv6 prefixes in use on the equipment."
            ::= { hwIPv6PoolStatistic 5 }
        
        hwAllIPv6AddressTotalNum OBJECT-TYPE
            SYNTAX Integer32
            MAX-ACCESS read-only
            STATUS current
            DESCRIPTION
                "The total IPv6 address number."
            ::= { hwIPv6PoolStatistic 6 }
            
        hwAllIPv6AddressUsedNum OBJECT-TYPE
            SYNTAX Integer32
            MAX-ACCESS read-only
            STATUS current
            DESCRIPTION
                "The used IPv6 address number."
            ::= { hwIPv6PoolStatistic 7 }
            
        hwAllIPv6AddressIdleNum OBJECT-TYPE
            SYNTAX Integer32
            MAX-ACCESS read-only
            STATUS current
            DESCRIPTION
                "The free IPv6 address number."
            ::= { hwIPv6PoolStatistic 8 }
          
        hwAllIPv6ConflictAddressNum OBJECT-TYPE
            SYNTAX Integer32
            MAX-ACCESS read-only
            STATUS current
            DESCRIPTION
                "The conflict IPv6 address number."
            ::= { hwIPv6PoolStatistic 9 }
          
        hwAllIPv6ExcludeAddressNum OBJECT-TYPE
            SYNTAX Integer32
            MAX-ACCESS read-only
            STATUS current
            DESCRIPTION
                "The excluded IPv6 address number."
            ::= { hwIPv6PoolStatistic 10 }
          
        hwAllIPv6AddressUsedPercent OBJECT-TYPE
            SYNTAX Integer32
            MAX-ACCESS read-only
            STATUS current
            DESCRIPTION
                "The percent of used IPv6 address."
            ::= { hwIPv6PoolStatistic 11 }
          
        hwAllNDRAPrefixTotalNum OBJECT-TYPE
            SYNTAX Integer32
            MAX-ACCESS read-only
            STATUS current
            DESCRIPTION
                "The total NDRA prefix number."
            ::= { hwIPv6PoolStatistic 12 }
          
        hwAllNDRAPrefixUsedNum OBJECT-TYPE
            SYNTAX Integer32
            MAX-ACCESS read-only
            STATUS current
            DESCRIPTION
                "The used NDRA prefix number."
            ::= { hwIPv6PoolStatistic 13 }
          
        hwAllNDRAPrefixFreeNum OBJECT-TYPE
            SYNTAX Integer32
            MAX-ACCESS read-only
            STATUS current
            DESCRIPTION
                "The free NDRA prefix number."
            ::= { hwIPv6PoolStatistic 14 }
          
        hwAllNDRAPrefixConflictNum OBJECT-TYPE
            SYNTAX Integer32
            MAX-ACCESS read-only
            STATUS current
            DESCRIPTION
                "The conflict NDRA prefix number."
            ::= { hwIPv6PoolStatistic 15 }
          
        hwAllNDRAPrefixExcludeNum OBJECT-TYPE
            SYNTAX Integer32
            MAX-ACCESS read-only
            STATUS current
            DESCRIPTION
                "The excluded NDRA prefix number."
            ::= { hwIPv6PoolStatistic 16 }
          
        hwAllNDRAPrefixUsedPercent OBJECT-TYPE
            SYNTAX Integer32
            MAX-ACCESS read-only
            STATUS current
            DESCRIPTION
                "The percent of used IPv6 NDRA prefix."
            ::= { hwIPv6PoolStatistic 17 }
          
        hwAllPDPrefixTotalNum OBJECT-TYPE
            SYNTAX Integer32
            MAX-ACCESS read-only
            STATUS current
            DESCRIPTION
                "The total PD prefix number."
            ::= { hwIPv6PoolStatistic 18 }
            
        hwAllPDPrefixUsedNum OBJECT-TYPE
            SYNTAX Integer32
            MAX-ACCESS read-only
            STATUS current
            DESCRIPTION
                "The used PD prefix number."
            ::= { hwIPv6PoolStatistic 19 }
            
        hwAllPDPrefixFreeNum OBJECT-TYPE
            SYNTAX Integer32
            MAX-ACCESS read-only
            STATUS current
            DESCRIPTION
                "The free PD prefix number."
            ::= { hwIPv6PoolStatistic 20 }
            
        hwAllPDPrefixConflictNum OBJECT-TYPE
            SYNTAX Integer32
            MAX-ACCESS read-only
            STATUS current
            DESCRIPTION
                "The conflict PD prefix number."
            ::= { hwIPv6PoolStatistic 21 }      
            
        hwAllPDPrefixExcludeNum OBJECT-TYPE
            SYNTAX Integer32
            MAX-ACCESS read-only
            STATUS current
            DESCRIPTION
                "The excluded PD prefix number."
            ::= { hwIPv6PoolStatistic 22 }  

        hwAllPDPrefixUsedPercent OBJECT-TYPE
            SYNTAX Integer32
            MAX-ACCESS read-only
            STATUS current
            DESCRIPTION
                "The percent of used IPv6 PD prefix."
            ::= { hwIPv6PoolStatistic 23 }

 --end:added by t00189639 for amv6
 
--begin:added by d00177572 for option 43
        hwIPPoolOptionExtTable OBJECT-TYPE
            SYNTAX SEQUENCE OF HwIPPoolOptionExtEntry
            MAX-ACCESS not-accessible
            STATUS current
            DESCRIPTION
                "A Ext table for configuring options to DHCP server pools,
               include option code type and value and so on ."
            ::= { hwIPPoolMibObjects 14 }
        
        hwIPPoolOptionExtEntry OBJECT-TYPE
            SYNTAX HwIPPoolOptionExtEntry
            MAX-ACCESS not-accessible
            STATUS current
            DESCRIPTION
                "DESCRIPTION."
            INDEX { hwIPPoolIndex, hwIPDhcpOptionId, hwIPDhcpOptionSubId }
            ::= { hwIPPoolOptionExtTable 1 }
        
        HwIPPoolOptionExtEntry ::=
            SEQUENCE {  
                    hwIPDhcpOptionSubId
                        Integer32,
                    hwIPDhcpOptionSubType
                        INTEGER,  
                    hwIPDhcpOptionSubValue
                        OCTET STRING,
                    hwIPDhcpOptionSubRowStatus 
                        RowStatus          
                 }
                 
        hwIPDhcpOptionSubId OBJECT-TYPE
            SYNTAX Integer32 (1..254)
            MAX-ACCESS read-only
            STATUS current
            DESCRIPTION
                "Sub Option ID.
                 When IP addresses are allocated by the built-in DHCP sever, the option is a configuration parameter, which needs to be defined and explained by the carrier."
            ::= { hwIPPoolOptionExtEntry 1 }           
      
        hwIPDhcpOptionSubType OBJECT-TYPE
            SYNTAX INTEGER {ip(1), string(2)}
            MAX-ACCESS read-create
            STATUS current
            DESCRIPTION
                "Value indicates the type of sub-option, 1--ip, 2--string."
            ::= { hwIPPoolOptionExtEntry 2 }    
   
        hwIPDhcpOptionSubValue OBJECT-TYPE
            SYNTAX OCTET STRING(SIZE (1..64))
            MAX-ACCESS read-create
            STATUS current
            DESCRIPTION
                "Value of the sub-option."
            ::= { hwIPPoolOptionExtEntry 3 }       

                   
            
        hwIPDhcpOptionSubRowStatus OBJECT-TYPE
            SYNTAX RowStatus
            MAX-ACCESS read-create
            STATUS current
            DESCRIPTION
                "This object is used to configuration new rows in this
            table, modify existing rows, and to delete
            existing rows.Only three actions are used: active(1),
            createAndGo(4), destroy(6).
            while configuration new suboption, you must specify suboption type 
            and value"
            ::= { hwIPPoolOptionExtEntry 50 }                            
  
--End:added by d00177572 for option 43
 --begin:added by d00134788 for option43-suboption

         hwIPPoolReplyOptionTable OBJECT-TYPE
            SYNTAX SEQUENCE OF HwIPPoolReplyOptionEntry
            MAX-ACCESS not-accessible
            STATUS current
            DESCRIPTION
                "A table for configuring options which will be replied to client 
                 in according to specified option value of DHCP client request "
            ::= { hwIPPoolMibObjects 15 }
        
        hwIPPoolReplyOptionEntry OBJECT-TYPE
            SYNTAX HwIPPoolReplyOptionEntry
            MAX-ACCESS not-accessible
            STATUS current
            DESCRIPTION
                "DESCRIPTION."
            INDEX { hwIPPoolIndex,hwIPDhcpSpecOptionId,hwIPDhcpSpecOption,hwIPDhcpReplyOptionId,hwIPDhcpReplyOptionSubId }
            ::= { hwIPPoolReplyOptionTable 1 }
        
        HwIPPoolReplyOptionEntry ::=
            SEQUENCE {  
                    hwIPDhcpSpecOptionId
                        Integer32,
                    hwIPDhcpSpecOption
                        OCTET STRING,
                    hwIPDhcpReplyOptionId
                        Integer32,
                    hwIPDhcpReplyOptionSubId
                        Integer32,
                    hwIPDhcpReplyOptionSubType
                        INTEGER,
                    hwIPDhcpReplyOptionSub
                        OCTET STRING,                                                                        
                    hwIPDhcpReplyOptionRowStatus 
                        RowStatus       
                 }
                 
        hwIPDhcpSpecOptionId OBJECT-TYPE
            SYNTAX Integer32 (60..60)
            MAX-ACCESS read-only
            STATUS current
            DESCRIPTION
                "Option ID.
                 Option code from DHCP request of client."
            ::= { hwIPPoolReplyOptionEntry 1 }                 

        hwIPDhcpSpecOption OBJECT-TYPE
            SYNTAX OCTET STRING (SIZE(1..64))
            MAX-ACCESS read-only
            STATUS current
            DESCRIPTION
                "Option ID.
                 Option code from DHCP request of client."
            ::= { hwIPPoolReplyOptionEntry 2 }           
            
        hwIPDhcpReplyOptionId OBJECT-TYPE
            SYNTAX Integer32 (2..254)
            MAX-ACCESS read-only
            STATUS current
            DESCRIPTION
                "This object is used to configuration option code which is needed to 
                reply to client according to specified option value in DHCP request,
                Option code, from 2 to 254, include 2 and 254, exclude
                  3,6,15,44,46,50-54,57-60,82"
            ::= { hwIPPoolReplyOptionEntry 3 }

        hwIPDhcpReplyOptionSubId OBJECT-TYPE
            SYNTAX Integer32 (1..254)
            MAX-ACCESS read-only
            STATUS current
            DESCRIPTION
                "Sub Option ID.
                 When IP addresses are allocated by the built-in DHCP sever, the option is a configuration parameter, 
                 which needs to be defined and explained by the carrier."
            ::= { hwIPPoolReplyOptionEntry 4 }           
      
        hwIPDhcpReplyOptionSubType OBJECT-TYPE
            SYNTAX INTEGER {ip(1), string(2), hex(3)}
            MAX-ACCESS read-create
            STATUS current
            DESCRIPTION
                "Value indicates the type of sub-option, 1--ip, 2--string, 3--hex."
            ::= { hwIPPoolReplyOptionEntry 5 }    
   
        hwIPDhcpReplyOptionSub OBJECT-TYPE
            SYNTAX OCTET STRING(SIZE (1..128))
            MAX-ACCESS read-create
            STATUS current
            DESCRIPTION
                "Value of the sub-option."
            ::= { hwIPPoolReplyOptionEntry 6 }       
                        
        hwIPDhcpReplyOptionRowStatus OBJECT-TYPE
            SYNTAX RowStatus
            MAX-ACCESS read-create
            STATUS current
            DESCRIPTION
                "This object is used to configuration new rows in this
            table, modify existing rows, and to delete
            existing rows.Only three actions are used: active(1),
            createAndGo(4), destroy(6).
            while configuration new option, you must specify option type 
            and value"
            ::= { hwIPPoolReplyOptionEntry 50 }                           

  --end:added by d00134788 for option43-suboption           

        hwIPPoolMibTrap OBJECT IDENTIFIER ::= { hwIPpool 2 }

        hwIPPoolTrapOid OBJECT IDENTIFIER ::= { hwIPPoolMibTrap 1 }

        hwUserIPAddress OBJECT-TYPE
            SYNTAX IpAddress
            MAX-ACCESS accessible-for-notify
            STATUS current
            DESCRIPTION
                "IP address of the user."
            ::= { hwIPPoolTrapOid 1 }

        hwDHCPServerAddr OBJECT-TYPE
            SYNTAX IpAddress
            MAX-ACCESS accessible-for-notify
            STATUS current
            DESCRIPTION
                "IP address of the DHCP server."
            ::= { hwIPPoolTrapOid 2 }
                                      
        hwDhcpSvrVrfName OBJECT-TYPE
            SYNTAX DisplayString (SIZE (1..31))
            MAX-ACCESS accessible-for-notify
            STATUS current
            DESCRIPTION
                "DHCP    VPN instance name."
            ::= { hwIPPoolTrapOid 3 }

       hwIPPoolGroupIndex OBJECT-TYPE
            SYNTAX Integer32 (0..255)
            MAX-ACCESS accessible-for-notify
            STATUS current
            DESCRIPTION
                "Exclusive index of IP pool group."
            ::= { hwIPPoolTrapOid 4 } 

                                      
        hwIPPoolTrapsDefine OBJECT IDENTIFIER ::= { hwIPPoolMibTrap 2 }

        hwIPPoolTraps OBJECT IDENTIFIER ::= { hwIPPoolTrapsDefine 0 }

        hwUserIPConflictAlarm NOTIFICATION-TYPE
            OBJECTS { hwUserIPAddress,hwIPPoolName}
            STATUS current
            DESCRIPTION
                "
                1 Notice/Trap name: IP address conflict error.
                2 Notice/Trap generation cause: user IP address conflict.
                3 Repair suggestions:
                    Check whether to renew configuring the BAS IP pool.
                    Check whether the IP address of BAS interface conflicts user IP address."
            ::= { hwIPPoolTraps 1 }

        hwUserIPLeaseAlarm NOTIFICATION-TYPE
            OBJECTS { hwUserIPAddress }
            STATUS current
            DESCRIPTION
                "
                1 Notice/Trap name: IP address lease alarm.
                2 Notice/Trap generation cause: The user IP lease is over.
                3 Repair suggestion:
                    Check whether to renew configuring BAS IP pool."
            ::= { hwIPPoolTraps 2 }

        hwAllocUserIPFailAlarm NOTIFICATION-TYPE
            OBJECTS { hwIPPoolIndex,hwIPPoolName }
            STATUS current
            DESCRIPTION
                "
                1 Notice/Trap name: allocate user IP fail alarm.
                2 Notice/Trap generation cause: there are no enough IP addresses for users.
                3 Repair suggestion:
                    Check whether there are enough addresses in IP pool of the domain."
            ::= { hwIPPoolTraps 3 }

        hwDhcpServerDown NOTIFICATION-TYPE
            OBJECTS { hwDHCPServerAddr, hwRemoteIPPoolRouterIPAddr,hwDhcpSvrVrfName}
            STATUS current
            DESCRIPTION 
                "
                Description: The DHCP server does not respond. This alarm is generated if the network is unstable, the DHCP server is Down, or there is not any available address in the DHCP server when a user applies for an address to the external DHCP server. 
                Parameter: IP address of the DHCP server, address pool that the user expects (the address pool is identified by the gateway address because there may be multiple address pools on a server), VPN instance name.
                    "
            ::= { hwIPPoolTraps 4 }
            
        hwLocalIPPoolDifferWithServer NOTIFICATION-TYPE
            OBJECTS { hwRemoteIPPoolName }
            STATUS current
            DESCRIPTION 
                "
                The configuration of the IP address pool on the DHCP server is not the same as the configuration of the remote address pool on the local equipment.
                Solution: Check whether the configuration of the IP address pool on the DHCP server, including the gateway address, mask, and the address range, is the same as the configuration of the remote address pool on the local equipment.
                "
            ::= { hwIPPoolTraps 5 }
            
        hwUsedIPReachThreshold NOTIFICATION-TYPE
            OBJECTS { hwIPPoolIndex,hwIPPoolName }
            STATUS current
            DESCRIPTION 
                "
                The number of used IP addresses in the pool exceeds the threshold.
                Repair suggestion: Check the configuration of the IP address pool.
                "
            ::= { hwIPPoolTraps 6 }  
        
       hwUsedIPReachThresholdResume NOTIFICATION-TYPE
            OBJECTS { hwIPPoolIndex,hwIPPoolName }
            STATUS current
            DESCRIPTION 
                "
                The number of used IP addresses  in the pool is under the threshold.
                "
            ::= { hwIPPoolTraps 7 } 
       
       hwUsedDeleteUnnumberedRouter  NOTIFICATION-TYPE
            OBJECTS { hwIPPoolIndex,hwIPPoolName }
            STATUS current
            DESCRIPTION
                "
                   The interface is unnumbered by the pool.
                "
            ::= { hwIPPoolTraps 8 }

       hwPoolGroupUsedIPReachThreshold NOTIFICATION-TYPE
            OBJECTS { hwIPPoolGroupIndex, hwIPPoolGroupName }
            STATUS current
            DESCRIPTION 
                "
                The number of used IP addresses in the IP pool group exceeds the threshold.
                Repair suggestion: Check the configuration of the IP address pool group.
                "
            ::= { hwIPPoolTraps 9 }  
        
       hwPoolGroupUsedIPReachThresholdResume NOTIFICATION-TYPE
            OBJECTS { hwIPPoolGroupIndex, hwIPPoolGroupName }
            STATUS current
            DESCRIPTION 
                "
                The number of used IP addresses in the IP pool group is under the threshold.
                "
            ::= { hwIPPoolTraps 10 } 
            
       hwIPPoolConstantIndexFail NOTIFICATION-TYPE
            STATUS current
            DESCRIPTION 
                "
                The constance index of ip pool recover failure.
                "
            ::= { hwIPPoolTraps 11 }
            
       hwIPv6PrefixConstantIndexFail NOTIFICATION-TYPE
            STATUS current
            DESCRIPTION 
                "
                The constance index of  ipv6 prefix pool recover failure.
                "
            ::= { hwIPPoolTraps 12 }
            
       hwIPv6PoolConstantIndexFail NOTIFICATION-TYPE
            STATUS current
            DESCRIPTION 
                "
                The constance index of ipv6 pool recover failure.
                "
            ::= { hwIPPoolTraps 13 } 
      hwUsedIPExhaust NOTIFICATION-TYPE
            OBJECTS { hwIPPoolIndex,hwIPPoolName }
            STATUS current
            DESCRIPTION 
                "
                The number of IP addresses in the IP pool is exhausted.
                "
            ::= { hwIPPoolTraps 14 } 
              
      hwUsedIPExhaustResume NOTIFICATION-TYPE
            OBJECTS { hwIPPoolIndex,hwIPPoolName }
            STATUS current
            DESCRIPTION 
                "
                The number of IP addresses in the IP pool is under the exhaust.
                "
            ::= { hwIPPoolTraps 15 }  
            
      hwPoolGroupUsedIPExhaust NOTIFICATION-TYPE 
           OBJECTS { hwIPPoolGroupIndex, hwIPPoolGroupName }
           STATUS current
           DESCRIPTION 
                "
                The number of IP addresses in the IP pool group is exhausted.
                "
           ::= { hwIPPoolTraps 16 }
      hwPoolGroupUsedIPExhaustResume NOTIFICATION-TYPE 
           OBJECTS { hwIPPoolGroupIndex, hwIPPoolGroupName }
           STATUS current
           DESCRIPTION 
                "
                The number of IP addresses in the IP pool group is under the exhaust.
                "
           ::= { hwIPPoolTraps 17 }
        
    --  ============== conformance information ==============

        hwIpPoolMIBConformance OBJECT IDENTIFIER ::= { hwIPpool 3 }
            
        hwIpPoolCompliances OBJECT IDENTIFIER ::= { hwIpPoolMIBConformance 1 }
        hwIpPoolCompliance MODULE-COMPLIANCE
               STATUS      current
               DESCRIPTION
                   "The compliance statement for systems supporting this module."

               MODULE      -- this module
               MANDATORY-GROUPS    { hwIpPoolTableGroup, hwIpSectionTableGroup, hwIpPoolExtTableGroup,
                                     hwIpAddressStatusTableGroup, hwDhcpSvrGroupTableGroup, hwRemotePoolTableGroup, hwDhcpServerTableGroup, 
                                     hwIpPoolStatisticGroup, hwIpPoolTrapOidGroup, hwIpPoolTrapsGroup, hwIPPoolGroupTableGroup, 
                                     hwIPPoolGroupExtTableGroup, hwIPPoolGroupDisplayTableGroup, hwIPPoolDomainSearchListTableGroup,
                                     hwIPv6PrefixTableGroup, hwIPv6PoolTableGroup, hwIPv6PoolStatusTableGroup,
                                     hwIPv6DuidBindPrefixTableGroup, hwDhcpv6SvrGroupTableGroup, hwIPv6RemotePoolTableGroup, hwIPv6PoolStatisticGroup}  
                                               
              ::= { hwIpPoolCompliances 1 }
              
    --  ============== groups ==============  
        hwIpPoolObjectGroups OBJECT IDENTIFIER ::= { hwIpPoolMIBConformance 2 } 

        hwIpPoolTableGroup OBJECT-GROUP            
            OBJECTS { hwIPPoolIndex, 
            hwIPPoolName,
            hwIPPoolRouterIPAddr,
            hwIPPoolRouterIPMask,
            hwIPPoolPriDNSIPAddr,
            hwIPPoolSecDNSIPAddr,
            hwIPPoolPriNBNSIPAddr,
            hwIPPoolSecNBNSIPAddr,
            hwIPPoolIPAddrLease,
            hwIPPoolStatus,
            hwIPPoolVPNInstance,
            hwIPPoolType,
            hwIPPoolNetwork,
            hwIPPoolNetworkMask,
            hwIPPoolIPTotalNum,    
            hwIPPoolIPUsedNum,
            hwIPPoolIPConflictNum, 
            hwIPPoolIPExcludeNum, 
            hwIPPoolIPIdleNum,
            hwIPPoolIPUsedPercent,
            hwIPPoolDNSIPAddrString,
            hwIPPoolDNSIPAddrStringUndo,
            hwIPPoolNBNSIPAddrString,
            hwIPPoolNBNSIPAddrStringUndo
                           }
        STATUS current
        DESCRIPTION 
            "The HUAWEI IP pool configuration group."
        ::= { hwIpPoolObjectGroups 1 }    
        
        hwIpSectionTableGroup OBJECT-GROUP            
            OBJECTS {hwIPSectionIndex,
            hwIPSectionDesc,
            hwIPSectionLowAddr,
            hwIPSectionHighAddr,
            hwIPSectionLength,
            hwIPSectionUsedNum,
            hwIPSectionConflict,
            hwIPSectionInvalid,
            hwIPSectionAvailableNum,
            hwIPSectionRowStatus
                }
        STATUS current
        DESCRIPTION 
            "The HUAWEI IP section configuration group."
        ::= { hwIpPoolObjectGroups 2 }    
        
        hwIpPoolExtTableGroup OBJECT-GROUP            
            OBJECTS {hwIPPoolAvailableStatus,
            hwIPDhcpOptionId1,
                    hwIPDhcpOption1,
                    hwIPDhcpOptionId2,
                    hwIPDhcpOption2,
                    hwIPDhcpOptionId3,
                    hwIPDhcpOption3,
                    hwIPDhcpOptionId4,
                    hwIPDhcpOption4,
                    hwIPDnsSuffix,
                    hwIPDhcpSvrIPRsv,
                    hwIPPoolIpAddrRenewal,
                    hwIPPoolIpAddrRebinding,
                    hwIPPoolSIPAddr1,
                    hwIPPoolSIPAddr2,
                    hwIPPoolSIPName1,
                    hwIPPoolSIPName2
                }
        STATUS current
        DESCRIPTION 
            "The HUAWEI IP pool extension configuration group."
        ::= { hwIpPoolObjectGroups 3 }    
        
        hwIpAddressStatusTableGroup OBJECT-GROUP            
            OBJECTS {hwIPAddress,
            hwIPAddressStatus,
            hwPoolName
                }
        STATUS current
        DESCRIPTION 
            "The HUAWEI IP address status configuration group."
        ::= { hwIpPoolObjectGroups 4 }    
        
        hwDhcpSvrGroupTableGroup OBJECT-GROUP            
            OBJECTS {hwIPPoolDhcpSvrGroupIndex,
                    hwIPPoolDhcpSvrGroupName,
                    hwIPDhcpSvrPriAddr,
                    hwIPDhcpSvrScdiAddr,
                    hwIPDhcpSvrPriState,
                    hwIPDhcpScdPriState,
                    hwIPDhcpSvrAutoRelease,
                    hwIPDhcpSvrRefCount,
                    hwIPDhcpSvrRowStatus,  
                    hwIPDhcpSvrPriVpnInstance,
                    hwIPDhcpSvrScdVpnInstance,
                    hwIPDhcpSvrSouce
                }
        STATUS current
        DESCRIPTION 
            "The HUAWEI DHCP service group configuration group."
        ::= { hwIpPoolObjectGroups 5 }    
        
        hwRemotePoolTableGroup OBJECT-GROUP            
            OBJECTS {hwRemoteIPPoolIndex,
                    hwRemoteIPPoolName,
                    hwRemoteIPPoolRouterIPAddr,
                    hwRemoteIPPoolRouterIPMask,
                    hwRemoteIPPoolDhcpSvrGroupID,
                    hwRemoteIPPoolAvailableStatus,
                    hwRemoteIPPoolRowStatus,
                    hwRemoteIPPoolPriDNSIPAddress,
                    hwRemoteIPPoolSecDNSIPAddress,
                    hwRemoteIPPoolPriNBNSIPAddress,
                    hwRemoteIPPoolSecNBNSIPAddress,
                    hwRemoteIPPoolVPNInstance,
                    hwRemoteIPPoolDhcpGroupName
                }
        STATUS current
        DESCRIPTION 
            "The HUAWEI remote pool configuration group."
        ::= { hwIpPoolObjectGroups 6 }

        hwIpPoolStatisticGroup OBJECT-GROUP            
            OBJECTS {hwIPPoolNum,
                    hwIPIdleTotalNum,
                    hwIPUsedTotalNum,
                    hwIPConflictTotalNum,
                    hwIPExcludeTotalNum,
                    hwIPTotalNum,
                    hwIPUsedPercent
                }
        STATUS current
        DESCRIPTION 
            "The HUAWEI IP pool statistics group."
        ::= { hwIpPoolObjectGroups 7 }

        hwIpPoolTrapOidGroup OBJECT-GROUP            
            OBJECTS {hwUserIPAddress,
                    hwDHCPServerAddr,
                    hwDhcpSvrVrfName,
                    hwIPPoolGroupIndex
                }
        STATUS current
        DESCRIPTION 
            "The HUAWEI IP pool trap OID group."
        ::= { hwIpPoolObjectGroups 8 }
        
        hwIpPoolTrapsGroup NOTIFICATION-GROUP
            NOTIFICATIONS { hwUserIPConflictAlarm, hwUserIPLeaseAlarm, hwAllocUserIPFailAlarm,
                            hwDhcpServerDown, hwLocalIPPoolDifferWithServer, 
                            hwUsedIPReachThreshold, hwUsedIPReachThresholdResume, hwUsedDeleteUnnumberedRouter, 
                            hwPoolGroupUsedIPReachThreshold, hwPoolGroupUsedIPReachThresholdResume,
                            hwIPPoolConstantIndexFail, hwIPv6PrefixConstantIndexFail,
                            hwIPv6PoolConstantIndexFail, 
                            hwUsedIPExhaust,hwUsedIPExhaustResume,
                            hwPoolGroupUsedIPExhaust,hwPoolGroupUsedIPExhaustResume}
            STATUS current
            DESCRIPTION 
                "The HUAWEI IP pool traps group."
            ::= { hwIpPoolObjectGroups 9 }

        hwDhcpServerTableGroup OBJECT-GROUP            
            OBJECTS {hwDhcpServerIndex,
                    hwIPPoolDhcpServerIP,
                    hwIPPoolDhcpServerVRFName,
                    hwIPPoolDhcpServerState,
                    hwIPPoolDhcpServerSendDisvSpdNum,
                    hwIPPoolDhcpServerSendDisvSpdSec
                }
            STATUS current
            DESCRIPTION 
                "The HUAWEI IP pool DHCP server configure group."
            ::= { hwIpPoolObjectGroups 10 }    
        
        hwIPPoolOptionTableGroup OBJECT-GROUP            
            OBJECTS {hwIPDhcpOptionId,
                     hwIPDhcpOption,
                     hwIPDhcpOptionRowStatus       
                }
            STATUS current
            DESCRIPTION 
                "A table for configuring options to DHCP server pools,
              include option code type and value and so on ."
            ::= { hwIpPoolObjectGroups 11 }    
            
        hwIPPoolGroupTableGroup OBJECT-GROUP            
            OBJECTS {hwIPPoolGroupName,
                     hwIPPoolGroupVPNInstance,
                     hwIPPoolGroupIncludeUndo,
                     hwIPPoolGroupRowStatus
                }
        STATUS current
        DESCRIPTION 
            "The HUAWEI Ip pool group configuration group."
        ::= { hwIpPoolObjectGroups 12 }
        
        hwIPPoolGroupExtTableGroup OBJECT-GROUP            
            OBJECTS {hwIPPoolGroupExtIncludePoolName,
                     hwIPPoolGroupExtIncludePoolMoveOrder,
                     hwIPPoolGroupExtRowStatus
                }
        STATUS current
        DESCRIPTION 
            "The HUAWEI Ip pool group extension configuration group."
        ::= { hwIpPoolObjectGroups 13 }
        
        hwIPPoolGroupDisplayTableGroup OBJECT-GROUP            
            OBJECTS {hwIPPoolGroupIncludePoolNum,
                     hwIPPoolGroupBoundByDomainNum,
                     hwIPPoolGroupIPTotalNum,
                     hwIPPoolGroupIPUsedNum,
                     hwIPPoolGroupIPConflictedNum,
                     hwIPPoolGroupIPDisableNum,
                     hwIPPoolGroupIPDesignatedNum,
                     hwIPPoolGroupIPFreeNum,
                     hwIPPoolGroupIPUsedPercent
                }
        STATUS current
        DESCRIPTION 
            "A table for displaying HUAWEI IP pool group."
        ::= { hwIpPoolObjectGroups 14 }
        
 --begin:added by w00175317 for option119        
        hwIPPoolDomainSearchListGroup OBJECT-GROUP            
            OBJECTS {hwIPPoolDomainSearchList,
                     hwIPPoolDomainSearchListRowStatus
                }
        STATUS current
        DESCRIPTION 
            "Set the domain search list name which is uesed to fill content of DHCP packet option 119."
        ::= { hwIpPoolObjectGroups 15 }
 --end:added by w00175317 for option119
 --begin:added by d00177572 for 0ption43
        hwIPPoolOptionExtTableGroup OBJECT-GROUP            
            OBJECTS {hwIPDhcpOptionSubId,
                     hwIPDhcpOptionSubType,
                     hwIPDhcpOptionSubValue, 
                     hwIPDhcpOptionSubRowStatus       
                }
            STATUS current
            DESCRIPTION 
                "A table for configuring options to DHCP server pools,
              include suboption code type and value and so on ."
            ::= { hwIpPoolObjectGroups 16 }   
 --end:added by d00177572 for 0ption43
 --begin:added by d00134788 for option43-suboption   
        hwIPPoolReplyOptionGroup OBJECT-GROUP            
            OBJECTS {hwIPDhcpSpecOptionId,
                     hwIPDhcpSpecOption,
                     hwIPDhcpReplyOptionId,
                     hwIPDhcpReplyOptionSubId,
                     hwIPDhcpReplyOptionSubType,
                     hwIPDhcpReplyOptionSub,
                     hwIPDhcpReplyOptionRowStatus
                }

        STATUS current
        DESCRIPTION 
            "Dhcp reply options which will be replied to client 
             in according to specified option value of DHCP client request "
        ::= { hwIpPoolObjectGroups 17 }

 --end:added by d00134788 for option43-suboption
 
 --begin: added by t00189639 for amv6
       hwIPv6PrefixTableGroup OBJECT-GROUP            
            OBJECTS {
                hwIPv6PrefixIndex,
                hwIPv6PrefixName,
                hwIPv6PrefixType,
                hwIPv6Prefix,
                hwIPv6PrefixLen,
                hwIPv6PrefixDelegatingLen,
                hwIPv6PrefixAdvPreferredLifetime,
                hwIPv6PrefixAdvValidLifetime,
                hwIPv6PrefixAvailableStatus,
                hwIPv6VPNInstance,
                hwIPv6PrefixReservedFlag,
                hwIPv6LinkAddress,
                hwIPv6SlaacUnsharedFlag,
                hwIPv6PrefixRowStatus
                }
        STATUS current
        DESCRIPTION 
            "."
        ::= { hwIpPoolObjectGroups 18 }

        hwIPv6PoolTableGroup OBJECT-GROUP            
            OBJECTS {
                hwIPv6PoolIndex,
                hwIPv6PoolName,
                hwIPv6PoolType,
                hwIPv6PoolPrefixName,
                hwIPv6PoolDnsIPAddr,
                hwIPv6PoolDnsSearchList,
                hwIPv6PoolPreference,
                hwIPv6PoolAvailableStatus,
                hwIPv6PoolRenewPercent,
                hwIPv6PoolRebindingPercent,
                hwIPv6PoolRapidCommitFlag,
                hwIPv6PoolUnicastOption,
                hwIPv6PoolAFTRName,
                hwIPv6PoolRowStatus
                }
        STATUS current
        DESCRIPTION 
            "."
        ::= { hwIpPoolObjectGroups 19 }

        hwIPv6PoolStatusTableGroup OBJECT-GROUP            
            OBJECTS {                
                hwIPv6FreeAddressNum,
                hwIPv6UsedAddressNum,
                hwIPv6FreePrefixNum,
                hwIPv6UsedPrefixNum,
                hwIPv6AddressTotalNum,
                hwIPv6AddressUsedNum,
                hwIPv6AddressFreeNum,     
                hwIPv6AddressConflictNum,
                hwIPv6AddressExcludeNum,
                hwIPv6AddressUsedPercent, 
                hwIPv6NDRAPrefixTotalNum,     
                hwIPv6NDRAPrefixUsedNum,      
                hwIPv6NDRAPrefixFreeNum,      
                hwIPv6NDRAPrefixConflictNum,  
                hwIPv6NDRAPrefixExcludeNum,   
                hwIPv6NDRAPrefixUsedPercent,  
                hwIPv6PDPrefixTotalNum,     
                hwIPv6PDPrefixUsedNum,      
                hwIPv6PDPrefixFreeNum,      
                hwIPv6PDPrefixConflictNum,  
                hwIPv6PDPrefixExcludeNum,   
                hwIPv6PDPrefixUsedPercent
                }
        STATUS current
        DESCRIPTION 
            "."
        ::= { hwIpPoolObjectGroups 20 }

        hwIPv6DuidBindPrefixTableGroup OBJECT-GROUP            
            OBJECTS {
                hwIPv6ClientDuid,
                hwIPv6BindPrefix,
                hwIPv6DuidBindPrefixRowStatus
                }
        STATUS current
        DESCRIPTION 
            "."
        ::= { hwIpPoolObjectGroups 21 }

        hwDhcpv6SvrGroupTableGroup OBJECT-GROUP            
            OBJECTS {
                hwDhcpv6SvrGroupIndex,
                hwDhcpv6SvrGroupName,
                hwIPDhcpv6SvrAddr1,
                hwIPDhcpv6SvrAddr2,
                hwIPDhcpv6PriSvrState,
                hwIPDhcpv6ScdSvrState,
                hwIPDhcpv6SvrAutoRelease,
                hwIPDhcpv6SvrGroupRefCount,
                hwDhcpv6SvrInterface1,
                hwDhcpv6SvrInterface2,
                hwDhcpv6SvrAlgorithm,
                hwDhcpv6SvrWeight1,
                hwDhcpv6SvrWeight2,
                hwIPDhcpv6Svr1VrfName,
                hwIPDhcpv6Svr2VrfName,
                hwDhcpv6SvrGroupRowStatus
                }
        STATUS current
        DESCRIPTION 
            "."
        ::= { hwIpPoolObjectGroups 22 }

        hwIPv6RemotePoolTableGroup OBJECT-GROUP            
            OBJECTS {
                hwIPv6RemotePoolIndex,
                hwIPv6RemotePoolName,
                hwIPv6RemotePoolPrefixName,
                hwIPv6RemotePoolDhcpv6SvrGroupName,
                hwIPv6RemotePoolAvailableStatus,
                hwIPv6RemotePoolExportHostRouteFlag,
                hwIPv6RemotePoolRowStatus
                }
        STATUS current
        DESCRIPTION 
            "."
        ::= { hwIpPoolObjectGroups 23 }

        hwIPv6PoolStatisticGroup OBJECT-GROUP            
            OBJECTS {hwIpv6PoolNum,
                    hwIpv6AddressIdleTotalNum,
                    hwIpv6PrefixIdleTotalNum,
                    hwIpv6AddressUsedTotalNum,
                    hwIpv6PrefixUsedTotalNum,
                    hwAllIPv6AddressTotalNum,
                    hwAllIPv6AddressUsedNum,
                    hwAllIPv6AddressIdleNum,      
                    hwAllIPv6ConflictAddressNum,
                    hwAllIPv6ExcludeAddressNum,
                    hwAllIPv6AddressUsedPercent,
                    hwAllNDRAPrefixTotalNum,
                    hwAllNDRAPrefixUsedNum,
                    hwAllNDRAPrefixFreeNum,
                    hwAllNDRAPrefixConflictNum,
                    hwAllNDRAPrefixExcludeNum,
                    hwAllNDRAPrefixUsedPercent,
                    hwAllPDPrefixTotalNum,
                    hwAllPDPrefixUsedNum,
                    hwAllPDPrefixFreeNum,
                    hwAllPDPrefixConflictNum,
                    hwAllPDPrefixExcludeNum,
                    hwAllPDPrefixUsedPercent
                }
        STATUS current
        DESCRIPTION 
            "The HUAWEI IPv6 pool statistics group."
        ::= { hwIpPoolObjectGroups 24 }
 --end: added by t00189639 for amv6

    END
