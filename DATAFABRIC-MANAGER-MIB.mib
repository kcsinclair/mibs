--  ============================= --
	-- DataFabric Manager Custom MIB --
	-- ============================= --

	-- Version 4.0

	-- Copyright (c) 2007 Network Appliance, Inc.
	-- All rights reserved.

	-- This DataFabric Manager SNMP Management Information Base
	-- (Specification) embodies Network Appliance's confidential
	-- and proprietary intellectual property.  Network Appliance
	-- retains all title and ownership in the Specification,
	-- including any revisions.

	-- This Specification is supplied "AS IS," and Network Appliance
	-- makes no warranty, either express or implied, as to the use,
	-- operation, condition, or performance of the Specification.

	-- Agent support for this MIB is not available yet.

	DATAFABRIC-MANAGER-MIB DEFINITIONS ::= BEGIN

	IMPORTS
		netapp
			FROM NETWORK-APPLIANCE-MIB
		OBJECT-TYPE
			FROM RFC-1212;

	--  This MIB module uses the extended OBJECT-TYPE macro as
	--  defined in RFC-1212


	--  MIB-II (same prefix as MIB-I)


	-- textual conventions

	DisplayString ::=
		OCTET STRING
	-- This data type is used to model textual information taken
	-- from the NVT ASCII character set.  By convention, objects
	-- with this syntax are declared as having
	--
	--      SIZE (0..255)

	-- the DataFabric Manager MIB

	-- root for all objects for DataFabric Manager

	netappDataFabricManager	OBJECT IDENTIFIER ::= { netapp 3 }

	dfmSerialNumber	OBJECT-TYPE
	SYNTAX		DisplayString
	ACCESS		read-only
	STATUS		mandatory
	DESCRIPTION
			"Serial number of the DataFabric Manager installation."
	::= { netappDataFabricManager 1 }


	-- event table

	dfmEventTable	OBJECT-TYPE
	SYNTAX		SEQUENCE OF DfmEventEntry
	ACCESS		not-accessible
	STATUS		mandatory
	DESCRIPTION	
			"Table of all the events generated by the
			DataFabric Manager event service"
	::= { netappDataFabricManager 11 }

	dfmEventEntry	OBJECT-TYPE
	SYNTAX		DfmEventEntry
	ACCESS		not-accessible
	STATUS		mandatory
	DESCRIPTION	
			"Represents row corresponding to a single event."
	INDEX	{ dfmEventId }
	::= { dfmEventTable 1 }

	DfmEventEntry ::=
		SEQUENCE {
			dfmEventId
			    INTEGER,
			dfmEventSourceId
			    INTEGER,
			dfmEventSeverity
			    INTEGER,
			dfmEventTimestamp
			    INTEGER,
			dfmEventName
			    DisplayString,
			dfmEventMessage
			    DisplayString,
			dfmEventMessageDetails
			    DisplayString,
			dfmEventSourceTable
			    INTEGER,
			dfmEventSourceSerialNumber
			    DisplayString,
			dfmEventSourceProductId
			    DisplayString
		}

	dfmEventId	OBJECT-TYPE
	SYNTAX		INTEGER
	ACCESS		read-only
	STATUS		mandatory
	DESCRIPTION	
			"Identifier of the event."
	::= { dfmEventEntry 1 }

	dfmEventSourceId	OBJECT-TYPE
	SYNTAX			INTEGER
	ACCESS			read-only
	STATUS			mandatory
	DESCRIPTION	
			"Identifier of the object that is source of the event."
	::= { dfmEventEntry 2 }

	dfmEventSeverity	OBJECT-TYPE
	SYNTAX			INTEGER {
					normal(1),
					information(2),
					warning(3),
					error(4),
					critical(5),
					emergency(6)
				}
	ACCESS			read-only
	STATUS			mandatory
	DESCRIPTION	
				"Severity of the event."
	::= { dfmEventEntry 3 }

	dfmEventTimestamp	OBJECT-TYPE
	SYNTAX			INTEGER
	ACCESS			read-only
	STATUS			mandatory
	DESCRIPTION	
				"Event creation timestamp represented as the 
				 number of seconds since 00:00:00 UTC, 
				 January 1, 1970."
	::= { dfmEventEntry 4 }

	dfmEventName	OBJECT-TYPE
	SYNTAX		DisplayString
	ACCESS		read-only
	STATUS		mandatory
	DESCRIPTION	
			"Display name of the event. e.g. Volume Full."
	::= { dfmEventEntry 5 }

	dfmEventMessage	OBJECT-TYPE
	SYNTAX		DisplayString
	ACCESS		read-only
	STATUS		mandatory
	DESCRIPTION	
			"Fixed format message describing condition that caused 
			 the event."
	::= { dfmEventEntry 6 }

	dfmEventMessageDetails	OBJECT-TYPE
	SYNTAX		DisplayString
	ACCESS		read-only
	STATUS		mandatory
	DESCRIPTION	
			"More detailed message about the event if available." 
	::= { dfmEventEntry 7 }

	dfmEventSourceTable	OBJECT-TYPE
	SYNTAX			INTEGER {
					objects(1),
					quotas(2)
				}
	ACCESS			read-only
	STATUS			mandatory
	DESCRIPTION	
			"Database table in which the event source is stored.
			 Identifier of the source is unique within that database
			 table."
	::= { dfmEventEntry 8 }

	dfmEventSourceSerialNumber OBJECT-TYPE
	SYNTAX		DisplayString
	ACCESS		read-only
	STATUS		mandatory
	DESCRIPTION	
			"Product serial number of the host that caused the
			 event." 
	::= { dfmEventEntry 9 }

	dfmEventSourceProductId OBJECT-TYPE
	SYNTAX		DisplayString
	ACCESS		read-only
	STATUS		mandatory
	DESCRIPTION	
			"System Id of the host that caused the
			 event. This is mostly meaningful only for 
			 host running Data ONTAP." 
	::= { dfmEventEntry 10 }



	-- dfmObject table

	dfmObjectTable	OBJECT-TYPE
	SYNTAX		SEQUENCE OF DfmObjectEntry
	ACCESS		not-accessible
	STATUS		mandatory
	DESCRIPTION	
			"Table of objects in the DataFabric Manager database. 
			Some of these objects can be source of events generated
			by DataFabric Manager."
	::= { netappDataFabricManager 12 }

	dfmObjectEntry	OBJECT-TYPE
	SYNTAX		DfmObjectEntry
	ACCESS		not-accessible
	STATUS		mandatory
	DESCRIPTION	
			"Represents row corresponding to a single object."
	INDEX	{ dfmObjectId }
	::= { dfmObjectTable 1 }

	DfmObjectEntry ::=
		SEQUENCE {
			dfmObjectId
			    INTEGER,
			dfmObjectFullName
			    DisplayString,
			dfmObjectType
			    INTEGER,
			dfmObjectStatus
			    INTEGER,
			dfmHostFullName
			    DisplayString,
			dfmCommentFields
			    DisplayString,
			dfmPhysicalHostId
			    INTEGER,
			dfmPhysicalHostFullName
			    DisplayString
		}

	dfmObjectId	OBJECT-TYPE
	SYNTAX		INTEGER
	ACCESS		read-only
	STATUS		mandatory
	DESCRIPTION	
			"Identifier of an object in DataFabric Manager 
			database."
	::= { dfmObjectEntry 1 }

	dfmObjectFullName	OBJECT-TYPE
	SYNTAX		DisplayString
	ACCESS		read-only
	STATUS		mandatory
	DESCRIPTION	
			"Full name of the object."
	::= { dfmObjectEntry 2 }

	dfmObjectType	OBJECT-TYPE
	SYNTAX		INTEGER {
				unknown(1),
				mgmtStation(2),
				host(3),
				volume(4),
				qtree(5),
				config(6),
				user(7),
				network(8),
				lun(9),
				group(10),
				fcSwitchPort(11),
				directory(12),
				hbaPort(13),
				cmsJob(14),
				aggregate(15),
				interface(16),
				script(17),
				scriptJob(18),
				dataset(19),
				storageset(20),
				resourcePool(21),
				dpPolicy(22),
				dpSchedule(23),
				dpThrottle(24),
				ossvDirectory(25),
				schedule(26),
				reportSchedule(27),
				provPolicy(28),
				vfilerTemplate(29),
				disk(30),
				scriptSchedule(31),
				port(32),
				ifgrp(33),
				lif(34),
				storageService(35)
			}
	ACCESS		read-only
	STATUS		mandatory
	DESCRIPTION	
			"Type of the object."
	::= { dfmObjectEntry 3 }

	dfmObjectStatus	OBJECT-TYPE
	SYNTAX		INTEGER {
				unknown(1),
				unmanaged(2),
				normal(3),
				warning(4),
				error(5),
				critical(6),
				emergency(7)
			}
	ACCESS		read-only
	STATUS		mandatory
	DESCRIPTION	
			"Status of the object." 
	::= { dfmObjectEntry 4 }

	dfmHostFullName	OBJECT-TYPE
	SYNTAX		DisplayString
	ACCESS		read-only
	STATUS		mandatory
	DESCRIPTION	
			"Full name of the host where the object resides."
	::= { dfmObjectEntry 5 }

	dfmCommentFields OBJECT-TYPE
	SYNTAX		DisplayString
	ACCESS		read-only
	STATUS		mandatory
	DESCRIPTION
			"Non empty comment fields of the object."
	::= { dfmObjectEntry 6 }

	dfmPhysicalHostId OBJECT-TYPE
	SYNTAX		INTEGER
	ACCESS		read-only
	STATUS		mandatory
	DESCRIPTION
			"Identifier of the physical host object in
			DataFabric Manager database. If the event source
			corresponds to a vFiler unit or a storage object owned
			by a vFiler unit, then this will contain the hosting 
			storage system identifier. If the event source 
			corresponds to a storage system or an object owned by
			the storage system, then this will contain the storage
			system identifier."
	::= { dfmObjectEntry 7 }

	dfmPhysicalHostFullName OBJECT-TYPE
	SYNTAX		DisplayString
	ACCESS		read-only
	STATUS		mandatory
	DESCRIPTION
			"Full name of the physical host object in
			DataFabric Manager database. If the event source
			corresponds to a vFiler unit or a storage object owned
			by a vFiler unit, then this will contain the hosting 
			storage system name. If the event source 
			corresponds to a storage system or an object owned by
			the storage system, then this will contain the storage
			system name."
	::= { dfmObjectEntry 8 }

	-- =================
	-- Traps sent by DataFabric Manager
	-- =================


	-- snapshot events

	dfmEvtSnapshotSpaceOk	TRAP-TYPE
	ENTERPRISE		netappDataFabricManager
	VARIABLES	{
				dfmSerialNumber, dfmEventSourceSerialNumber,
				dfmEventId, dfmEventName, dfmEventSeverity,
				dfmEventTimestamp, dfmEventMessage, 
				dfmEventMessageDetails,
				dfmEventSourceId, dfmEventSourceTable,
				dfmObjectId, dfmObjectType, dfmObjectFullName,
				dfmObjectStatus, dfmEventSourceProductId,
				dfmHostFullName, dfmCommentFields,
				dfmPhysicalHostId, dfmPhysicalHostFullName
			}
	DESCRIPTION
		"The space utilization by a snapshot being
		 managed by DataFabric Manager is below its 'full' threshold. 
		 Variable dfmObjectId identifies the snapshot."
	::= 10001

	dfmEvtSnapshotFull	TRAP-TYPE
	ENTERPRISE		netappDataFabricManager
	VARIABLES	{
				dfmSerialNumber, dfmEventSourceSerialNumber,
				dfmEventId, dfmEventName, dfmEventSeverity,
				dfmEventTimestamp, dfmEventMessage, 
				dfmEventMessageDetails,
				dfmEventSourceId, dfmEventSourceTable,
				dfmObjectId, dfmObjectType, dfmObjectFullName,
				dfmObjectStatus, dfmEventSourceProductId,
				dfmHostFullName, dfmCommentFields,
				dfmPhysicalHostId, dfmPhysicalHostFullName
			}
	DESCRIPTION
		"The space utilization by a snapshot being managed by 
		 DataFabric Manager has crossed 'full' threshold.
		 Variable dfmObjectId identifies the snapshot."
	::= 10002

	-- volume events

	dfmEvtVolumeSpaceOk	TRAP-TYPE
	ENTERPRISE		netappDataFabricManager
	VARIABLES	{
				dfmSerialNumber, dfmEventSourceSerialNumber,
				dfmEventId, dfmEventName, dfmEventSeverity,
				dfmEventTimestamp, dfmEventMessage, 
				dfmEventMessageDetails,
				dfmEventSourceId, dfmEventSourceTable,
				dfmObjectId, dfmObjectType, dfmObjectFullName,
				dfmObjectStatus, dfmEventSourceProductId,
				dfmHostFullName, dfmCommentFields,
				dfmPhysicalHostId, dfmPhysicalHostFullName
			}
	DESCRIPTION
		"The space utilization on the volume being
		 managed by DataFabric Manager is below its 
		 'almostFull' threshold. Variable 
		 dfmObjectId identifies the volume."
	::= 10011

	dfmEvtVolumeAlmostFull	TRAP-TYPE
	ENTERPRISE		netappDataFabricManager
	VARIABLES	{
				dfmSerialNumber, dfmEventSourceSerialNumber,
				dfmEventId, dfmEventName, dfmEventSeverity,
				dfmEventTimestamp, dfmEventMessage, 
				dfmEventMessageDetails,
				dfmEventSourceId, dfmEventSourceTable,
				dfmObjectId, dfmObjectType, dfmObjectFullName,
				dfmObjectStatus, dfmEventSourceProductId,
				dfmHostFullName, dfmCommentFields,
				dfmPhysicalHostId, dfmPhysicalHostFullName
			}
	DESCRIPTION
		"The space utilization by a volume 
		 being managed by DataFabric Manager has crossed 
		 'almostFull' threshold. 
		 Variable dfmObjectId identifies the volume."
	::= 10012
	
	dfmEvtVolumeFull	TRAP-TYPE
	ENTERPRISE		netappDataFabricManager
	VARIABLES	{
				dfmSerialNumber, dfmEventSourceSerialNumber,
				dfmEventId, dfmEventName, dfmEventSeverity,
				dfmEventTimestamp, dfmEventMessage, 
				dfmEventMessageDetails,
				dfmEventSourceId, dfmEventSourceTable,
				dfmObjectId, dfmObjectType, dfmObjectFullName,
				dfmObjectStatus, dfmEventSourceProductId,
				dfmHostFullName, dfmCommentFields,
				dfmPhysicalHostId, dfmPhysicalHostFullName
			}
	DESCRIPTION
		"The space utilization by a volume
		 being managed by DataFabric Manager has crossed 
		 'full' threshold.
		 Variable dfmObjectId identifies the volume."
	::= 10013
	

	-- inodes events

	dfmEvtInodesUtilOk	TRAP-TYPE
	ENTERPRISE		netappDataFabricManager
	VARIABLES	{
				dfmSerialNumber, dfmEventSourceSerialNumber,
				dfmEventId, dfmEventName, dfmEventSeverity,
				dfmEventTimestamp, dfmEventMessage, 
				dfmEventMessageDetails,
				dfmEventSourceId, dfmEventSourceTable,
				dfmObjectId, dfmObjectType, dfmObjectFullName,
				dfmObjectStatus, dfmEventSourceProductId,
				dfmHostFullName, dfmCommentFields,
				dfmPhysicalHostId, dfmPhysicalHostFullName
			}
	DESCRIPTION	
		"The number of inodes used up on volume 
		 managed by DataFabric Manager, is below 
		 the 'almostFull' threshold. 
		 Variable dfmObjectId identifies the volume."
	::= 10021

	dfmEvtInodesAlmostFull	TRAP-TYPE
	ENTERPRISE		netappDataFabricManager
	VARIABLES	{
				dfmSerialNumber, dfmEventSourceSerialNumber,
				dfmEventId, dfmEventName, dfmEventSeverity,
				dfmEventTimestamp, dfmEventMessage, 
				dfmEventMessageDetails,
				dfmEventSourceId, dfmEventSourceTable,
				dfmObjectId, dfmObjectType, dfmObjectFullName,
				dfmObjectStatus, dfmEventSourceProductId,
				dfmHostFullName, dfmCommentFields,
				dfmPhysicalHostId, dfmPhysicalHostFullName
			}
	DESCRIPTION	
		"The number of inodes used up on volume 
		 managed by DataFabric Manager, has exceeded 
		 the 'almostFull' threshold. 
		 Variable dfmObjectId identifies the volume."
	::= 10022

	dfmEvtInodesFull	TRAP-TYPE
	ENTERPRISE		netappDataFabricManager
	VARIABLES	{
				dfmSerialNumber, dfmEventSourceSerialNumber,
				dfmEventId, dfmEventName, dfmEventSeverity,
				dfmEventTimestamp, dfmEventMessage, 
				dfmEventMessageDetails,
				dfmEventSourceId, dfmEventSourceTable,
				dfmObjectId, dfmObjectType, dfmObjectFullName,
				dfmObjectStatus, dfmEventSourceProductId,
				dfmHostFullName, dfmCommentFields,
				dfmPhysicalHostId, dfmPhysicalHostFullName
			}
	DESCRIPTION	
		"The number of inodes used up on volume 
		 managed by DataFabric Manager, has exceeded 
		 the 'full' threshold. 
		 Variable dfmObjectId identifies the volume."
	::= 10023



	-- management station node limit events

	dfmEvtMgmtStNodeLimitOk	TRAP-TYPE
	ENTERPRISE		netappDataFabricManager
	VARIABLES	{
				dfmSerialNumber, dfmEventSourceSerialNumber,
				dfmEventId, dfmEventName, dfmEventSeverity,
				dfmEventTimestamp, dfmEventMessage, 
				dfmEventMessageDetails,
				dfmEventSourceId, dfmEventSourceTable,
				dfmObjectId, dfmObjectType, dfmObjectFullName,
				dfmObjectStatus, dfmEventSourceProductId,
				dfmHostFullName, dfmCommentFields,
				dfmPhysicalHostId, dfmPhysicalHostFullName
			}
	DESCRIPTION	
		"The number of nodes being managed by
		 DataFabric Manager is below the node 
		 limit specified in the license key."
	::= 10031

	dfmEvtMgmtStNodeLimitNearlyReached	TRAP-TYPE
	ENTERPRISE		netappDataFabricManager
	VARIABLES	{
				dfmSerialNumber, dfmEventSourceSerialNumber,
				dfmEventId, dfmEventName, dfmEventSeverity,
				dfmEventTimestamp, dfmEventMessage, 
				dfmEventMessageDetails,
				dfmEventSourceId, dfmEventSourceTable,
				dfmObjectId, dfmObjectType, dfmObjectFullName,
				dfmObjectStatus, dfmEventSourceProductId,
				dfmHostFullName, dfmCommentFields,
				dfmPhysicalHostId, dfmPhysicalHostFullName
			}
	DESCRIPTION	
		"The number of nodes being managed by
		 DataFabric Manager has nearly reached 
		 the node limit specified in the 
		 license key."
	::= 10032

	dfmEvtMgmtStNodeLimitReached	TRAP-TYPE
	ENTERPRISE		netappDataFabricManager
	VARIABLES	{
				dfmSerialNumber, dfmEventSourceSerialNumber,
				dfmEventId, dfmEventName, dfmEventSeverity,
				dfmEventTimestamp, dfmEventMessage, 
				dfmEventMessageDetails,
				dfmEventSourceId, dfmEventSourceTable,
				dfmObjectId, dfmObjectType, dfmObjectFullName,
				dfmObjectStatus, dfmEventSourceProductId,
				dfmHostFullName, dfmCommentFields,
				dfmPhysicalHostId, dfmPhysicalHostFullName
			}
	DESCRIPTION	
		"The number of nodes being managed by
		 DataFabric Manager has reached the node 
		 limit specified in the license key."
	::= 10033

	-- perf advisor free space events

	dfmEvtMgmtStPerfAdvisorFreeSpaceOk	TRAP-TYPE
	ENTERPRISE			netappDataFabricManager
	VARIABLES	{
				dfmSerialNumber, dfmEventSourceSerialNumber,
				dfmEventId, dfmEventName, dfmEventSeverity,
				dfmEventTimestamp, dfmEventMessage, 
				dfmEventMessageDetails,
				dfmEventSourceId, dfmEventSourceTable,
				dfmObjectId, dfmObjectType, dfmObjectFullName,
				dfmObjectStatus, dfmEventSourceProductId,
				dfmHostFullName, dfmCommentFields,
				dfmPhysicalHostId, dfmPhysicalHostFullName
			}
	DESCRIPTION	
		"Performance Advisor has sufficient free disk space."
	::= 10034	

	dfmEvtMgmtStPerfAdvisorNotEnoughFreeSpace	TRAP-TYPE
	ENTERPRISE			netappDataFabricManager
	VARIABLES	{
				dfmSerialNumber, dfmEventSourceSerialNumber,
				dfmEventId, dfmEventName, dfmEventSeverity,
				dfmEventTimestamp, dfmEventMessage, 
				dfmEventMessageDetails,
				dfmEventSourceId, dfmEventSourceTable,
				dfmObjectId, dfmObjectType, dfmObjectFullName,
				dfmObjectStatus, dfmEventSourceProductId,
				dfmHostFullName, dfmCommentFields,
				dfmPhysicalHostId, dfmPhysicalHostFullName
			}
	DESCRIPTION	
		"Performance Advisor has insufficient free 
		 disk space for the DataFabric Manager. 
		 All Performance Advisor activity has stopped."
	
	::= 10035


	-- volume availability events

	dfmEvtVolumeOnline	TRAP-TYPE
	ENTERPRISE		netappDataFabricManager
	VARIABLES	{
				dfmSerialNumber, dfmEventSourceSerialNumber,
				dfmEventId, dfmEventName, dfmEventSeverity,
				dfmEventTimestamp, dfmEventMessage, 
				dfmEventMessageDetails,
				dfmEventSourceId, dfmEventSourceTable,
				dfmObjectId, dfmObjectType, dfmObjectFullName,
				dfmObjectStatus, dfmEventSourceProductId,
				dfmHostFullName, dfmCommentFields,
				dfmPhysicalHostId, dfmPhysicalHostFullName
			}
	DESCRIPTION	
		"The volume is online.
		 Variable dfmObjectId identifies the volume."
	::= 10036


	dfmEvtVolumeOfflineOrDestroyed	TRAP-TYPE
	ENTERPRISE		netappDataFabricManager
	VARIABLES	{
				dfmSerialNumber, dfmEventSourceSerialNumber,
				dfmEventId, dfmEventName, dfmEventSeverity,
				dfmEventTimestamp, dfmEventMessage, 
				dfmEventMessageDetails,
				dfmEventSourceId, dfmEventSourceTable,
				dfmObjectId, dfmObjectType, dfmObjectFullName,
				dfmObjectStatus, dfmEventSourceProductId,
				dfmHostFullName, dfmCommentFields,
				dfmPhysicalHostId, dfmPhysicalHostFullName
			}
	DESCRIPTION	
		"The volume is offline or destroyed.
		 Variable dfmObjectId identifies the volume."
	::= 10037

	dfmEvtVolumeOffline	TRAP-TYPE
	ENTERPRISE		netappDataFabricManager
	VARIABLES	{
				dfmSerialNumber, dfmEventSourceSerialNumber,
				dfmEventId, dfmEventName, dfmEventSeverity,
				dfmEventTimestamp, dfmEventMessage, 
				dfmEventMessageDetails,
				dfmEventSourceId, dfmEventSourceTable,
				dfmObjectId, dfmObjectType, dfmObjectFullName,
				dfmObjectStatus, dfmEventSourceProductId,
				dfmHostFullName, dfmCommentFields,
				dfmPhysicalHostId, dfmPhysicalHostFullName
			}
	DESCRIPTION	
		"The volume is offline.
		 Variable dfmObjectId identifies the volume."
	::= 10038

	dfmEvtVolumeDestroyed	TRAP-TYPE
	ENTERPRISE		netappDataFabricManager
	VARIABLES	{
				dfmSerialNumber, dfmEventSourceSerialNumber,
				dfmEventId, dfmEventName, dfmEventSeverity,
				dfmEventTimestamp, dfmEventMessage, 
				dfmEventMessageDetails,
				dfmEventSourceId, dfmEventSourceTable,
				dfmObjectId, dfmObjectType, dfmObjectFullName,
				dfmObjectStatus, dfmEventSourceProductId,
				dfmHostFullName, dfmCommentFields,
				dfmPhysicalHostId, dfmPhysicalHostFullName
			}
	DESCRIPTION	
		"The volume has been destroyed.
		 Variable dfmObjectId identifies the volume."
	::= 10039

	dfmEvtVolumeRestricted	TRAP-TYPE
	ENTERPRISE		netappDataFabricManager
	VARIABLES	{
				dfmSerialNumber, dfmEventSourceSerialNumber,
				dfmEventId, dfmEventName, dfmEventSeverity,
				dfmEventTimestamp, dfmEventMessage, 
				dfmEventMessageDetails,
				dfmEventSourceId, dfmEventSourceTable,
				dfmObjectId, dfmObjectType, dfmObjectFullName,
				dfmObjectStatus, dfmEventSourceProductId,
				dfmHostFullName, dfmCommentFields,
				dfmPhysicalHostId, dfmPhysicalHostFullName
			}
	DESCRIPTION	
		"The volume has been restricted.
		 Variable dfmObjectId identifies the volume."
	::= 10040



	-- management station license expiration events

	dfmEvtMgmtStLicenseNotExpired	TRAP-TYPE
	ENTERPRISE			netappDataFabricManager
	VARIABLES	{
				dfmSerialNumber, dfmEventSourceSerialNumber,
				dfmEventId, dfmEventName, dfmEventSeverity,
				dfmEventTimestamp, dfmEventMessage, 
				dfmEventMessageDetails,
				dfmEventSourceId, dfmEventSourceTable,
				dfmObjectId, dfmObjectType, dfmObjectFullName,
				dfmObjectStatus, dfmEventSourceProductId,
				dfmHostFullName, dfmCommentFields,
				dfmPhysicalHostId, dfmPhysicalHostFullName
			}
	DESCRIPTION	
		"The the license on DataFabric Manager management station
		 has not expired."
	::= 10041

	dfmEvtMgmtStLicenseNearlyExpired	TRAP-TYPE
	ENTERPRISE				netappDataFabricManager
	VARIABLES	{
				dfmSerialNumber, dfmEventSourceSerialNumber,
				dfmEventId, dfmEventName, dfmEventSeverity,
				dfmEventTimestamp, dfmEventMessage, 
				dfmEventMessageDetails,
				dfmEventSourceId, dfmEventSourceTable,
				dfmObjectId, dfmObjectType, dfmObjectFullName,
				dfmObjectStatus, dfmEventSourceProductId,
				dfmHostFullName, dfmCommentFields,
				dfmPhysicalHostId, dfmPhysicalHostFullName
			}
	DESCRIPTION	
		"The the license on DataFabric Manager management station
		 is close to getting expired."
	::= 10042

	dfmEvtMgmtStLicenseExpired	TRAP-TYPE
	ENTERPRISE			netappDataFabricManager
	VARIABLES	{
				dfmSerialNumber, dfmEventSourceSerialNumber,
				dfmEventId, dfmEventName, dfmEventSeverity,
				dfmEventTimestamp, dfmEventMessage, 
				dfmEventMessageDetails,
				dfmEventSourceId, dfmEventSourceTable,
				dfmObjectId, dfmObjectType, dfmObjectFullName,
				dfmObjectStatus, dfmEventSourceProductId,
				dfmHostFullName, dfmCommentFields,
				dfmPhysicalHostId, dfmPhysicalHostFullName
			}
	DESCRIPTION	
		"The the license on DataFabric Manager management station
		 has expired."
	::= 10043



	-- service availability

	dfmEvtMgmtStSchedulerUp		TRAP-TYPE
	ENTERPRISE			netappDataFabricManager
	VARIABLES	{
				dfmSerialNumber, dfmEventSourceSerialNumber,
				dfmEventId, dfmEventName, dfmEventSeverity,
				dfmEventTimestamp, dfmEventMessage, 
				dfmEventMessageDetails,
				dfmEventSourceId, dfmEventSourceTable,
				dfmObjectId, dfmObjectType, dfmObjectFullName,
				dfmObjectStatus, dfmEventSourceProductId,
				dfmHostFullName, dfmCommentFields,
				dfmPhysicalHostId, dfmPhysicalHostFullName
			}
	DESCRIPTION	
		"DataFabric Manager scheduler is available. 
		 The dfmEventId variable contains
		 a dummy event identifier. The dfmObjectId 
		 is identifier of the management station object."
	::= 10049

	dfmEvtMgmtStSchedulerDown	TRAP-TYPE
	ENTERPRISE			netappDataFabricManager
	VARIABLES	{
				dfmSerialNumber, dfmEventSourceSerialNumber,
				dfmEventId, dfmEventName, dfmEventSeverity,
				dfmEventTimestamp, dfmEventMessage, 
				dfmEventMessageDetails,
				dfmEventSourceId, dfmEventSourceTable,
				dfmObjectId, dfmObjectType, dfmObjectFullName,
				dfmObjectStatus, dfmEventSourceProductId,
				dfmHostFullName, dfmCommentFields,
				dfmPhysicalHostId, dfmPhysicalHostFullName
			}
	DESCRIPTION	
		"DataFabric Manager scheduler is no longer 
		 available and therefore DataFabric Manager has 
		 stopped monitoring. The dfmEventId variable contains a dummy 
		 event identifier. The dfmObjectId is identifier of the 
		 management station object."
	::= 10050

	dfmEvtMgmtStDatabaseUp	TRAP-TYPE
	ENTERPRISE		netappDataFabricManager
	VARIABLES	{
				dfmSerialNumber, dfmEventSourceSerialNumber,
				dfmEventId, dfmEventName, dfmEventSeverity,
				dfmEventTimestamp, dfmEventMessage, 
				dfmEventMessageDetails,
				dfmEventSourceId, dfmEventSourceTable,
				dfmObjectId, dfmObjectType, dfmObjectFullName,
				dfmObjectStatus, dfmEventSourceProductId,
				dfmHostFullName, dfmCommentFields,
				dfmPhysicalHostId, dfmPhysicalHostFullName
			}
	DESCRIPTION	
		"DataFabric Manager database is available. 
		 The dfmEventId variable contains
		 a dummy event identifier. The dfmObjectId 
		 is identifier of the management station object."
	::= 10051

	dfmEvtMgmtStDatabaseDown	TRAP-TYPE
	ENTERPRISE			netappDataFabricManager
	VARIABLES	{
				dfmSerialNumber, dfmEventSourceSerialNumber,
				dfmEventId, dfmEventName, dfmEventSeverity,
				dfmEventTimestamp, dfmEventMessage, 
				dfmEventMessageDetails,
				dfmEventSourceId, dfmEventSourceTable,
				dfmObjectId, dfmObjectType, dfmObjectFullName,
				dfmObjectStatus, dfmEventSourceProductId,
				dfmHostFullName, dfmCommentFields,
				dfmPhysicalHostId, dfmPhysicalHostFullName
			}
	DESCRIPTION	
		"DataFabric Manager database is no longer 
		 available and therefore DataFabric Manager has 
		 stopped monitoring. The dfmEventId variable contains a dummy 
		 event identifier. The dfmObjectId is identifier of the 
		 management station object."
	::= 10052

	dfmEvtMgmtStMonitorUp	TRAP-TYPE
	ENTERPRISE		netappDataFabricManager
	VARIABLES	{
				dfmSerialNumber, dfmEventSourceSerialNumber,
				dfmEventId, dfmEventName, dfmEventSeverity,
				dfmEventTimestamp, dfmEventMessage, 
				dfmEventMessageDetails,
				dfmEventSourceId, dfmEventSourceTable,
				dfmObjectId, dfmObjectType, dfmObjectFullName,
				dfmObjectStatus, dfmEventSourceProductId,
				dfmHostFullName, dfmCommentFields,
				dfmPhysicalHostId, dfmPhysicalHostFullName
			}
	DESCRIPTION	
		"DataFabric Manager monitor is available. 
		 The dfmEventId variable contains
		 a dummy event identifier. The dfmObjectId 
		 is identifier of the management station object."
	::= 10053

	dfmEvtMgmtStMonitorDown	TRAP-TYPE
	ENTERPRISE			netappDataFabricManager
	VARIABLES	{
				dfmSerialNumber, dfmEventSourceSerialNumber,
				dfmEventId, dfmEventName, dfmEventSeverity,
				dfmEventTimestamp, dfmEventMessage, 
				dfmEventMessageDetails,
				dfmEventSourceId, dfmEventSourceTable,
				dfmObjectId, dfmObjectType, dfmObjectFullName,
				dfmObjectStatus, dfmEventSourceProductId,
				dfmHostFullName, dfmCommentFields,
				dfmPhysicalHostId, dfmPhysicalHostFullName
			}
	DESCRIPTION	
		"DataFabric Manager monitor is no longer 
		 available and therefore DataFabric Manager has 
		 stopped monitoring. The dfmEventId variable contains a dummy 
		 event identifier. The dfmObjectId is identifier of the 
		 management station object."
	::= 10054

	dfmEvtMgmtStEventdUp	TRAP-TYPE
	ENTERPRISE		netappDataFabricManager
	VARIABLES	{
				dfmSerialNumber, dfmEventSourceSerialNumber,
				dfmEventId, dfmEventName, dfmEventSeverity,
				dfmEventTimestamp, dfmEventMessage, 
				dfmEventMessageDetails,
				dfmEventSourceId, dfmEventSourceTable,
				dfmObjectId, dfmObjectType, dfmObjectFullName,
				dfmObjectStatus, dfmEventSourceProductId,
				dfmHostFullName, dfmCommentFields,
				dfmPhysicalHostId, dfmPhysicalHostFullName
			}
	DESCRIPTION	
		"DataFabric Manager eventd is available. 
		 The dfmEventId variable contains
		 a dummy event identifier. The dfmObjectId 
		 is identifier of the management station object."
	::= 10055

	dfmEvtMgmtStEventdDown	TRAP-TYPE
	ENTERPRISE			netappDataFabricManager
	VARIABLES	{
				dfmSerialNumber, dfmEventSourceSerialNumber,
				dfmEventId, dfmEventName, dfmEventSeverity,
				dfmEventTimestamp, dfmEventMessage, 
				dfmEventMessageDetails,
				dfmEventSourceId, dfmEventSourceTable,
				dfmObjectId, dfmObjectType, dfmObjectFullName,
				dfmObjectStatus, dfmEventSourceProductId,
				dfmHostFullName, dfmCommentFields,
				dfmPhysicalHostId, dfmPhysicalHostFullName
			}
	DESCRIPTION	
		"DataFabric Manager eventd is no longer 
		 available and therefore DataFabric Manager has 
		 stopped processing events. The dfmEventId variable contains
		 a dummy event identifier. The dfmObjectId is identifier of
		 the management station object."
	::= 10056

	dfmEvtMgmtStWatchdogUp	TRAP-TYPE
	ENTERPRISE		netappDataFabricManager
	VARIABLES	{
				dfmSerialNumber, dfmEventSourceSerialNumber,
				dfmEventId, dfmEventName, dfmEventSeverity,
				dfmEventTimestamp, dfmEventMessage, 
				dfmEventMessageDetails,
				dfmEventSourceId, dfmEventSourceTable,
				dfmObjectId, dfmObjectType, dfmObjectFullName,
				dfmObjectStatus, dfmEventSourceProductId,
				dfmHostFullName, dfmCommentFields,
				dfmPhysicalHostId, dfmPhysicalHostFullName
			}
	DESCRIPTION	
		"DataFabric Manager watchdog is available. 
		 The dfmEventId variable contains
		 a dummy event identifier. The dfmObjectId 
		 is identifier of the management station object."
	::= 10057

	dfmEvtMgmtStWatchdogDown	TRAP-TYPE
	ENTERPRISE			netappDataFabricManager
	VARIABLES	{
				dfmSerialNumber, dfmEventSourceSerialNumber,
				dfmEventId, dfmEventName, dfmEventSeverity,
				dfmEventTimestamp, dfmEventMessage, 
				dfmEventMessageDetails,
				dfmEventSourceId, dfmEventSourceTable,
				dfmObjectId, dfmObjectType, dfmObjectFullName,
				dfmObjectStatus, dfmEventSourceProductId,
				dfmHostFullName, dfmCommentFields,
				dfmPhysicalHostId, dfmPhysicalHostFullName
			}
	DESCRIPTION	
		"DataFabric Manager watchdog is no longer available.
		 The dfmEventId variable contains a dummy event identifier.
		 The dfmObjectId is identifier of the management station
		 object."
	::= 10058

	dfmEvtMgmtStServerUp	TRAP-TYPE
	ENTERPRISE		netappDataFabricManager
	VARIABLES	{
				dfmSerialNumber, dfmEventSourceSerialNumber,
				dfmEventId, dfmEventName, dfmEventSeverity,
				dfmEventTimestamp, dfmEventMessage, 
				dfmEventMessageDetails,
				dfmEventSourceId, dfmEventSourceTable,
				dfmObjectId, dfmObjectType, dfmObjectFullName,
				dfmObjectStatus, dfmEventSourceProductId,
				dfmHostFullName, dfmCommentFields,
				dfmPhysicalHostId, dfmPhysicalHostFullName
			}
	DESCRIPTION	
		"DataFabric Manager server is available. 
		 The dfmEventId variable contains
		 a dummy event identifier. The dfmObjectId 
		 is identifier of the management station object."
	::= 10059

	dfmEvtMgmtStServerDown	TRAP-TYPE
	ENTERPRISE			netappDataFabricManager
	VARIABLES	{
				dfmSerialNumber, dfmEventSourceSerialNumber,
				dfmEventId, dfmEventName, dfmEventSeverity,
				dfmEventTimestamp, dfmEventMessage, 
				dfmEventMessageDetails,
				dfmEventSourceId, dfmEventSourceTable,
				dfmObjectId, dfmObjectType, dfmObjectFullName,
				dfmObjectStatus, dfmEventSourceProductId,
				dfmHostFullName, dfmCommentFields,
				dfmPhysicalHostId, dfmPhysicalHostFullName
			}
	DESCRIPTION	
		"DataFabric Manager server is no longer available.
		 The dfmEventId variable contains a dummy event identifier.
		 The dfmObjectId is identifier of the management station
		 object."
	::= 10060

	-- disk events 

	dfmEvtDisksSparesAvailable	TRAP-TYPE
	ENTERPRISE			netappDataFabricManager
	VARIABLES	{
				dfmSerialNumber, dfmEventSourceSerialNumber,
				dfmEventId, dfmEventName, dfmEventSeverity,
				dfmEventTimestamp, dfmEventMessage, 
				dfmEventMessageDetails,
				dfmEventSourceId, dfmEventSourceTable,
				dfmObjectId, dfmObjectType, dfmObjectFullName,
				dfmObjectStatus, dfmEventSourceProductId,
				dfmHostFullName, dfmCommentFields,
				dfmPhysicalHostId, dfmPhysicalHostFullName
			}
	DESCRIPTION
		"There are spare disks available on the host being monitored 
		 by DataFabric Manager. The dfmObjectId is that of the host."
	::= 10061


	dfmEvtDisksNoSpares	TRAP-TYPE
	ENTERPRISE		netappDataFabricManager
	VARIABLES	{
				dfmSerialNumber, dfmEventSourceSerialNumber,
				dfmEventId, dfmEventName, dfmEventSeverity,
				dfmEventTimestamp, dfmEventMessage, 
				dfmEventMessageDetails,
				dfmEventSourceId, dfmEventSourceTable,
				dfmObjectId, dfmObjectType, dfmObjectFullName,
				dfmObjectStatus, dfmEventSourceProductId,
				dfmHostFullName, dfmCommentFields,
				dfmPhysicalHostId, dfmPhysicalHostFullName
			}
	DESCRIPTION
		"There are no spare disks on the host being 
		 monitored by DataFabric Manager. 
		 The dfmObjectId is that of the host."
	::= 10062


	dfmEvtDisksNoneFailed		TRAP-TYPE
	ENTERPRISE			netappDataFabricManager
	VARIABLES	{
				dfmSerialNumber, dfmEventSourceSerialNumber,
				dfmEventId, dfmEventName, dfmEventSeverity,
				dfmEventTimestamp, dfmEventMessage, 
				dfmEventMessageDetails,
				dfmEventSourceId, dfmEventSourceTable,
				dfmObjectId, dfmObjectType, dfmObjectFullName,
				dfmObjectStatus, dfmEventSourceProductId,
				dfmHostFullName, dfmCommentFields,
				dfmPhysicalHostId, dfmPhysicalHostFullName
			}
	DESCRIPTION
		"There are no failed disks on the host being 
		 monitored by DataFabric Manager." 
	::= 10071


	dfmEvtDisksSomeFailed	TRAP-TYPE
	ENTERPRISE		netappDataFabricManager
	VARIABLES	{
				dfmSerialNumber, dfmEventSourceSerialNumber,
				dfmEventId, dfmEventName, dfmEventSeverity,
				dfmEventTimestamp, dfmEventMessage, 
				dfmEventMessageDetails,
				dfmEventSourceId, dfmEventSourceTable,
				dfmObjectId, dfmObjectType, dfmObjectFullName,
				dfmObjectStatus, dfmEventSourceProductId,
				dfmHostFullName, dfmCommentFields,
				dfmPhysicalHostId, dfmPhysicalHostFullName
			}
	DESCRIPTION
		"There are some failed disks on the host being monitored 
		 by DataFabric Manager."
	::= 10072


	dfmEvtDisksReconstructNone		TRAP-TYPE
	ENTERPRISE		netappDataFabricManager
	VARIABLES	{
				dfmSerialNumber, dfmEventSourceSerialNumber,
				dfmEventId, dfmEventName, dfmEventSeverity,
				dfmEventTimestamp, dfmEventMessage, 
				dfmEventMessageDetails,
				dfmEventSourceId, dfmEventSourceTable,
				dfmObjectId, dfmObjectType, dfmObjectFullName,
				dfmObjectStatus, dfmEventSourceProductId,
				dfmHostFullName, dfmCommentFields,
				dfmPhysicalHostId, dfmPhysicalHostFullName
			}
	DESCRIPTION
		"No disks are reconstructing."
	::= 10081


	dfmEvtDisksReconstructSome		TRAP-TYPE
	ENTERPRISE		netappDataFabricManager
	VARIABLES	{
				dfmSerialNumber, dfmEventSourceSerialNumber,
				dfmEventId, dfmEventName, dfmEventSeverity,
				dfmEventTimestamp, dfmEventMessage, 
				dfmEventMessageDetails,
				dfmEventSourceId, dfmEventSourceTable,
				dfmObjectId, dfmObjectType, dfmObjectFullName,
				dfmObjectStatus, dfmEventSourceProductId,
				dfmHostFullName, dfmCommentFields,
				dfmPhysicalHostId, dfmPhysicalHostFullName
			}
	DESCRIPTION
		"There are some disks that are reconstructing."
	::= 10082


	-- host events

	dfmEvtHostUp		TRAP-TYPE
	ENTERPRISE		netappDataFabricManager
	VARIABLES	{
				dfmSerialNumber, dfmEventSourceSerialNumber,
				dfmEventId, dfmEventName, dfmEventSeverity,
				dfmEventTimestamp, dfmEventMessage, 
				dfmEventMessageDetails,
				dfmEventSourceId, dfmEventSourceTable,
				dfmObjectId, dfmObjectType, dfmObjectFullName,
				dfmObjectStatus, dfmEventSourceProductId,
				dfmHostFullName, dfmCommentFields,
				dfmPhysicalHostId, dfmPhysicalHostFullName
			}
	DESCRIPTION
		"The host managed by DataFabric Manager is up."
	::= 10091


	dfmEvtHostDown		TRAP-TYPE
	ENTERPRISE		netappDataFabricManager
	VARIABLES	{
				dfmSerialNumber, dfmEventSourceSerialNumber,
				dfmEventId, dfmEventName, dfmEventSeverity,
				dfmEventTimestamp, dfmEventMessage, 
				dfmEventMessageDetails,
				dfmEventSourceId, dfmEventSourceTable,
				dfmObjectId, dfmObjectType, dfmObjectFullName,
				dfmObjectStatus, dfmEventSourceProductId,
				dfmHostFullName, dfmCommentFields,
				dfmPhysicalHostId, dfmPhysicalHostFullName
			}
	DESCRIPTION
		"The host managed by DataFabric Manager is down."
	::= 10092


	dfmEvtHostReachable	TRAP-TYPE
	ENTERPRISE		netappDataFabricManager
	VARIABLES	{
				dfmSerialNumber, dfmEventSourceSerialNumber,
				dfmEventId, dfmEventName, dfmEventSeverity,
				dfmEventTimestamp, dfmEventMessage, 
				dfmEventMessageDetails,
				dfmEventSourceId, dfmEventSourceTable,
				dfmObjectId, dfmObjectType, dfmObjectFullName,
				dfmObjectStatus, dfmEventSourceProductId,
				dfmHostFullName, dfmCommentFields
			}
	DESCRIPTION
		"The host managed by DataFabric Manager is reachable."
	::= 10093
	

	dfmEvtHostUnreachable	TRAP-TYPE
	ENTERPRISE		netappDataFabricManager
	VARIABLES	{
				dfmSerialNumber, dfmEventSourceSerialNumber,
				dfmEventId, dfmEventName, dfmEventSeverity,
				dfmEventTimestamp, dfmEventMessage, 
				dfmEventMessageDetails,
				dfmEventSourceId, dfmEventSourceTable,
				dfmObjectId, dfmObjectType, dfmObjectFullName,
				dfmObjectStatus, dfmEventSourceProductId,
				dfmHostFullName, dfmCommentFields
			}
	DESCRIPTION
		"The host managed by DataFabric Manager is not reachable."
	::= 10094

	
	-- qtree events

	dfmEvtQtreeSpaceOk	TRAP-TYPE
	ENTERPRISE		netappDataFabricManager
	VARIABLES	{
				dfmSerialNumber, dfmEventSourceSerialNumber,
				dfmEventId, dfmEventName, dfmEventSeverity,
				dfmEventTimestamp, dfmEventMessage, 
				dfmEventMessageDetails,
				dfmEventSourceId, dfmEventSourceTable,
				dfmObjectId, dfmObjectType, dfmObjectFullName,
				dfmObjectStatus, dfmEventSourceProductId,
				dfmHostFullName, dfmCommentFields,
				dfmPhysicalHostId, dfmPhysicalHostFullName
			}
	DESCRIPTION
		"The qtree monitored by DataFabric Manager has not reached 
		 'almostFull' threshold."
	::= 10101


	dfmEvtQtreeAlmostFull	TRAP-TYPE
	ENTERPRISE		netappDataFabricManager
	VARIABLES	{
				dfmSerialNumber, dfmEventSourceSerialNumber,
				dfmEventId, dfmEventName, dfmEventSeverity,
				dfmEventTimestamp, dfmEventMessage, 
				dfmEventMessageDetails,
				dfmEventSourceId, dfmEventSourceTable,
				dfmObjectId, dfmObjectType, dfmObjectFullName,
				dfmObjectStatus, dfmEventSourceProductId,
				dfmHostFullName, dfmCommentFields,
				dfmPhysicalHostId, dfmPhysicalHostFullName
			}
	DESCRIPTION
		"The qtree monitored by DataFabric Manager has reached 
		 'almostFull' threshold."
	::= 10102


	dfmEvtQtreeFull		TRAP-TYPE
	ENTERPRISE		netappDataFabricManager
	VARIABLES	{
				dfmSerialNumber, dfmEventSourceSerialNumber,
				dfmEventId, dfmEventName, dfmEventSeverity,
				dfmEventTimestamp, dfmEventMessage, 
				dfmEventMessageDetails,
				dfmEventSourceId, dfmEventSourceTable,
				dfmObjectId, dfmObjectType, dfmObjectFullName,
				dfmObjectStatus, dfmEventSourceProductId,
				dfmHostFullName, dfmCommentFields,
				dfmPhysicalHostId, dfmPhysicalHostFullName
			}
	DESCRIPTION
		"The qtree monitored by DataFabric Manager 
		 has reached 'full' threshold."
	::= 10103

	dfmEvtQtreeFilesOk	TRAP-TYPE
	ENTERPRISE		netappDataFabricManager
	VARIABLES	{
				dfmSerialNumber, dfmEventSourceSerialNumber,
				dfmEventId, dfmEventName, dfmEventSeverity,
				dfmEventTimestamp, dfmEventMessage, 
				dfmEventMessageDetails,
				dfmEventSourceId, dfmEventSourceTable,
				dfmObjectId, dfmObjectType, dfmObjectFullName,
				dfmObjectStatus, dfmEventSourceProductId,
				dfmHostFullName, dfmCommentFields,
				dfmPhysicalHostId, dfmPhysicalHostFullName
			}
	DESCRIPTION
		"The qtree files count monitored by DataFabric Manager has 
		not reached 'almostFull' threshold."
	::= 10104


	dfmEvtQtreeFilesAlmostFull	TRAP-TYPE
	ENTERPRISE		netappDataFabricManager
	VARIABLES	{
				dfmSerialNumber, dfmEventSourceSerialNumber,
				dfmEventId, dfmEventName, dfmEventSeverity,
				dfmEventTimestamp, dfmEventMessage, 
				dfmEventMessageDetails,
				dfmEventSourceId, dfmEventSourceTable,
				dfmObjectId, dfmObjectType, dfmObjectFullName,
				dfmObjectStatus, dfmEventSourceProductId,
				dfmHostFullName, dfmCommentFields,
				dfmPhysicalHostId, dfmPhysicalHostFullName
			}
	DESCRIPTION
		"The qtree files count monitored by DataFabric Manager has reached 
		 'almostFull' threshold."
	::= 10105


	dfmEvtQtreeFilesFull		TRAP-TYPE
	ENTERPRISE		netappDataFabricManager
	VARIABLES	{
				dfmSerialNumber, dfmEventSourceSerialNumber,
				dfmEventId, dfmEventName, dfmEventSeverity,
				dfmEventTimestamp, dfmEventMessage, 
				dfmEventMessageDetails,
				dfmEventSourceId, dfmEventSourceTable,
				dfmObjectId, dfmObjectType, dfmObjectFullName,
				dfmObjectStatus, dfmEventSourceProductId,
				dfmHostFullName, dfmCommentFields,
				dfmPhysicalHostId, dfmPhysicalHostFullName
			}
	DESCRIPTION
		"The qtree files count monitored by DataFabric Manager 
		 has reached 'full' threshold."
	::= 10106

	-- cpu utilization events

	dfmEvtCpuUtilOk		TRAP-TYPE
	ENTERPRISE		netappDataFabricManager
	VARIABLES	{
				dfmSerialNumber, dfmEventSourceSerialNumber,
				dfmEventId, dfmEventName, dfmEventSeverity,
				dfmEventTimestamp, dfmEventMessage, 
				dfmEventMessageDetails,
				dfmEventSourceId, dfmEventSourceTable,
				dfmObjectId, dfmObjectType, dfmObjectFullName,
				dfmObjectStatus, dfmEventSourceProductId,
				dfmHostFullName, dfmCommentFields,
				dfmPhysicalHostId, dfmPhysicalHostFullName
			}
	DESCRIPTION
		"The CPU utilization on the host being 
		 monitored by DataFabric Manager was
		 below the 'tooBusy' threshold."
	::= 10111


	dfmEvtCpuTooBusy	TRAP-TYPE
	ENTERPRISE		netappDataFabricManager
	VARIABLES	{
				dfmSerialNumber, dfmEventSourceSerialNumber,
				dfmEventId, dfmEventName, dfmEventSeverity,
				dfmEventTimestamp, dfmEventMessage, 
				dfmEventMessageDetails,
				dfmEventSourceId, dfmEventSourceTable,
				dfmObjectId, dfmObjectType, dfmObjectFullName,
				dfmObjectStatus, dfmEventSourceProductId,
				dfmHostFullName, dfmCommentFields,
				dfmPhysicalHostId, dfmPhysicalHostFullName
			}
	DESCRIPTION
		"The CPU utilization on the host being 
		 monitored by DataFabric Manager, 
		 exceeded the 'tooBusy' threshold for some period of time. "
	::= 10112


	-- fan events

	dfmEvtFansNormal	TRAP-TYPE
	ENTERPRISE		netappDataFabricManager
	VARIABLES	{
				dfmSerialNumber, dfmEventSourceSerialNumber,
				dfmEventId, dfmEventName, dfmEventSeverity,
				dfmEventTimestamp, dfmEventMessage, 
				dfmEventMessageDetails,
				dfmEventSourceId, dfmEventSourceTable,
				dfmObjectId, dfmObjectType, dfmObjectFullName,
				dfmObjectStatus, dfmEventSourceProductId,
				dfmHostFullName, dfmCommentFields,
				dfmPhysicalHostId, dfmPhysicalHostFullName
			}
	DESCRIPTION
		"The fans on the monitored host are functioning normally."
	::= 10121


	dfmEvtFansOneFailed	TRAP-TYPE
	ENTERPRISE		netappDataFabricManager
	VARIABLES	{
				dfmSerialNumber, dfmEventSourceSerialNumber,
				dfmEventId, dfmEventName, dfmEventSeverity,
				dfmEventTimestamp, dfmEventMessage, 
				dfmEventMessageDetails,
				dfmEventSourceId, dfmEventSourceTable,
				dfmObjectId, dfmObjectType, dfmObjectFullName,
				dfmObjectStatus, dfmEventSourceProductId,
				dfmHostFullName, dfmCommentFields,
				dfmPhysicalHostId, dfmPhysicalHostFullName
			}
	DESCRIPTION
		"There is one fan failed on the host being 
		 monitored by DataFabric Manager."
	::= 10122


	dfmEvtFansManyFailed	TRAP-TYPE
	ENTERPRISE		netappDataFabricManager
	VARIABLES	{
				dfmSerialNumber, dfmEventSourceSerialNumber,
				dfmEventId, dfmEventName, dfmEventSeverity,
				dfmEventTimestamp, dfmEventMessage, 
				dfmEventMessageDetails,
				dfmEventSourceId, dfmEventSourceTable,
				dfmObjectId, dfmObjectType, dfmObjectFullName,
				dfmObjectStatus, dfmEventSourceProductId,
				dfmHostFullName, dfmCommentFields,
				dfmPhysicalHostId, dfmPhysicalHostFullName
			}
	DESCRIPTION
		"There are many fans failed on the host 
		 being monitored by DataFabric Manager."
	::= 10123


	-- power supply events

	dfmEvtPowerSupplyOk	TRAP-TYPE
	ENTERPRISE		netappDataFabricManager
	VARIABLES	{
				dfmSerialNumber, dfmEventSourceSerialNumber,
				dfmEventId, dfmEventName, dfmEventSeverity,
				dfmEventTimestamp, dfmEventMessage, 
				dfmEventMessageDetails,
				dfmEventSourceId, dfmEventSourceTable,
				dfmObjectId, dfmObjectType, dfmObjectFullName,
				dfmObjectStatus, dfmEventSourceProductId,
				dfmHostFullName, dfmCommentFields,
				dfmPhysicalHostId, dfmPhysicalHostFullName
			}
	DESCRIPTION
		"The power supplies on the monitored host are functioning 
		 normally."
	::= 10131


	dfmEvtPowerSupplyOneFailed	TRAP-TYPE
	ENTERPRISE			netappDataFabricManager
	VARIABLES	{
				dfmSerialNumber, dfmEventSourceSerialNumber,
				dfmEventId, dfmEventName, dfmEventSeverity,
				dfmEventTimestamp, dfmEventMessage, 
				dfmEventMessageDetails,
				dfmEventSourceId, dfmEventSourceTable,
				dfmObjectId, dfmObjectType, dfmObjectFullName,
				dfmObjectStatus, dfmEventSourceProductId,
				dfmHostFullName, dfmCommentFields,
				dfmPhysicalHostId, dfmPhysicalHostFullName
			}
	DESCRIPTION
		"DataFabric Manager has detected one failed power supply on 
		 the monitored host."
	::= 10132


	dfmEvtPowerSupplyManyFailed	TRAP-TYPE
	ENTERPRISE			netappDataFabricManager
	VARIABLES	{
				dfmSerialNumber, dfmEventSourceSerialNumber,
				dfmEventId, dfmEventName, dfmEventSeverity,
				dfmEventTimestamp, dfmEventMessage, 
				dfmEventMessageDetails,
				dfmEventSourceId, dfmEventSourceTable,
				dfmObjectId, dfmObjectType, dfmObjectFullName,
				dfmObjectStatus, dfmEventSourceProductId,
				dfmHostFullName, dfmCommentFields,
				dfmPhysicalHostId, dfmPhysicalHostFullName
			}
	DESCRIPTION
		"DataFabric Manager has detected more than 
		 one failed power supplies on the monitored host."
	::= 10133



	-- temperature events

	dfmEvtTemperatureOk	TRAP-TYPE
	ENTERPRISE		netappDataFabricManager
	VARIABLES	{
				dfmSerialNumber, dfmEventSourceSerialNumber,
				dfmEventId, dfmEventName, dfmEventSeverity,
				dfmEventTimestamp, dfmEventMessage, 
				dfmEventMessageDetails,
				dfmEventSourceId, dfmEventSourceTable,
				dfmObjectId, dfmObjectType, dfmObjectFullName,
				dfmObjectStatus, dfmEventSourceProductId,
				dfmHostFullName, dfmCommentFields,
				dfmPhysicalHostId, dfmPhysicalHostFullName
			}
	DESCRIPTION
		"The temperature of the monitored host is normal."
	::= 10141


	dfmEvtTemperatureHot	TRAP-TYPE
	ENTERPRISE		netappDataFabricManager
	VARIABLES	{
				dfmSerialNumber, dfmEventSourceSerialNumber,
				dfmEventId, dfmEventName, dfmEventSeverity,
				dfmEventTimestamp, dfmEventMessage, 
				dfmEventMessageDetails,
				dfmEventSourceId, dfmEventSourceTable,
				dfmObjectId, dfmObjectType, dfmObjectFullName,
				dfmObjectStatus, dfmEventSourceProductId,
				dfmHostFullName, dfmCommentFields,
				dfmPhysicalHostId, dfmPhysicalHostFullName
			}
	DESCRIPTION
		"The temperature of the monitored host is too hot."
	::= 10142


	-- NVRAM Battery events

	dfmEvtNvramBatteryOk	TRAP-TYPE
	ENTERPRISE		netappDataFabricManager
	VARIABLES	{
				dfmSerialNumber, dfmEventSourceSerialNumber,
				dfmEventId, dfmEventName, dfmEventSeverity,
				dfmEventTimestamp, dfmEventMessage, 
				dfmEventMessageDetails,
				dfmEventSourceId, dfmEventSourceTable,
				dfmObjectId, dfmObjectType, dfmObjectFullName,
				dfmObjectStatus, dfmEventSourceProductId,
				dfmHostFullName, dfmCommentFields,
				dfmPhysicalHostId, dfmPhysicalHostFullName
			}
	DESCRIPTION
		"The NVRAM battery on the host monitored 
		 by DataFabric Manager is fine."
	::= 10151


	dfmEvtNvramBatteryLow	TRAP-TYPE
	ENTERPRISE		netappDataFabricManager
	VARIABLES	{
				dfmSerialNumber, dfmEventSourceSerialNumber,
				dfmEventId, dfmEventName, dfmEventSeverity,
				dfmEventTimestamp, dfmEventMessage, 
				dfmEventMessageDetails,
				dfmEventSourceId, dfmEventSourceTable,
				dfmObjectId, dfmObjectType, dfmObjectFullName,
				dfmObjectStatus, dfmEventSourceProductId,
				dfmHostFullName, dfmCommentFields,
				dfmPhysicalHostId, dfmPhysicalHostFullName
			}
	DESCRIPTION
		"The NVRAM battery on the host monitored 
		 by DataFabric Manager has been partially discharged."
	::= 10152


	dfmEvtNvramBatteryDischarged	TRAP-TYPE
	ENTERPRISE			netappDataFabricManager
	VARIABLES	{
				dfmSerialNumber, dfmEventSourceSerialNumber,
				dfmEventId, dfmEventName, dfmEventSeverity,
				dfmEventTimestamp, dfmEventMessage, 
				dfmEventMessageDetails,
				dfmEventSourceId, dfmEventSourceTable,
				dfmObjectId, dfmObjectType, dfmObjectFullName,
				dfmObjectStatus, dfmEventSourceProductId,
				dfmHostFullName, dfmCommentFields,
				dfmPhysicalHostId, dfmPhysicalHostFullName
			}
	DESCRIPTION
		"The NVRAM battery on the host monitored by 
		 DataFabric Manager has been fully discharged."
	::= 10153


	dfmEvtNvramBatteryMissing	TRAP-TYPE
	ENTERPRISE			netappDataFabricManager
	VARIABLES	{
				dfmSerialNumber, dfmEventSourceSerialNumber,
				dfmEventId, dfmEventName, dfmEventSeverity,
				dfmEventTimestamp, dfmEventMessage, 
				dfmEventMessageDetails,
				dfmEventSourceId, dfmEventSourceTable,
				dfmObjectId, dfmObjectType, dfmObjectFullName,
				dfmObjectStatus, dfmEventSourceProductId,
				dfmHostFullName, dfmCommentFields,
				dfmPhysicalHostId, dfmPhysicalHostFullName
			}
	DESCRIPTION
		"The NVRAM battery on the host monitored by 
		 DataFabric Manager is missing."
	::= 10154


	dfmEvtNvramBatteryOld	TRAP-TYPE
	ENTERPRISE		netappDataFabricManager
	VARIABLES	{
				dfmSerialNumber, dfmEventSourceSerialNumber,
				dfmEventId, dfmEventName, dfmEventSeverity,
				dfmEventTimestamp, dfmEventMessage, 
				dfmEventMessageDetails,
				dfmEventSourceId, dfmEventSourceTable,
				dfmObjectId, dfmObjectType, dfmObjectFullName,
				dfmObjectStatus, dfmEventSourceProductId,
				dfmHostFullName, dfmCommentFields,
				dfmPhysicalHostId, dfmPhysicalHostFullName
			}
	DESCRIPTION
		"The NVRAM battery on the host monitored by
		 DataFabric Manager is too old."
	::= 10155


	dfmEvtNvramBatteryReplace	TRAP-TYPE
	ENTERPRISE			netappDataFabricManager
	VARIABLES	{
				dfmSerialNumber, dfmEventSourceSerialNumber,
				dfmEventId, dfmEventName, dfmEventSeverity,
				dfmEventTimestamp, dfmEventMessage, 
				dfmEventMessageDetails,
				dfmEventSourceId, dfmEventSourceTable,
				dfmObjectId, dfmObjectType, dfmObjectFullName,
				dfmObjectStatus, dfmEventSourceProductId,
				dfmHostFullName, dfmCommentFields,
				dfmPhysicalHostId, dfmPhysicalHostFullName
			}
	DESCRIPTION
		"The NVRAM battery on the host monitored 
		 by DataFabric Manager needs to be replaced."
	::= 10156


	dfmEvtNvramBatteryUnknown	TRAP-TYPE
	ENTERPRISE			netappDataFabricManager
	VARIABLES	{
				dfmSerialNumber, dfmEventSourceSerialNumber,
				dfmEventId, dfmEventName, dfmEventSeverity,
				dfmEventTimestamp, dfmEventMessage, 
				dfmEventMessageDetails,
				dfmEventSourceId, dfmEventSourceTable,
				dfmObjectId, dfmObjectType, dfmObjectFullName,
				dfmObjectStatus, dfmEventSourceProductId,
				dfmHostFullName, dfmCommentFields,
				dfmPhysicalHostId, dfmPhysicalHostFullName
			}
	DESCRIPTION
		"DataFabric Manager could not determine 
		 if NVRAM battery on the host being monitored is ok."
	::= 10157

	dfmEvtNvramBatteryOverCharged	TRAP-TYPE
	ENTERPRISE			netappDataFabricManager
	VARIABLES	{ 
				dfmSerialNumber, dfmEventSourceSerialNumber,
				dfmEventId, dfmEventName, dfmEventSeverity,
				dfmEventTimestamp, dfmEventMessage, 
				dfmEventMessageDetails,
				dfmEventSourceId, dfmEventSourceTable,
				dfmObjectId, dfmObjectType, dfmObjectFullName,
				dfmObjectStatus, dfmEventSourceProductId,
				dfmHostFullName, dfmCommentFields,
				dfmPhysicalHostId, dfmPhysicalHostFullName
			} 
	DESCRIPTION 
		"The NVRAM battery on the host monitored 
		by DataFabric Manager has been overcharged." 
	::= 10158

	dfmEvtNvramBatteryFullyCharged	TRAP-TYPE
	ENTERPRISE			netappDataFabricManager
	VARIABLES	{ 
				dfmSerialNumber, dfmEventSourceSerialNumber,
				dfmEventId, dfmEventName, dfmEventSeverity,
				dfmEventTimestamp, dfmEventMessage, 
				dfmEventMessageDetails,
				dfmEventSourceId, dfmEventSourceTable,
				dfmObjectId, dfmObjectType, dfmObjectFullName,
				dfmObjectStatus, dfmEventSourceProductId,
				dfmHostFullName, dfmCommentFields,
				dfmPhysicalHostId, dfmPhysicalHostFullName
			} 
	DESCRIPTION 
		"The NVRAM battery on the host monitored 
		by DataFabric Manager has been fully charged." 
	::= 10159

	-- global status events

	dfmEvtGlobalStatusOther		TRAP-TYPE
	ENTERPRISE			netappDataFabricManager
	VARIABLES	{
				dfmSerialNumber, dfmEventSourceSerialNumber,
				dfmEventId, dfmEventName, dfmEventSeverity,
				dfmEventTimestamp, dfmEventMessage, 
				dfmEventMessageDetails,
				dfmEventSourceId, dfmEventSourceTable,
				dfmObjectId, dfmObjectType, dfmObjectFullName,
				dfmObjectStatus, dfmEventSourceProductId,
				dfmHostFullName, dfmCommentFields,
				dfmPhysicalHostId, dfmPhysicalHostFullName
			}
	DESCRIPTION
		"The host being monitored by DataFabric Manager 
		 has global status value 'other'."
	::= 10161


	dfmEvtGlobalStatusUnknown	TRAP-TYPE
	ENTERPRISE			netappDataFabricManager
	VARIABLES	{
				dfmSerialNumber, dfmEventSourceSerialNumber,
				dfmEventId, dfmEventName, dfmEventSeverity,
				dfmEventTimestamp, dfmEventMessage, 
				dfmEventMessageDetails,
				dfmEventSourceId, dfmEventSourceTable,
				dfmObjectId, dfmObjectType, dfmObjectFullName,
				dfmObjectStatus, dfmEventSourceProductId,
				dfmHostFullName, dfmCommentFields,
				dfmPhysicalHostId, dfmPhysicalHostFullName
			}
	DESCRIPTION
		"The host being monitored by DataFabric Manager 
		 has global status value 'unknown'."
	::= 10162


	dfmEvtGlobalStatusOk	TRAP-TYPE
	ENTERPRISE		netappDataFabricManager
	VARIABLES	{
				dfmSerialNumber, dfmEventSourceSerialNumber,
				dfmEventId, dfmEventName, dfmEventSeverity,
				dfmEventTimestamp, dfmEventMessage, 
				dfmEventMessageDetails,
				dfmEventSourceId, dfmEventSourceTable,
				dfmObjectId, dfmObjectType, dfmObjectFullName,
				dfmObjectStatus, dfmEventSourceProductId,
				dfmHostFullName, dfmCommentFields,
				dfmPhysicalHostId, dfmPhysicalHostFullName
			}
	DESCRIPTION
		"The host being monitored by DataFabric Manager 
		 has global status value 'ok'."
	::= 10163


	dfmEvtGlobalStatusNonCritical	TRAP-TYPE
	ENTERPRISE			netappDataFabricManager
	VARIABLES	{
				dfmSerialNumber, dfmEventSourceSerialNumber,
				dfmEventId, dfmEventName, dfmEventSeverity,
				dfmEventTimestamp, dfmEventMessage, 
				dfmEventMessageDetails,
				dfmEventSourceId, dfmEventSourceTable,
				dfmObjectId, dfmObjectType, dfmObjectFullName,
				dfmObjectStatus, dfmEventSourceProductId,
				dfmHostFullName, dfmCommentFields,
				dfmPhysicalHostId, dfmPhysicalHostFullName
			}
	DESCRIPTION
		"The host being monitored by DataFabric Manager 
		 has global status value 'NonCritical'."
	::= 10164


	dfmEvtGlobalStatusCritical	TRAP-TYPE
	ENTERPRISE			netappDataFabricManager
	VARIABLES	{
				dfmSerialNumber, dfmEventSourceSerialNumber,
				dfmEventId, dfmEventName, dfmEventSeverity,
				dfmEventTimestamp, dfmEventMessage, 
				dfmEventMessageDetails,
				dfmEventSourceId, dfmEventSourceTable,
				dfmObjectId, dfmObjectType, dfmObjectFullName,
				dfmObjectStatus, dfmEventSourceProductId,
				dfmHostFullName, dfmCommentFields,
				dfmPhysicalHostId, dfmPhysicalHostFullName
			}
	DESCRIPTION
		"The host being monitored by DataFabric Manager has 
		 global status value 'Critical'."
	::= 10165


	dfmEvtGlobalStatusNonRecoverable	TRAP-TYPE
	ENTERPRISE				netappDataFabricManager
	VARIABLES	{
				dfmSerialNumber, dfmEventSourceSerialNumber,
				dfmEventId, dfmEventName, dfmEventSeverity,
				dfmEventTimestamp, dfmEventMessage, 
				dfmEventMessageDetails,
				dfmEventSourceId, dfmEventSourceTable,
				dfmObjectId, dfmObjectType, dfmObjectFullName,
				dfmObjectStatus, dfmEventSourceProductId,
				dfmHostFullName, dfmCommentFields,
				dfmPhysicalHostId, dfmPhysicalHostFullName
			}
	DESCRIPTION
		"The host being monitored by DataFabric Manager 
		 has global status value 'NonRecoverable'."
	::= 10166


	-- snapmirror events

	dfmEvtSnapMirrorOff	TRAP-TYPE
	ENTERPRISE		netappDataFabricManager
	VARIABLES	{
				dfmSerialNumber, dfmEventSourceSerialNumber,
				dfmEventId, dfmEventName, dfmEventSeverity,
				dfmEventTimestamp, dfmEventMessage, 
				dfmEventMessageDetails,
				dfmEventSourceId, dfmEventSourceTable,
				dfmObjectId, dfmObjectType, dfmObjectFullName,
				dfmObjectStatus, dfmEventSourceProductId,
				dfmHostFullName, dfmCommentFields,
				dfmPhysicalHostId, dfmPhysicalHostFullName
			}
	DESCRIPTION
		"DataFabric Manager has determined that the SnapMirror 
		 is off on the host being monitored."
	::= 10171


	dfmEvtSnapMirrorWorking		TRAP-TYPE
	ENTERPRISE			netappDataFabricManager
	VARIABLES	{
				dfmSerialNumber, dfmEventSourceSerialNumber,
				dfmEventId, dfmEventName, dfmEventSeverity,
				dfmEventTimestamp, dfmEventMessage, 
				dfmEventMessageDetails,
				dfmEventSourceId, dfmEventSourceTable,
				dfmObjectId, dfmObjectType, dfmObjectFullName,
				dfmObjectStatus, dfmEventSourceProductId,
				dfmHostFullName, dfmCommentFields,
				dfmPhysicalHostId, dfmPhysicalHostFullName
			}
	DESCRIPTION
		"DataFabric Manager has determined that 
		 the SnapMirror is working properly
		 on the host being monitored."
	::= 10172


	dfmEvtSnapMirrorNotScheduled	TRAP-TYPE
	ENTERPRISE			netappDataFabricManager
	VARIABLES	{
				dfmSerialNumber, dfmEventSourceSerialNumber,
				dfmEventId, dfmEventName, dfmEventSeverity,
				dfmEventTimestamp, dfmEventMessage, 
				dfmEventMessageDetails,
				dfmEventSourceId, dfmEventSourceTable,
				dfmObjectId, dfmObjectType, dfmObjectFullName,
				dfmObjectStatus, dfmEventSourceProductId,
				dfmHostFullName, dfmCommentFields,
				dfmPhysicalHostId, dfmPhysicalHostFullName
			}
	DESCRIPTION
		"DataFabric Manager has determined that the SnapMirror 
		 has not been scheduled on the host being monitored."
	::= 10173


	dfmEvtSnapMirrorPossibleProblem		TRAP-TYPE
	ENTERPRISE				netappDataFabricManager
	VARIABLES	{
				dfmSerialNumber, dfmEventSourceSerialNumber,
				dfmEventId, dfmEventName, dfmEventSeverity,
				dfmEventTimestamp, dfmEventMessage, 
				dfmEventMessageDetails,
				dfmEventSourceId, dfmEventSourceTable,
				dfmObjectId, dfmObjectType, dfmObjectFullName,
				dfmObjectStatus, dfmEventSourceProductId,
				dfmHostFullName, dfmCommentFields,
				dfmPhysicalHostId, dfmPhysicalHostFullName
			}
	DESCRIPTION
		"DataFabric Manager has determined that 
		 the SnapMirror may not be working
		 properly on the host being monitored."
	::= 10174


	dfmEvtSnapMirrorNotWorking	TRAP-TYPE
	ENTERPRISE			netappDataFabricManager
	VARIABLES	{
				dfmSerialNumber, dfmEventSourceSerialNumber,
				dfmEventId, dfmEventName, dfmEventSeverity,
				dfmEventTimestamp, dfmEventMessage, 
				dfmEventMessageDetails,
				dfmEventSourceId, dfmEventSourceTable,
				dfmObjectId, dfmObjectType, dfmObjectFullName,
				dfmObjectStatus, dfmEventSourceProductId,
				dfmHostFullName, dfmCommentFields,
				dfmPhysicalHostId, dfmPhysicalHostFullName
			}
	DESCRIPTION
		"DataFabric Manager has determined that 
		 the SnapMirror is not be working
		 properly on the host being monitored."
	::= 10175


	dfmEvtSnapMirrorUnknown		TRAP-TYPE
	ENTERPRISE			netappDataFabricManager
	VARIABLES	{
				dfmSerialNumber, dfmEventSourceSerialNumber,
				dfmEventId, dfmEventName, dfmEventSeverity,
				dfmEventTimestamp, dfmEventMessage, 
				dfmEventMessageDetails,
				dfmEventSourceId, dfmEventSourceTable,
				dfmObjectId, dfmObjectType, dfmObjectFullName,
				dfmObjectStatus, dfmEventSourceProductId,
				dfmHostFullName, dfmCommentFields,
				dfmPhysicalHostId, dfmPhysicalHostFullName
			}
	DESCRIPTION
		"DataFabric Manager could not determine 
		 if the SnapMirror is working
		 properly on the host being monitored."
	::= 10176


	-- CFO Settings events

	dfmEvtCfoSettingsEnabled	TRAP-TYPE
	ENTERPRISE			netappDataFabricManager
	VARIABLES	{
				dfmSerialNumber, dfmEventSourceSerialNumber,
				dfmEventId, dfmEventName, dfmEventSeverity,
				dfmEventTimestamp, dfmEventMessage, 
				dfmEventMessageDetails,
				dfmEventSourceId, dfmEventSourceTable,
				dfmObjectId, dfmObjectType, dfmObjectFullName,
				dfmObjectStatus, dfmEventSourceProductId,
				dfmHostFullName, dfmCommentFields,
				dfmPhysicalHostId, dfmPhysicalHostFullName
			}
	DESCRIPTION
		"The cluster has been enabled on the host being
		 monitored by DataFabric Manager."
	::= 10181


	dfmEvtCfoSettingsNotConfigured		TRAP-TYPE
	ENTERPRISE				netappDataFabricManager
	VARIABLES	{
				dfmSerialNumber, dfmEventSourceSerialNumber,
				dfmEventId, dfmEventName, dfmEventSeverity,
				dfmEventTimestamp, dfmEventMessage, 
				dfmEventMessageDetails,
				dfmEventSourceId, dfmEventSourceTable,
				dfmObjectId, dfmObjectType, dfmObjectFullName,
				dfmObjectStatus, dfmEventSourceProductId,
				dfmHostFullName, dfmCommentFields,
				dfmPhysicalHostId, dfmPhysicalHostFullName
			}
	DESCRIPTION
		"The cluster has not been configured on the host being 
		 monitored by DataFabric Manager."
	::= 10182


	dfmEvtCfoSettingsDisabled	TRAP-TYPE
	ENTERPRISE			netappDataFabricManager
	VARIABLES	{
				dfmSerialNumber, dfmEventSourceSerialNumber,
				dfmEventId, dfmEventName, dfmEventSeverity,
				dfmEventTimestamp, dfmEventMessage, 
				dfmEventMessageDetails,
				dfmEventSourceId, dfmEventSourceTable,
				dfmObjectId, dfmObjectType, dfmObjectFullName,
				dfmObjectStatus, dfmEventSourceProductId,
				dfmHostFullName, dfmCommentFields,
				dfmPhysicalHostId, dfmPhysicalHostFullName
			}
	DESCRIPTION
		"The cluster has been disabled on the host being 
		 monitored by DataFabric Manager."
	::= 10183


	dfmEvtCfoSettingsTakeoverDisabled	TRAP-TYPE
	ENTERPRISE				netappDataFabricManager
	VARIABLES	{
				dfmSerialNumber, dfmEventSourceSerialNumber,
				dfmEventId, dfmEventName, dfmEventSeverity,
				dfmEventTimestamp, dfmEventMessage, 
				dfmEventMessageDetails,
				dfmEventSourceId, dfmEventSourceTable,
				dfmObjectId, dfmObjectType, dfmObjectFullName,
				dfmObjectStatus, dfmEventSourceProductId,
				dfmHostFullName, dfmCommentFields,
				dfmPhysicalHostId, dfmPhysicalHostFullName
			}
	DESCRIPTION
		"Cluster takeover has been disabled on the host being 
		 monitored by DataFabric Manager."
	::= 10184


	dfmEvtCfoSettingsThisNodeDead	TRAP-TYPE
	ENTERPRISE			netappDataFabricManager
	VARIABLES	{
				dfmSerialNumber, dfmEventSourceSerialNumber,
				dfmEventId, dfmEventName, dfmEventSeverity,
				dfmEventTimestamp, dfmEventMessage, 
				dfmEventMessageDetails,
				dfmEventSourceId, dfmEventSourceTable,
				dfmObjectId, dfmObjectType, dfmObjectFullName,
				dfmObjectStatus, dfmEventSourceProductId,
				dfmHostFullName, dfmCommentFields,
				dfmPhysicalHostId, dfmPhysicalHostFullName
			}
	DESCRIPTION
		"The active/active controller being monitored by 
		 DataFabric Manager has gone down."
	::= 10185


	-- CFO This Filer events

	dfmEvtCfoThisFilerCanTakeover	TRAP-TYPE
	ENTERPRISE			netappDataFabricManager
	VARIABLES	{
				dfmSerialNumber, dfmEventSourceSerialNumber,
				dfmEventId, dfmEventName, dfmEventSeverity,
				dfmEventTimestamp, dfmEventMessage, 
				dfmEventMessageDetails,
				dfmEventSourceId, dfmEventSourceTable,
				dfmObjectId, dfmObjectType, dfmObjectFullName,
				dfmObjectStatus, dfmEventSourceProductId,
				dfmHostFullName, dfmCommentFields,
				dfmPhysicalHostId, dfmPhysicalHostFullName
			}
	DESCRIPTION
		"The active/active controller being monitored by 
		 DataFabric Manager is capable of 
		 taking over its partner."
	::= 10191


	dfmEvtCfoThisFilerCannotTakeover	TRAP-TYPE
	ENTERPRISE				netappDataFabricManager
	VARIABLES	{
				dfmSerialNumber, dfmEventSourceSerialNumber,
				dfmEventId, dfmEventName, dfmEventSeverity,
				dfmEventTimestamp, dfmEventMessage, 
				dfmEventMessageDetails,
				dfmEventSourceId, dfmEventSourceTable,
				dfmObjectId, dfmObjectType, dfmObjectFullName,
				dfmObjectStatus, dfmEventSourceProductId,
				dfmHostFullName, dfmCommentFields,
				dfmPhysicalHostId, dfmPhysicalHostFullName
			}
	DESCRIPTION
		"The active/active controller being monitored by 
		 DataFabric Manager is not capable of
		 taking over its partner."
	::= 10192


	dfmEvtCfoThisFilerTakeover	TRAP-TYPE
	ENTERPRISE			netappDataFabricManager
	VARIABLES	{
				dfmSerialNumber, dfmEventSourceSerialNumber,
				dfmEventId, dfmEventName, dfmEventSeverity,
				dfmEventTimestamp, dfmEventMessage, 
				dfmEventMessageDetails,
				dfmEventSourceId, dfmEventSourceTable,
				dfmObjectId, dfmObjectType, dfmObjectFullName,
				dfmObjectStatus, dfmEventSourceProductId,
				dfmHostFullName, dfmCommentFields,
				dfmPhysicalHostId, dfmPhysicalHostFullName
			}
	DESCRIPTION
		"The active/active controller being monitored by 
		 DataFabric Manager has taken over its partner."
	::= 10193


	dfmEvtCfoThisFilerDead		TRAP-TYPE
	ENTERPRISE			netappDataFabricManager
	VARIABLES	{
				dfmSerialNumber, dfmEventSourceSerialNumber,
				dfmEventId, dfmEventName, dfmEventSeverity,
				dfmEventTimestamp, dfmEventMessage, 
				dfmEventMessageDetails,
				dfmEventSourceId, dfmEventSourceTable,
				dfmObjectId, dfmObjectType, dfmObjectFullName,
				dfmObjectStatus, dfmEventSourceProductId,
				dfmHostFullName, dfmCommentFields,
				dfmPhysicalHostId, dfmPhysicalHostFullName
			}
	DESCRIPTION
		"The active/active controller being monitored by 
		 DataFabric Manager has gone down."
	::= 10194


	-- CFO Partner events

	dfmEvtCfoPartnerOk	TRAP-TYPE
	ENTERPRISE		netappDataFabricManager
	VARIABLES	{
				dfmSerialNumber, dfmEventSourceSerialNumber,
				dfmEventId, dfmEventName, dfmEventSeverity,
				dfmEventTimestamp, dfmEventMessage, 
				dfmEventMessageDetails,
				dfmEventSourceId, dfmEventSourceTable,
				dfmObjectId, dfmObjectType, dfmObjectFullName,
				dfmObjectStatus, dfmEventSourceProductId,
				dfmHostFullName, dfmCommentFields,
				dfmPhysicalHostId, dfmPhysicalHostFullName
			}
	DESCRIPTION
		"Active/Active partner of the host being monitored 
		 by DataFabric Manager is up."
	::= 10201


	dfmEvtCfoPartnerMayBeDown	TRAP-TYPE
	ENTERPRISE			netappDataFabricManager
	VARIABLES	{
				dfmSerialNumber, dfmEventSourceSerialNumber,
				dfmEventId, dfmEventName, dfmEventSeverity,
				dfmEventTimestamp, dfmEventMessage, 
				dfmEventMessageDetails,
				dfmEventSourceId, dfmEventSourceTable,
				dfmObjectId, dfmObjectType, dfmObjectFullName,
				dfmObjectStatus, dfmEventSourceProductId,
				dfmHostFullName, dfmCommentFields,
				dfmPhysicalHostId, dfmPhysicalHostFullName
			}
	DESCRIPTION
		"Active/Active partner of the host being monitored 
		 by DataFabric Manager may be down."
	::= 10202


	dfmEvtCfoPartnerDead	TRAP-TYPE
	ENTERPRISE		netappDataFabricManager
	VARIABLES	{
				dfmSerialNumber, dfmEventSourceSerialNumber,
				dfmEventId, dfmEventName, dfmEventSeverity,
				dfmEventTimestamp, dfmEventMessage, 
				dfmEventMessageDetails,
				dfmEventSourceId, dfmEventSourceTable,
				dfmObjectId, dfmObjectType, dfmObjectFullName,
				dfmObjectStatus, dfmEventSourceProductId,
				dfmHostFullName, dfmCommentFields,
				dfmPhysicalHostId, dfmPhysicalHostFullName
			}
	DESCRIPTION
		"Active/Active partner of the host being monitored 
		 by DataFabric Manager is down."
	::= 10203


	-- CFO Interconnect events

	dfmEvtCfoInterconnectUp		TRAP-TYPE
	ENTERPRISE			netappDataFabricManager
	VARIABLES	{
				dfmSerialNumber, dfmEventSourceSerialNumber,
				dfmEventId, dfmEventName, dfmEventSeverity,
				dfmEventTimestamp, dfmEventMessage, 
				dfmEventMessageDetails,
				dfmEventSourceId, dfmEventSourceTable,
				dfmObjectId, dfmObjectType, dfmObjectFullName,
				dfmObjectStatus, dfmEventSourceProductId,
				dfmHostFullName, dfmCommentFields,
				dfmPhysicalHostId, dfmPhysicalHostFullName
			}
	DESCRIPTION
		"The cluster interconnect hardware attached to the clustered 
		 host being monitored by DataFabric Manager is up."
	::= 10211


	dfmEvtCfoInterconnectNotPresent		TRAP-TYPE
	ENTERPRISE				netappDataFabricManager
	VARIABLES	{
				dfmSerialNumber, dfmEventSourceSerialNumber,
				dfmEventId, dfmEventName, dfmEventSeverity,
				dfmEventTimestamp, dfmEventMessage, 
				dfmEventMessageDetails,
				dfmEventSourceId, dfmEventSourceTable,
				dfmObjectId, dfmObjectType, dfmObjectFullName,
				dfmObjectStatus, dfmEventSourceProductId,
				dfmHostFullName, dfmCommentFields,
				dfmPhysicalHostId, dfmPhysicalHostFullName
			}
	DESCRIPTION
		"There is no cluster interconnect hardware attached to the 
		 active/active controller being monitored by DataFabric Manager."
	::= 10212


	dfmEvtCfoInterconnectDown	TRAP-TYPE
	ENTERPRISE			netappDataFabricManager
	VARIABLES	{
				dfmSerialNumber, dfmEventSourceSerialNumber,
				dfmEventId, dfmEventName, dfmEventSeverity,
				dfmEventTimestamp, dfmEventMessage, 
				dfmEventMessageDetails,
				dfmEventSourceId, dfmEventSourceTable,
				dfmObjectId, dfmObjectType, dfmObjectFullName,
				dfmObjectStatus, dfmEventSourceProductId,
				dfmHostFullName, dfmCommentFields,
				dfmPhysicalHostId, dfmPhysicalHostFullName
			}
	DESCRIPTION
		"The cluster interconnect hardware attached to the clustered 
		 host being monitored by DataFabric Manager is down."
	::= 10213


	dfmEvtCfoInterconnectPartialFailure	TRAP-TYPE
	ENTERPRISE				netappDataFabricManager
	VARIABLES	{
				dfmSerialNumber, dfmEventSourceSerialNumber,
				dfmEventId, dfmEventName, dfmEventSeverity,
				dfmEventTimestamp, dfmEventMessage, 
				dfmEventMessageDetails,
				dfmEventSourceId, dfmEventSourceTable,
				dfmObjectId, dfmObjectType, dfmObjectFullName,
				dfmObjectStatus, dfmEventSourceProductId,
				dfmHostFullName, dfmCommentFields,
				dfmPhysicalHostId, dfmPhysicalHostFullName
			}
	DESCRIPTION
		"The cluster interconnect hardware attached to the clustered 
		 host being monitored by DataFabric Manager 
		 has partially failed."
	::= 10214


	dfmEvtSvdirDiscovered		TRAP-TYPE
	ENTERPRISE			netappDataFabricManager
	VARIABLES	{
				dfmSerialNumber, dfmEventSourceSerialNumber,
				dfmEventId, dfmEventName, dfmEventSeverity,
				dfmEventTimestamp, dfmEventMessage, 
				dfmEventMessageDetails,
				dfmEventSourceId, dfmEventSourceTable,
				dfmObjectId, dfmObjectType, dfmObjectFullName,
				dfmObjectStatus, dfmEventSourceProductId,
				dfmHostFullName, dfmCommentFields,
				dfmPhysicalHostId, dfmPhysicalHostFullName
			}
	DESCRIPTION
		"DataFabric Manager discovered a dir that is not backedup."
	::= 10220


	dfmEvtHostDiscovered		TRAP-TYPE
	ENTERPRISE			netappDataFabricManager
	VARIABLES	{
				dfmSerialNumber, dfmEventSourceSerialNumber,
				dfmEventId, dfmEventName, dfmEventSeverity,
				dfmEventTimestamp, dfmEventMessage, 
				dfmEventMessageDetails,
				dfmEventSourceId, dfmEventSourceTable,
				dfmObjectId, dfmObjectType, dfmObjectFullName,
				dfmObjectStatus, dfmEventSourceProductId,
				dfmHostFullName, dfmCommentFields,
				dfmPhysicalHostId, dfmPhysicalHostFullName
			}
	DESCRIPTION
		"DataFabric Manager discovered a host."
	::= 10221


	dfmEvtHostSystemIdChanged	TRAP-TYPE
	ENTERPRISE		netappDataFabricManager
	VARIABLES	{
				dfmSerialNumber, dfmEventSourceSerialNumber,
				dfmEventId, dfmEventName, dfmEventSeverity,
				dfmEventTimestamp, dfmEventMessage, 
				dfmEventMessageDetails,
				dfmEventSourceId, dfmEventSourceTable,
				dfmObjectId, dfmObjectType, dfmObjectFullName,
				dfmObjectStatus, dfmEventSourceProductId,
				dfmHostFullName, dfmCommentFields,
				dfmPhysicalHostId, dfmPhysicalHostFullName
			}
	DESCRIPTION
		"The system ID of the appliance has changed."
	::= 10222


	dfmEvtHostNameChanged	TRAP-TYPE
	ENTERPRISE		netappDataFabricManager
	VARIABLES	{
				dfmSerialNumber, dfmEventSourceSerialNumber,
				dfmEventId, dfmEventName, dfmEventSeverity,
				dfmEventTimestamp, dfmEventMessage, 
				dfmEventMessageDetails,
				dfmEventSourceId, dfmEventSourceTable,
				dfmObjectId, dfmObjectType, dfmObjectFullName,
				dfmObjectStatus, dfmEventSourceProductId,
				dfmHostFullName, dfmCommentFields,
				dfmPhysicalHostId, dfmPhysicalHostFullName
			}
	DESCRIPTION
		"The name of the appliance has changed."
	::= 10223


	dfmEvtOssvHostDiscovered	TRAP-TYPE
	ENTERPRISE			netappDataFabricManager
	VARIABLES	{
				dfmSerialNumber, dfmEventSourceSerialNumber,
				dfmEventId, dfmEventName, dfmEventSeverity,
				dfmEventTimestamp, dfmEventMessage, 
				dfmEventMessageDetails,
				dfmEventSourceId, dfmEventSourceTable,
				dfmObjectId, dfmObjectType, dfmObjectFullName,
				dfmObjectStatus, dfmEventSourceProductId,
				dfmHostFullName, dfmCommentFields,
				dfmPhysicalHostId, dfmPhysicalHostFullName
			}
	DESCRIPTION
		"DataFabric Manager discovered an OSSV host."
	::= 10224


	dfmEvtHostIdentityOk	TRAP-TYPE
	ENTERPRISE		netappDataFabricManager
	VARIABLES	{
				dfmSerialNumber, dfmEventSourceSerialNumber,
				dfmEventId, dfmEventName, dfmEventSeverity,
				dfmEventTimestamp, dfmEventMessage, 
				dfmEventMessageDetails,
				dfmEventSourceId, dfmEventSourceTable,
				dfmObjectId, dfmObjectType, dfmObjectFullName,
				dfmObjectStatus, dfmEventSourceProductId,
				dfmHostFullName, dfmCommentFields,
				dfmPhysicalHostId, dfmPhysicalHostFullName
			}
	DESCRIPTION
		"The name and system ID of the appliance have not changed."
	::= 10225

	dfmEvtHostIdentityConflict	TRAP-TYPE
	ENTERPRISE		netappDataFabricManager
	VARIABLES	{
				dfmSerialNumber, dfmEventSourceSerialNumber,
				dfmEventId, dfmEventName, dfmEventSeverity,
				dfmEventTimestamp, dfmEventMessage, 
				dfmEventMessageDetails,
				dfmEventSourceId, dfmEventSourceTable,
				dfmObjectId, dfmObjectType, dfmObjectFullName,
				dfmObjectStatus, dfmEventSourceProductId,
				dfmHostFullName, dfmCommentFields,
				dfmPhysicalHostId, dfmPhysicalHostFullName
			}
	DESCRIPTION
		"The name and system ID of the appliance have changed."

	::= 10226
	dfmEvtHostLoginOk	TRAP-TYPE
	ENTERPRISE		netappDataFabricManager
	VARIABLES	{
				dfmSerialNumber, dfmEventSourceSerialNumber,
				dfmEventId, dfmEventName, dfmEventSeverity,
				dfmEventTimestamp, dfmEventMessage, 
				dfmEventMessageDetails,
				dfmEventSourceId, dfmEventSourceTable,
				dfmObjectId, dfmObjectType, dfmObjectFullName,
				dfmObjectStatus, dfmEventSourceProductId,
				dfmHostFullName, dfmCommentFields,
				dfmPhysicalHostId, dfmPhysicalHostFullName
			}
	DESCRIPTION
		"The host login and password are correct."
	::= 10227

	dfmEvtHostLoginFailed	TRAP-TYPE
	ENTERPRISE		netappDataFabricManager
	VARIABLES	{
				dfmSerialNumber, dfmEventSourceSerialNumber,
				dfmEventId, dfmEventName, dfmEventSeverity,
				dfmEventTimestamp, dfmEventMessage, 
				dfmEventMessageDetails,
				dfmEventSourceId, dfmEventSourceTable,
				dfmObjectId, dfmObjectType, dfmObjectFullName,
				dfmObjectStatus, dfmEventSourceProductId,
				dfmHostFullName, dfmCommentFields,
				dfmPhysicalHostId, dfmPhysicalHostFullName
			}
	DESCRIPTION
		"The host login or password is not correct."
	::= 10228

	dfmEvtPrimaryHostDiscovered	TRAP-TYPE
	ENTERPRISE			netappDataFabricManager
	VARIABLES	{
				dfmSerialNumber, dfmEventSourceSerialNumber,
				dfmEventId, dfmEventName, dfmEventSeverity,
				dfmEventTimestamp, dfmEventMessage, 
				dfmEventMessageDetails,
				dfmEventSourceId, dfmEventSourceTable,
				dfmObjectId, dfmObjectType, dfmObjectFullName,
				dfmObjectStatus, dfmEventSourceProductId,
				dfmHostFullName, dfmCommentFields,
				dfmPhysicalHostId, dfmPhysicalHostFullName
			}
	DESCRIPTION
		"DataFabric Manager discovered an Primary host."
	::= 10229

	-- management station free space events

	dfmEvtMgmtStFreeSpaceOk		TRAP-TYPE
	ENTERPRISE			netappDataFabricManager
	VARIABLES	{
				dfmSerialNumber, dfmEventSourceSerialNumber,
				dfmEventId, dfmEventName, dfmEventSeverity,
				dfmEventTimestamp, dfmEventMessage, 
				dfmEventMessageDetails,
				dfmEventSourceId, dfmEventSourceTable,
				dfmObjectId, dfmObjectType, dfmObjectFullName,
				dfmObjectStatus, dfmEventSourceProductId,
				dfmHostFullName, dfmCommentFields,
				dfmPhysicalHostId, dfmPhysicalHostFullName
			}
	DESCRIPTION	
		"Management station has sufficient free disk space."
	::= 10231

	dfmEvtMgmtStNotEnoughFreeSpace	TRAP-TYPE
	ENTERPRISE			netappDataFabricManager
	VARIABLES	{
				dfmSerialNumber, dfmEventSourceSerialNumber,
				dfmEventId, dfmEventName, dfmEventSeverity,
				dfmEventTimestamp, dfmEventMessage, 
				dfmEventMessageDetails,
				dfmEventSourceId, dfmEventSourceTable,
				dfmObjectId, dfmObjectType, dfmObjectFullName,
				dfmObjectStatus, dfmEventSourceProductId,
				dfmHostFullName, dfmCommentFields,
				dfmPhysicalHostId, dfmPhysicalHostFullName
			}
	DESCRIPTION	
		"Management station does not have sufficient free 
		 disk space for the DataFabric Manager. 
		 All monitoring activity has stopped."
	::= 10232

	dfmEvtMgmtStFileSystemFileSizeLimitReached	TRAP-TYPE
	ENTERPRISE			netappDataFabricManager
	VARIABLES	{
				dfmSerialNumber, dfmEventSourceSerialNumber,
				dfmEventId, dfmEventName, dfmEventSeverity,
				dfmEventTimestamp, dfmEventMessage, 
				dfmEventMessageDetails,
				dfmEventSourceId, dfmEventSourceTable,
				dfmObjectId, dfmObjectType, dfmObjectFullName,
				dfmObjectStatus, dfmEventSourceProductId,
				dfmHostFullName, dfmCommentFields,
				dfmPhysicalHostId, dfmPhysicalHostFullName
			}
	DESCRIPTION
		"The file system holding the DFM database limits files to 
		2 GB and the database file is approaching this limit.
		All DFM services will stop if the database file 
		ever exceeds the file system file size limit."
	::= 10233


	dfmEvtConfigFileChanged		TRAP-TYPE
	ENTERPRISE			netappDataFabricManager
	VARIABLES	{
				dfmSerialNumber, dfmEventSourceSerialNumber,
				dfmEventId, dfmEventName, dfmEventSeverity,
				dfmEventTimestamp, dfmEventMessage, 
				dfmEventMessageDetails,
				dfmEventSourceId, dfmEventSourceTable,
				dfmObjectId, dfmObjectType, dfmObjectFullName,
				dfmObjectStatus, dfmEventSourceProductId,
				dfmHostFullName, dfmCommentFields,
				dfmPhysicalHostId, dfmPhysicalHostFullName
			}
	DESCRIPTION
		"A configuration file was changed on the DataFabric Manager server."
	::= 10241

	dfmEvtConfigGroupChanged	TRAP-TYPE
	ENTERPRISE			netappDataFabricManager
	VARIABLES	{
				dfmSerialNumber, dfmEventSourceSerialNumber,
				dfmEventId, dfmEventName, dfmEventSeverity,
				dfmEventTimestamp, dfmEventMessage, 
				dfmEventMessageDetails,
				dfmEventSourceId, dfmEventSourceTable,
				dfmObjectId, dfmObjectType, dfmObjectFullName,
				dfmObjectStatus, dfmEventSourceProductId,
				dfmHostFullName, dfmCommentFields,
				dfmPhysicalHostId, dfmPhysicalHostFullName
			}
	DESCRIPTION
		"A configuration group was changed on the DataFabric Manager server."
	::= 10242

	-- ::= 10251 used for dfmEvtLocalCacheConfigStatusOk dropped with
	-- de-support of NetCache


	-- ::= 10252 used for dfmEvtLocalCacheConfigStatusChanged

	-- snapmirror lag events
	
	dfmEvtSnapMirrorDateOk		TRAP-TYPE
	ENTERPRISE			netappDataFabricManager
	VARIABLES	{
				dfmSerialNumber, dfmEventSourceSerialNumber,
				dfmEventId, dfmEventName, dfmEventSeverity,
				dfmEventTimestamp, dfmEventMessage, 
				dfmEventMessageDetails,
				dfmEventSourceId, dfmEventSourceTable,
				dfmObjectId, dfmObjectType, dfmObjectFullName,
				dfmObjectStatus, dfmEventSourceProductId,
				dfmHostFullName, dfmCommentFields,
				dfmPhysicalHostId, dfmPhysicalHostFullName
			}
	DESCRIPTION
		"DataFabric Manager has determined
		 that the SnapMirror Status is normal
		 since the SnapMirror Destination has 
		 been recently updated."
	::= 10261


	dfmEvtSnapMirrorNearlyOutOfDate		TRAP-TYPE
	ENTERPRISE			netappDataFabricManager
	VARIABLES	{
				dfmSerialNumber, dfmEventSourceSerialNumber,
				dfmEventId, dfmEventName, dfmEventSeverity,
				dfmEventTimestamp, dfmEventMessage, 
				dfmEventMessageDetails,
				dfmEventSourceId, dfmEventSourceTable,
				dfmObjectId, dfmObjectType, dfmObjectFullName,
				dfmObjectStatus, dfmEventSourceProductId,
				dfmHostFullName, dfmCommentFields,
				dfmPhysicalHostId, dfmPhysicalHostFullName
			}
	DESCRIPTION
		"DataFabric Manager has determined
		 that the SnapMirror Destination has not
		 been updated for quite some time."
	::= 10262


	dfmEvtSnapMirrorOutOfDate		TRAP-TYPE
	ENTERPRISE			netappDataFabricManager
	VARIABLES	{
				dfmSerialNumber, dfmEventSourceSerialNumber,
				dfmEventId, dfmEventName, dfmEventSeverity,
				dfmEventTimestamp, dfmEventMessage, 
				dfmEventMessageDetails,
				dfmEventSourceId, dfmEventSourceTable,
				dfmObjectId, dfmObjectType, dfmObjectFullName,
				dfmObjectStatus, dfmEventSourceProductId,
				dfmHostFullName, dfmCommentFields,
				dfmPhysicalHostId, dfmPhysicalHostFullName
			}
	DESCRIPTION
		"DataFabric Manager has determined
		 that the SnapMirror Destination has not
		 been updated for a long time and the
		 mirror is out of date."
	::= 10263


	dfmEvtSnapMirrorDeleted		TRAP-TYPE
	ENTERPRISE			netappDataFabricManager
	VARIABLES	{
				dfmSerialNumber, dfmEventSourceSerialNumber,
				dfmEventId, dfmEventName, dfmEventSeverity,
				dfmEventTimestamp, dfmEventMessage, 
				dfmEventMessageDetails,
				dfmEventSourceId, dfmEventSourceTable,
				dfmObjectId, dfmObjectType, dfmObjectFullName,
				dfmObjectStatus, dfmEventSourceProductId,
				dfmHostFullName, dfmCommentFields,
				dfmPhysicalHostId, dfmPhysicalHostFullName
			}
	DESCRIPTION
		"DataFabric Manager has determined
		 that the SnapMirror Relationship
		 no longer exists."
	::= 10264


	dfmEvtSnapMirrorUndeleted		TRAP-TYPE
	ENTERPRISE			netappDataFabricManager
	VARIABLES	{
				dfmSerialNumber, dfmEventSourceSerialNumber,
				dfmEventId, dfmEventName, dfmEventSeverity,
				dfmEventTimestamp, dfmEventMessage, 
				dfmEventMessageDetails,
				dfmEventSourceId, dfmEventSourceTable,
				dfmObjectId, dfmObjectType, dfmObjectFullName,
				dfmObjectStatus, dfmEventSourceProductId,
				dfmHostFullName, dfmCommentFields,
				dfmPhysicalHostId, dfmPhysicalHostFullName
			}
	DESCRIPTION
		"DataFabric Manager has determined
		 that the SnapMirror Relationship
		 now exists again."
	::= 10265


	dfmEvtSnapMirrorDiscovered	TRAP-TYPE
	ENTERPRISE			netappDataFabricManager
	VARIABLES	{
				dfmSerialNumber, dfmEventSourceSerialNumber,
				dfmEventId, dfmEventName, dfmEventSeverity,
				dfmEventTimestamp, dfmEventMessage, 
				dfmEventMessageDetails,
				dfmEventSourceId, dfmEventSourceTable,
				dfmObjectId, dfmObjectType, dfmObjectFullName,
				dfmObjectStatus, dfmEventSourceProductId,
				dfmHostFullName, dfmCommentFields,
				dfmPhysicalHostId, dfmPhysicalHostFullName
			}
	DESCRIPTION
		"DataFabric Manager has discovered a new
		 SnapMirror Relationship."
	::= 10266

	dfmEvtSnapMirrorModified	TRAP-TYPE
	ENTERPRISE			netappDataFabricManager
	VARIABLES	{
				dfmSerialNumber, dfmEventSourceSerialNumber,
				dfmEventId, dfmEventName, dfmEventSeverity,
				dfmEventTimestamp, dfmEventMessage, 
				dfmEventMessageDetails,
				dfmEventSourceId, dfmEventSourceTable,
				dfmObjectId, dfmObjectType, dfmObjectFullName,
				dfmObjectStatus, dfmEventSourceProductId,
				dfmHostFullName, dfmCommentFields,
				dfmPhysicalHostId, dfmPhysicalHostFullName
			}
	DESCRIPTION
		"DataFabric Manager flags for a SnapMirror Relationship
	        have been modified."
	::= 10267


	-- Network discovery events

	dfmEvtNetworkOk			TRAP-TYPE
	ENTERPRISE			netappDataFabricManager
	VARIABLES	{
				dfmSerialNumber, dfmEventSourceSerialNumber,
				dfmEventId, dfmEventName, dfmEventSeverity,
				dfmEventTimestamp, dfmEventMessage, 
				dfmEventMessageDetails,
				dfmEventSourceId, dfmEventSourceTable,
				dfmObjectId, dfmObjectType, dfmObjectFullName,
				dfmObjectStatus, dfmEventSourceProductId,
				dfmHostFullName, dfmCommentFields,
				dfmPhysicalHostId, dfmPhysicalHostFullName
			}
	DESCRIPTION
		"The network is normal."
	::= 10281


	dfmEvtNetworkTooLarge		TRAP-TYPE
	ENTERPRISE			netappDataFabricManager
	VARIABLES	{
				dfmSerialNumber, dfmEventSourceSerialNumber,
				dfmEventId, dfmEventName, dfmEventSeverity,
				dfmEventTimestamp, dfmEventMessage, 
				dfmEventMessageDetails,
				dfmEventSourceId, dfmEventSourceTable,
				dfmObjectId, dfmObjectType, dfmObjectFullName,
				dfmObjectStatus, dfmEventSourceProductId,
				dfmHostFullName, dfmCommentFields,
				dfmPhysicalHostId, dfmPhysicalHostFullName
			}
	DESCRIPTION
		"The network is too large.  Host discovery for the network is disabled."
	::= 10282



	-- user quota events

	dfmEvtUserDiskSpaceQuotaOk	TRAP-TYPE
	ENTERPRISE		netappDataFabricManager
	VARIABLES	{
				dfmSerialNumber, dfmEventSourceSerialNumber,
				dfmEventId, dfmEventName, dfmEventSeverity,
				dfmEventTimestamp, dfmEventMessage, 
				dfmEventMessageDetails,
				dfmEventSourceId, dfmEventSourceTable,
				dfmEventSourceProductId
			}
	DESCRIPTION
		"Disk space quota for user has not reached 
		 'almostFull' threshold."
	::= 10291


	dfmEvtUserDiskSpaceQuotaAlmostFull	TRAP-TYPE
	ENTERPRISE		netappDataFabricManager
	VARIABLES	{
				dfmSerialNumber, dfmEventSourceSerialNumber,
				dfmEventId, dfmEventName, dfmEventSeverity,
				dfmEventTimestamp, dfmEventMessage, 
				dfmEventMessageDetails,
				dfmEventSourceId, dfmEventSourceTable,
				dfmEventSourceProductId
			}
	DESCRIPTION
		"Disk space quota for user has reached 'almostFull' threshold."
	::= 10292


	dfmEvtUserDiskSpaceQuotaFull	TRAP-TYPE
	ENTERPRISE		netappDataFabricManager
	VARIABLES	{
				dfmSerialNumber, dfmEventSourceSerialNumber,
				dfmEventId, dfmEventName, dfmEventSeverity,
				dfmEventTimestamp, dfmEventMessage, 
				dfmEventMessageDetails,
				dfmEventSourceId, dfmEventSourceTable,
				dfmEventSourceProductId
			}
	DESCRIPTION
		"Disk space quota for user has reached 'full' threshold."
	::= 10293


	dfmEvtUserFilesQuotaOk		TRAP-TYPE
	ENTERPRISE		netappDataFabricManager
	VARIABLES	{
				dfmSerialNumber, dfmEventSourceSerialNumber,
				dfmEventId, dfmEventName, dfmEventSeverity,
				dfmEventTimestamp, dfmEventMessage, 
				dfmEventMessageDetails,
				dfmEventSourceId, dfmEventSourceTable,
				dfmEventSourceProductId
			}
	DESCRIPTION
		"Files quota for user has not reached 'almostFull' threshold."
	::= 10301


	dfmEvtUserFilesQuotaAlmostFull	TRAP-TYPE
	ENTERPRISE		netappDataFabricManager
	VARIABLES	{
				dfmSerialNumber, dfmEventSourceSerialNumber,
				dfmEventId, dfmEventName, dfmEventSeverity,
				dfmEventTimestamp, dfmEventMessage, 
				dfmEventMessageDetails,
				dfmEventSourceId, dfmEventSourceTable,
				dfmEventSourceProductId
			}
	DESCRIPTION
		"Files quota for user has reached 'almostFull' threshold."
	::= 10302


	dfmEvtUserFilesQuotaFull		TRAP-TYPE
	ENTERPRISE		netappDataFabricManager
	VARIABLES	{
				dfmSerialNumber, dfmEventSourceSerialNumber,
				dfmEventId, dfmEventName, dfmEventSeverity,
				dfmEventTimestamp, dfmEventMessage, 
				dfmEventMessageDetails,
				dfmEventSourceId, dfmEventSourceTable,
				dfmEventSourceProductId
			}
	DESCRIPTION
		"Files quota for user has reached 'full' threshold."
	::= 10303


	-- Lun Management events

	dfmEvtLunOnline			TRAP-TYPE
	ENTERPRISE			netappDataFabricManager
	VARIABLES	{
				dfmSerialNumber, dfmEventSourceSerialNumber,
				dfmEventId, dfmEventName, dfmEventSeverity,
				dfmEventTimestamp, dfmEventMessage, 
				dfmEventMessageDetails,
				dfmEventSourceId, dfmEventSourceTable,
				dfmObjectId, dfmObjectType, dfmObjectFullName,
				dfmObjectStatus, dfmEventSourceProductId,
				dfmHostFullName, dfmCommentFields,
				dfmPhysicalHostId, dfmPhysicalHostFullName
			}
	DESCRIPTION
		"The lun is online. Variable dfmObjectId identifies the lun."
	::= 10311

	dfmEvtLunOffline		TRAP-TYPE
	ENTERPRISE			netappDataFabricManager
	VARIABLES	{
				dfmSerialNumber, dfmEventSourceSerialNumber,
				dfmEventId, dfmEventName, dfmEventSeverity,
				dfmEventTimestamp, dfmEventMessage, 
				dfmEventMessageDetails,
				dfmEventSourceId, dfmEventSourceTable,
				dfmObjectId, dfmObjectType, dfmObjectFullName,
				dfmObjectStatus, dfmEventSourceProductId,
				dfmHostFullName, dfmCommentFields,
				dfmPhysicalHostId, dfmPhysicalHostFullName
			}
	DESCRIPTION
		"The lun is offline. Variable dfmObjectId identifies the lun."
	::= 10312

	dfmEvtLunSnapshotOk		TRAP-TYPE
	ENTERPRISE			netappDataFabricManager
	VARIABLES	{
				dfmSerialNumber, dfmEventSourceSerialNumber,
				dfmEventId, dfmEventName, dfmEventSeverity,
				dfmEventTimestamp, dfmEventMessage, 
				dfmEventMessageDetails,
				dfmEventSourceId, dfmEventSourceTable,
				dfmObjectId, dfmObjectType, dfmObjectFullName,
				dfmObjectStatus, dfmEventSourceProductId,
				dfmHostFullName, dfmCommentFields,
				dfmPhysicalHostId, dfmPhysicalHostFullName
			}
	DESCRIPTION
		"A snapshot can be taken of the volume containing the lun. 
		 Variable dfmObjectId identifies the lun."
	::= 10313

	dfmEvtLunSnapshotNotPossible	TRAP-TYPE
	ENTERPRISE			netappDataFabricManager
	VARIABLES	{
				dfmSerialNumber, dfmEventSourceSerialNumber,
				dfmEventId, dfmEventName, dfmEventSeverity,
				dfmEventTimestamp, dfmEventMessage, 
				dfmEventMessageDetails,
				dfmEventSourceId, dfmEventSourceTable,
				dfmObjectId, dfmObjectType, dfmObjectFullName,
				dfmObjectStatus, dfmEventSourceProductId,
				dfmHostFullName, dfmCommentFields,
				dfmPhysicalHostId, dfmPhysicalHostFullName
			}
	DESCRIPTION
		"A snapshot of the volume containing this lun cannot be taken
		 because required space is not available for this operation. 
		 Variable dfmObjectId identifies the lun."
	::= 10314

	dfmEvtLunHostClusterConfigOk	TRAP-TYPE
	ENTERPRISE			netappDataFabricManager
	VARIABLES	{
				dfmSerialNumber, dfmEventSourceSerialNumber,
				dfmEventId, dfmEventName, dfmEventSeverity,
				dfmEventTimestamp, dfmEventMessage, 
				dfmEventMessageDetails,
				dfmEventSourceId, dfmEventSourceTable,
				dfmObjectId, dfmObjectType, dfmObjectFullName,
				dfmObjectStatus, dfmEventSourceProductId,
				dfmHostFullName, dfmCommentFields,
				dfmPhysicalHostId, dfmPhysicalHostFullName
			}
	DESCRIPTION
		"Cluster configuration cfmode settings and initiator group
		 settings of the storage system are ok."
	::= 10315

	dfmEvtLunHostClusterConfigError	TRAP-TYPE
	ENTERPRISE			netappDataFabricManager
	VARIABLES	{
				dfmSerialNumber, dfmEventSourceSerialNumber,
				dfmEventId, dfmEventName, dfmEventSeverity,
				dfmEventTimestamp, dfmEventMessage, 
				dfmEventMessageDetails,
				dfmEventSourceId, dfmEventSourceTable,
				dfmObjectId, dfmObjectType, dfmObjectFullName,
				dfmObjectStatus, dfmEventSourceProductId,
				dfmHostFullName, dfmCommentFields,
				dfmPhysicalHostId, dfmPhysicalHostFullName
			}
	DESCRIPTION
		"Some error found with cluster configuration cfmode settings
		 or initiator group settings of the storage system."
	::= 10316

	-- User Email Address events

	dfmEvtUserEmailAddressRejected		TRAP-TYPE
	ENTERPRISE				netappDataFabricManager
	VARIABLES	{
				dfmSerialNumber, dfmEventSourceSerialNumber,
				dfmEventId, dfmEventName, dfmEventSeverity,
				dfmEventTimestamp, dfmEventMessage, 
				dfmEventMessageDetails,
				dfmEventSourceId, dfmEventSourceTable,
				dfmObjectId, dfmObjectType, dfmObjectFullName,
				dfmObjectStatus, dfmEventSourceProductId,
				dfmHostFullName, dfmCommentFields,
				dfmPhysicalHostId, dfmPhysicalHostFullName
			}
	DESCRIPTION
		"Email server rejected the specified email address for the 
		 quota user."
	::= 10321

	dfmEvtUserEmailAddressOk		TRAP-TYPE
	ENTERPRISE				netappDataFabricManager
	VARIABLES	{
				dfmSerialNumber, dfmEventSourceSerialNumber,
				dfmEventId, dfmEventName, dfmEventSeverity,
				dfmEventTimestamp, dfmEventMessage, 
				dfmEventMessageDetails,
				dfmEventSourceId, dfmEventSourceTable,
				dfmObjectId, dfmObjectType, dfmObjectFullName,
				dfmObjectStatus, dfmEventSourceProductId,
				dfmHostFullName, dfmCommentFields,
				dfmPhysicalHostId, dfmPhysicalHostFullName
			}
	DESCRIPTION
		"Email address for the quota user is ok."
	::= 10322

	-- FC Switch Port events

	dfmEvtFCSwitchPortFaulty		TRAP-TYPE
	ENTERPRISE				netappDataFabricManager
	VARIABLES	{
				dfmSerialNumber, dfmEventSourceSerialNumber,
				dfmEventId, dfmEventName, dfmEventSeverity,
				dfmEventTimestamp, dfmEventMessage, 
				dfmEventMessageDetails,
				dfmEventSourceId, dfmEventSourceTable,
				dfmObjectId, dfmObjectType, dfmObjectFullName,
				dfmObjectStatus, dfmEventSourceProductId,
				dfmHostFullName, dfmCommentFields,
				dfmPhysicalHostId, dfmPhysicalHostFullName
			}
	DESCRIPTION
		"The port on the fibre channel switch is faulty."
	::= 10331

	dfmEvtFCSwitchPortOffline		TRAP-TYPE
	ENTERPRISE				netappDataFabricManager
	VARIABLES	{
				dfmSerialNumber, dfmEventSourceSerialNumber,
				dfmEventId, dfmEventName, dfmEventSeverity,
				dfmEventTimestamp, dfmEventMessage, 
				dfmEventMessageDetails,
				dfmEventSourceId, dfmEventSourceTable,
				dfmObjectId, dfmObjectType, dfmObjectFullName,
				dfmObjectStatus, dfmEventSourceProductId,
				dfmHostFullName, dfmCommentFields,
				dfmPhysicalHostId, dfmPhysicalHostFullName
			}
	DESCRIPTION
		"The port on the fibre channel switch is offline."
	::= 10332

	dfmEvtFCSwitchPortOnline		TRAP-TYPE
	ENTERPRISE				netappDataFabricManager
	VARIABLES	{
				dfmSerialNumber, dfmEventSourceSerialNumber,
				dfmEventId, dfmEventName, dfmEventSeverity,
				dfmEventTimestamp, dfmEventMessage, 
				dfmEventMessageDetails,
				dfmEventSourceId, dfmEventSourceTable,
				dfmObjectId, dfmObjectType, dfmObjectFullName,
				dfmObjectStatus, dfmEventSourceProductId,
				dfmHostFullName, dfmCommentFields,
				dfmPhysicalHostId, dfmPhysicalHostFullName
			}
	DESCRIPTION
		"The port on the fibre channel switch is online."
	::= 10333

	dfmEvtSnapvaultRelationshipCreated		TRAP-TYPE
	ENTERPRISE				netappDataFabricManager
	VARIABLES	{
				dfmSerialNumber, dfmEventSourceSerialNumber,
				dfmEventId, dfmEventName, dfmEventSeverity,
				dfmEventTimestamp, dfmEventMessage, 
				dfmEventMessageDetails,
				dfmEventSourceId, dfmEventSourceTable,
				dfmObjectId, dfmObjectType, dfmObjectFullName,
				dfmObjectStatus, dfmEventSourceProductId,
				dfmHostFullName, dfmCommentFields,
				dfmPhysicalHostId, dfmPhysicalHostFullName
			}
	DESCRIPTION
		"A new backup relationship has been created by dfm."
	::= 10334

	dfmEvtSnapvaultRelationshipDeleted		TRAP-TYPE
	ENTERPRISE				netappDataFabricManager
	VARIABLES	{
				dfmSerialNumber, dfmEventSourceSerialNumber,
				dfmEventId, dfmEventName, dfmEventSeverity,
				dfmEventTimestamp, dfmEventMessage, 
				dfmEventMessageDetails,
				dfmEventSourceId, dfmEventSourceTable,
				dfmObjectId, dfmObjectType, dfmObjectFullName,
				dfmObjectStatus, dfmEventSourceProductId,
				dfmHostFullName, dfmCommentFields,
				dfmPhysicalHostId, dfmPhysicalHostFullName
			}
	DESCRIPTION
		"A backup relationship that DFM has been managing is no 
		longer present."
	::= 10335
	

	dfmEvtSnapvaultRelationshipModified		TRAP-TYPE
	ENTERPRISE				netappDataFabricManager
	VARIABLES	{
				dfmSerialNumber, dfmEventSourceSerialNumber,
				dfmEventId, dfmEventName, dfmEventSeverity,
				dfmEventTimestamp, dfmEventMessage, 
				dfmEventMessageDetails,
				dfmEventSourceId, dfmEventSourceTable,
				dfmObjectId, dfmObjectType, dfmObjectFullName,
				dfmObjectStatus, dfmEventSourceProductId,
				dfmHostFullName, dfmCommentFields,
				dfmPhysicalHostId, dfmPhysicalHostFullName
			}
	DESCRIPTION
		"DFM has modified a backup relationship it maintains."
	::= 10336
	
	dfmEvtSnapvaultReplicaDateOk		TRAP-TYPE
	ENTERPRISE				netappDataFabricManager
	VARIABLES	{
				dfmSerialNumber, dfmEventSourceSerialNumber,
				dfmEventId, dfmEventName, dfmEventSeverity,
				dfmEventTimestamp, dfmEventMessage, 
				dfmEventMessageDetails,
				dfmEventSourceId, dfmEventSourceTable,
				dfmObjectId, dfmObjectType, dfmObjectFullName,
				dfmObjectStatus, dfmEventSourceProductId,
				dfmHostFullName, dfmCommentFields,
				dfmPhysicalHostId, dfmPhysicalHostFullName
			}
	DESCRIPTION
		"DFM has determined that the lag for this backup 
		relationship is below the threshold."
	::= 10337
	
	dfmEvtSnapvaultReplicaNearlyOutOfDate		TRAP-TYPE
	ENTERPRISE				netappDataFabricManager
	VARIABLES	{
				dfmSerialNumber, dfmEventSourceSerialNumber,
				dfmEventId, dfmEventName, dfmEventSeverity,
				dfmEventTimestamp, dfmEventMessage, 
				dfmEventMessageDetails,
				dfmEventSourceId, dfmEventSourceTable,
				dfmObjectId, dfmObjectType, dfmObjectFullName,
				dfmObjectStatus, dfmEventSourceProductId,
				dfmHostFullName, dfmCommentFields,
				dfmPhysicalHostId, dfmPhysicalHostFullName
			}
	DESCRIPTION
		"DFM has determined that the lag for this backup 
		relationship is close to exceeding the threshold and will
		soon be out of date."
	::= 10338
	
	dfmEvtSnapvaultReplicaOutOfDate		TRAP-TYPE
	ENTERPRISE				netappDataFabricManager
	VARIABLES	{
				dfmSerialNumber, dfmEventSourceSerialNumber,
				dfmEventId, dfmEventName, dfmEventSeverity,
				dfmEventTimestamp, dfmEventMessage, 
				dfmEventMessageDetails,
				dfmEventSourceId, dfmEventSourceTable,
				dfmObjectId, dfmObjectType, dfmObjectFullName,
				dfmObjectStatus, dfmEventSourceProductId,
				dfmHostFullName, dfmCommentFields,
				dfmPhysicalHostId, dfmPhysicalHostFullName
			}
	DESCRIPTION
		"DFM has determined that the lag for this backup 
		relationship is out of date."
	::= 10339
	
	dfmEvtSnapvaultBackupCompleted		TRAP-TYPE
	ENTERPRISE				netappDataFabricManager
	VARIABLES	{
				dfmSerialNumber, dfmEventSourceSerialNumber,
				dfmEventId, dfmEventName, dfmEventSeverity,
				dfmEventTimestamp, dfmEventMessage, 
				dfmEventMessageDetails,
				dfmEventSourceId, dfmEventSourceTable,
				dfmObjectId, dfmObjectType, dfmObjectFullName,
				dfmObjectStatus, dfmEventSourceProductId,
				dfmHostFullName, dfmCommentFields,
				dfmPhysicalHostId, dfmPhysicalHostFullName
			}
	DESCRIPTION
		"A backup of an established relationship has been
		successfully performed by DFM."
	::= 10340
	
	dfmEvtSnapvaultBackupAborted		TRAP-TYPE
	ENTERPRISE				netappDataFabricManager
	VARIABLES	{
				dfmSerialNumber, dfmEventSourceSerialNumber,
				dfmEventId, dfmEventName, dfmEventSeverity,
				dfmEventTimestamp, dfmEventMessage, 
				dfmEventMessageDetails,
				dfmEventSourceId, dfmEventSourceTable,
				dfmObjectId, dfmObjectType, dfmObjectFullName,
				dfmObjectStatus, dfmEventSourceProductId,
				dfmHostFullName, dfmCommentFields,
				dfmPhysicalHostId, dfmPhysicalHostFullName
			}
	DESCRIPTION
		"A backup has been aborted."
	::= 10341
	
	dfmEvtSnapvaultBackupFailed		TRAP-TYPE
	ENTERPRISE				netappDataFabricManager
	VARIABLES	{
				dfmSerialNumber, dfmEventSourceSerialNumber,
				dfmEventId, dfmEventName, dfmEventSeverity,
				dfmEventTimestamp, dfmEventMessage, 
				dfmEventMessageDetails,
				dfmEventSourceId, dfmEventSourceTable,
				dfmObjectId, dfmObjectType, dfmObjectFullName,
				dfmObjectStatus, dfmEventSourceProductId,
				dfmHostFullName, dfmCommentFields,
				dfmPhysicalHostId, dfmPhysicalHostFullName
			}
	DESCRIPTION
		"A backup has failed."
	::= 10342
	
	dfmEvtSnapvaultRestoreCompleted		TRAP-TYPE
	ENTERPRISE				netappDataFabricManager
	VARIABLES	{
				dfmSerialNumber, dfmEventSourceSerialNumber,
				dfmEventId, dfmEventName, dfmEventSeverity,
				dfmEventTimestamp, dfmEventMessage, 
				dfmEventMessageDetails,
				dfmEventSourceId, dfmEventSourceTable,
				dfmObjectId, dfmObjectType, dfmObjectFullName,
				dfmObjectStatus, dfmEventSourceProductId,
				dfmHostFullName, dfmCommentFields,
				dfmPhysicalHostId, dfmPhysicalHostFullName
			}
	DESCRIPTION
		"A restore has been successfully performed by DFM."
	::= 10343
	
	dfmEvtSnapvaultRestoreAborted		TRAP-TYPE
	ENTERPRISE				netappDataFabricManager
	VARIABLES	{
				dfmSerialNumber, dfmEventSourceSerialNumber,
				dfmEventId, dfmEventName, dfmEventSeverity,
				dfmEventTimestamp, dfmEventMessage, 
				dfmEventMessageDetails,
				dfmEventSourceId, dfmEventSourceTable,
				dfmObjectId, dfmObjectType, dfmObjectFullName,
				dfmObjectStatus, dfmEventSourceProductId,
				dfmHostFullName, dfmCommentFields,
				dfmPhysicalHostId, dfmPhysicalHostFullName
			}
	DESCRIPTION
		"A restore has been aborted."
	::= 10344
	
	dfmEvtSnapvaultRestoreFailed		TRAP-TYPE
	ENTERPRISE				netappDataFabricManager
	VARIABLES	{
				dfmSerialNumber, dfmEventSourceSerialNumber,
				dfmEventId, dfmEventName, dfmEventSeverity,
				dfmEventTimestamp, dfmEventMessage, 
				dfmEventMessageDetails,
				dfmEventSourceId, dfmEventSourceTable,
				dfmObjectId, dfmObjectType, dfmObjectFullName,
				dfmObjectStatus, dfmEventSourceProductId,
				dfmHostFullName, dfmCommentFields,
				dfmPhysicalHostId, dfmPhysicalHostFullName
			}
	DESCRIPTION
		"A restore has failed."
	::= 10345


	dfmEvtSnapvaultRelationshipDiscovered		TRAP-TYPE
	ENTERPRISE				netappDataFabricManager
	VARIABLES	{
				dfmSerialNumber, dfmEventSourceSerialNumber,
				dfmEventId, dfmEventName, dfmEventSeverity,
				dfmEventTimestamp, dfmEventMessage, 
				dfmEventMessageDetails,
				dfmEventSourceId, dfmEventSourceTable,
				dfmObjectId, dfmObjectType, dfmObjectFullName,
				dfmObjectStatus, dfmEventSourceProductId,
				dfmHostFullName, dfmCommentFields,
				dfmPhysicalHostId, dfmPhysicalHostFullName
			}
	DESCRIPTION
		"A new backup relationship has been discovered by dfm."
	::= 10346

	dfmEvtSnapvaultRelationshipCreateFailed	TRAP-TYPE
	ENTERPRISE				netappDataFabricManager
	VARIABLES	{
				dfmSerialNumber, dfmEventSourceSerialNumber,
				dfmEventId, dfmEventName, dfmEventSeverity,
				dfmEventTimestamp, dfmEventMessage, 
				dfmEventMessageDetails,
				dfmEventSourceId,
				dfmObjectId, dfmObjectType, dfmObjectFullName,
				dfmObjectStatus, dfmEventSourceProductId,
				dfmHostFullName,
				dfmPhysicalHostId, dfmPhysicalHostFullName
			}
	DESCRIPTION
		"A backup relationship creation by dfm failed."
	::= 10347

	dfmEvtSnapvaultRelationshipCreateAborted	TRAP-TYPE
	ENTERPRISE				netappDataFabricManager
	VARIABLES	{
				dfmSerialNumber, dfmEventSourceSerialNumber,
				dfmEventId, dfmEventName, dfmEventSeverity,
				dfmEventTimestamp, dfmEventMessage, 
				dfmEventMessageDetails,
				dfmEventSourceId,
				dfmObjectId, dfmObjectType, dfmObjectFullName,
				dfmObjectStatus, dfmEventSourceProductId,
				dfmHostFullName,
				dfmPhysicalHostId, dfmPhysicalHostFullName
			}
	DESCRIPTION
		"A backup relationship creation by dfm aborted."
	::= 10348

	dfmEvtSnapvaultRelationshipDeleteFailed	TRAP-TYPE
	ENTERPRISE				netappDataFabricManager
	VARIABLES	{
				dfmSerialNumber, dfmEventSourceSerialNumber,
				dfmEventId, dfmEventName, dfmEventSeverity,
				dfmEventTimestamp, dfmEventMessage, 
				dfmEventMessageDetails,
				dfmEventSourceId,
				dfmObjectId, dfmObjectType, dfmObjectFullName,
				dfmObjectStatus, dfmEventSourceProductId,
				dfmHostFullName,
				dfmPhysicalHostId, dfmPhysicalHostFullName
			}
	DESCRIPTION
		"A backup relationship deletion by dfm failed."
	::= 10349

	dfmEvtSnapvaultRelationshipDeleteAborted	TRAP-TYPE
	ENTERPRISE				netappDataFabricManager
	VARIABLES	{
				dfmSerialNumber, dfmEventSourceSerialNumber,
				dfmEventId, dfmEventName, dfmEventSeverity,
				dfmEventTimestamp, dfmEventMessage, 
				dfmEventMessageDetails,
				dfmEventSourceId,
				dfmObjectId, dfmObjectType, dfmObjectFullName,
				dfmObjectStatus, dfmEventSourceProductId,
				dfmHostFullName,
				dfmPhysicalHostId, dfmPhysicalHostFullName
			}
	DESCRIPTION
		"A backup relationship deletion by dfm aborted."
	::= 10350
	--
	-- event for testing alarm (event source is management station)
	--

	dfmEvtTestAlarm	TRAP-TYPE
	ENTERPRISE		netappDataFabricManager
	VARIABLES	{
				dfmSerialNumber, dfmEventSourceSerialNumber,
				dfmEventId, dfmEventName, dfmEventSeverity,
				dfmEventTimestamp, dfmEventMessage, 
				dfmEventMessageDetails,
				dfmEventSourceId, dfmEventSourceTable,
				dfmObjectId, dfmObjectType, dfmObjectFullName,
				dfmObjectStatus, dfmEventSourceProductId,
				dfmHostFullName, dfmCommentFields,
				dfmPhysicalHostId, dfmPhysicalHostFullName
			}
	DESCRIPTION	
		"Test event was generated to test operation of an alarm."
	::= 10351

	-- user quota soft limit events

	dfmEvtUserDiskSpaceSoftLimitNotExceeded	TRAP-TYPE
	ENTERPRISE		netappDataFabricManager
	VARIABLES	{
				dfmSerialNumber, dfmEventSourceSerialNumber,
				dfmEventId, dfmEventName, dfmEventSeverity,
				dfmEventTimestamp, dfmEventMessage, 
				dfmEventMessageDetails,
				dfmEventSourceId, dfmEventSourceTable,
				dfmEventSourceProductId
			}
	DESCRIPTION
		"Disk space quota for user has not exceeded the soft limit."
	::= 10361


	dfmEvtUserDiskSpaceSoftLimitExceeded TRAP-TYPE
	ENTERPRISE		netappDataFabricManager
	VARIABLES	{
				dfmSerialNumber, dfmEventSourceSerialNumber,
				dfmEventId, dfmEventName, dfmEventSeverity,
				dfmEventTimestamp, dfmEventMessage, 
				dfmEventMessageDetails,
				dfmEventSourceId, dfmEventSourceTable,
				dfmEventSourceProductId
			}
	DESCRIPTION
		"Disk space quota for user has exceeded the soft limit."
	::= 10362


	dfmEvtUserFilesSoftLimitNotExceeded	TRAP-TYPE
	ENTERPRISE		netappDataFabricManager
	VARIABLES	{
				dfmSerialNumber, dfmEventSourceSerialNumber,
				dfmEventId, dfmEventName, dfmEventSeverity,
				dfmEventTimestamp, dfmEventMessage, 
				dfmEventMessageDetails,
				dfmEventSourceId, dfmEventSourceTable,
				dfmEventSourceProductId
			}
	DESCRIPTION
		"Files quota for user has not exceeded the soft limit."
	::= 10371


	dfmEvtUserFilesSoftLimitExceeded TRAP-TYPE
	ENTERPRISE		netappDataFabricManager
	VARIABLES	{
				dfmSerialNumber, dfmEventSourceSerialNumber,
				dfmEventId, dfmEventName, dfmEventSeverity,
				dfmEventTimestamp, dfmEventMessage, 
				dfmEventMessageDetails,
				dfmEventSourceId, dfmEventSourceTable,
				dfmEventSourceProductId
			}
	DESCRIPTION
		"Files quota for user has exceeded the soft limit."
	::= 10372

	-- SAN Host HBA Port events

	dfmEvtHbaPortOnline			TRAP-TYPE
	ENTERPRISE				netappDataFabricManager
	VARIABLES	{
				dfmSerialNumber, dfmEventSourceSerialNumber,
				dfmEventId, dfmEventName, dfmEventSeverity,
				dfmEventTimestamp, dfmEventMessage, 
				dfmEventMessageDetails,
				dfmEventSourceId, dfmEventSourceTable,
				dfmObjectId, dfmObjectType, dfmObjectFullName,
				dfmObjectStatus, dfmEventSourceProductId,
				dfmHostFullName, dfmCommentFields,
				dfmPhysicalHostId, dfmPhysicalHostFullName
			}
	DESCRIPTION
		"The HBA port on the SAN host is online."
	::= 10373

	dfmEvtHbaPortOffline			TRAP-TYPE
	ENTERPRISE				netappDataFabricManager
	VARIABLES	{
				dfmSerialNumber, dfmEventSourceSerialNumber,
				dfmEventId, dfmEventName, dfmEventSeverity,
				dfmEventTimestamp, dfmEventMessage, 
				dfmEventMessageDetails,
				dfmEventSourceId, dfmEventSourceTable,
				dfmObjectId, dfmObjectType, dfmObjectFullName,
				dfmObjectStatus, dfmEventSourceProductId,
				dfmHostFullName, dfmCommentFields,
				dfmPhysicalHostId, dfmPhysicalHostFullName
			}
	DESCRIPTION
		"The HBA port on the SAN host is offline or not functioning."
	::= 10374

	dfmEvtHbaPortError			TRAP-TYPE
	ENTERPRISE				netappDataFabricManager
	VARIABLES	{
				dfmSerialNumber, dfmEventSourceSerialNumber,
				dfmEventId, dfmEventName, dfmEventSeverity,
				dfmEventTimestamp, dfmEventMessage, 
				dfmEventMessageDetails,
				dfmEventSourceId, dfmEventSourceTable,
				dfmObjectId, dfmObjectType, dfmObjectFullName,
				dfmObjectStatus, dfmEventSourceProductId,
				dfmHostFullName, dfmCommentFields,
				dfmPhysicalHostId, dfmPhysicalHostFullName
			}
	DESCRIPTION
		"The HBA port on the SAN host has errors."
	::= 10375

	dfmEvtSanHostLunChanged			TRAP-TYPE
	ENTERPRISE				netappDataFabricManager
	VARIABLES	{
				dfmSerialNumber, dfmEventSourceSerialNumber,
				dfmEventId, dfmEventName, dfmEventSeverity,
				dfmEventTimestamp, dfmEventMessage, 
				dfmEventMessageDetails,
				dfmEventSourceId, dfmEventSourceTable,
				dfmObjectId, dfmObjectType, dfmObjectFullName,
				dfmObjectStatus, dfmEventSourceProductId,
				dfmHostFullName, dfmCommentFields,
				dfmPhysicalHostId, dfmPhysicalHostFullName
			}
	DESCRIPTION
		"The lun mapping on the SAN host has changed."
	::= 10376

	dfmEvtHostAgentUp			TRAP-TYPE
	ENTERPRISE				netappDataFabricManager
	VARIABLES	{
				dfmSerialNumber, dfmEventSourceSerialNumber,
				dfmEventId, dfmEventName, dfmEventSeverity,
				dfmEventTimestamp, dfmEventMessage, 
				dfmEventMessageDetails,
				dfmEventSourceId, dfmEventSourceTable,
				dfmObjectId, dfmObjectType, dfmObjectFullName,
				dfmObjectStatus, dfmEventSourceProductId,
				dfmHostFullName, dfmCommentFields,
				dfmPhysicalHostId, dfmPhysicalHostFullName
			}
	DESCRIPTION
		"The host agent software is responding."
	::= 10377

	dfmEvtHostAgentDown			TRAP-TYPE
	ENTERPRISE				netappDataFabricManager
	VARIABLES	{
				dfmSerialNumber, dfmEventSourceSerialNumber,
				dfmEventId, dfmEventName, dfmEventSeverity,
				dfmEventTimestamp, dfmEventMessage, 
				dfmEventMessageDetails,
				dfmEventSourceId, dfmEventSourceTable,
				dfmObjectId, dfmObjectType, dfmObjectFullName,
				dfmObjectStatus, dfmEventSourceProductId,
				dfmHostFullName, dfmCommentFields,
				dfmPhysicalHostId, dfmPhysicalHostFullName
			}
	DESCRIPTION
		"The host agent software is not responding."
	::= 10378

	dfmEvtHbaPortTrafficHigh		TRAP-TYPE
	ENTERPRISE				netappDataFabricManager
	VARIABLES	{
				dfmSerialNumber, dfmEventSourceSerialNumber,
				dfmEventId, dfmEventName, dfmEventSeverity,
				dfmEventTimestamp, dfmEventMessage, 
				dfmEventMessageDetails,
				dfmEventSourceId, dfmEventSourceTable,
				dfmObjectId, dfmObjectType, dfmObjectFullName,
				dfmObjectStatus, dfmEventSourceProductId,
				dfmHostFullName, dfmCommentFields,
				dfmPhysicalHostId, dfmPhysicalHostFullName
			}
	DESCRIPTION
		"The HBA port traffic on the SAN host is too high."
	::= 10379

	dfmEvtHbaPortTrafficOk			TRAP-TYPE
	ENTERPRISE				netappDataFabricManager
	VARIABLES	{
				dfmSerialNumber, dfmEventSourceSerialNumber,
				dfmEventId, dfmEventName, dfmEventSeverity,
				dfmEventTimestamp, dfmEventMessage, 
				dfmEventMessageDetails,
				dfmEventSourceId, dfmEventSourceTable,
				dfmObjectId, dfmObjectType, dfmObjectFullName,
				dfmObjectStatus, dfmEventSourceProductId,
				dfmHostFullName, dfmCommentFields,
				dfmPhysicalHostId, dfmPhysicalHostFullName
			}
	DESCRIPTION
		"The HBA port traffic on the SAN host is ok."
	::= 10380

	--
	-- Snapmirror management events
	--
	
	dfmEvtSnapMirrorInSync			TRAP-TYPE
	ENTERPRISE				netappDataFabricManager
	VARIABLES	{
				dfmSerialNumber, dfmEventSourceSerialNumber,
				dfmEventId, dfmEventName, dfmEventSeverity,
				dfmEventTimestamp, dfmEventMessage, 
				dfmEventMessageDetails,
				dfmEventSourceId, dfmEventSourceTable,
				dfmObjectId, dfmObjectType, dfmObjectFullName,
				dfmObjectStatus, dfmEventSourceProductId,
				dfmHostFullName, dfmCommentFields,
				dfmPhysicalHostId, dfmPhysicalHostFullName
			}
	DESCRIPTION
		"Synchronous Snapmirror retains sync mode."
	::= 10381
	
	dfmEvtSnapMirrorOutOfSync		TRAP-TYPE
	ENTERPRISE				netappDataFabricManager
	VARIABLES	{
				dfmSerialNumber, dfmEventSourceSerialNumber,
				dfmEventId, dfmEventName, dfmEventSeverity,
				dfmEventTimestamp, dfmEventMessage, 
				dfmEventMessageDetails,
				dfmEventSourceId, dfmEventSourceTable,
				dfmObjectId, dfmObjectType, dfmObjectFullName,
				dfmObjectStatus, dfmEventSourceProductId,
				dfmHostFullName, dfmCommentFields,
				dfmPhysicalHostId, dfmPhysicalHostFullName
			}
	DESCRIPTION
		"Synchronous Snapmirror falls out of sync."
	::= 10382
	
	dfmEvtSnapMirrorInitCompleted		TRAP-TYPE
	ENTERPRISE				netappDataFabricManager
	VARIABLES	{
				dfmSerialNumber, dfmEventSourceSerialNumber,
				dfmEventId, dfmEventName, dfmEventSeverity,
				dfmEventTimestamp, dfmEventMessage, 
				dfmEventMessageDetails,
				dfmEventSourceId, dfmEventSourceTable,
				dfmObjectId, dfmObjectType, dfmObjectFullName,
				dfmObjectStatus, dfmEventSourceProductId,
				dfmHostFullName, dfmCommentFields,
				dfmPhysicalHostId, dfmPhysicalHostFullName
			}
	DESCRIPTION
		"Snapmirror initialize completed successfully."
	::= 10383
	
	dfmEvtSnapMirrorInitAborted	TRAP-TYPE
	ENTERPRISE				netappDataFabricManager
	VARIABLES	{
				dfmSerialNumber, dfmEventSourceSerialNumber,
				dfmEventId, dfmEventName, dfmEventSeverity,
				dfmEventTimestamp, dfmEventMessage, 
				dfmEventMessageDetails,
				dfmEventSourceId, dfmEventSourceTable,
				dfmObjectId, dfmObjectType, dfmObjectFullName,
				dfmObjectStatus, dfmEventSourceProductId,
				dfmHostFullName, dfmCommentFields,
				dfmPhysicalHostId, dfmPhysicalHostFullName
			}
	DESCRIPTION
		"Snapmirror initialize aborted."
	::= 10384
	
	dfmEvtSnapMirrorInitFailed	TRAP-TYPE
	ENTERPRISE				netappDataFabricManager
	VARIABLES	{
				dfmSerialNumber, dfmEventSourceSerialNumber,
				dfmEventId, dfmEventName, dfmEventSeverity,
				dfmEventTimestamp, dfmEventMessage, 
				dfmEventMessageDetails,
				dfmEventSourceId, dfmEventSourceTable,
				dfmObjectId, dfmObjectType, dfmObjectFullName,
				dfmObjectStatus, dfmEventSourceProductId,
				dfmHostFullName, dfmCommentFields,
				dfmPhysicalHostId, dfmPhysicalHostFullName
			}
	DESCRIPTION
		"Snapmirror initialize failed."
	::= 10385
	
	dfmEvtSnapMirrorUpdateCompleted		TRAP-TYPE
	ENTERPRISE				netappDataFabricManager
	VARIABLES	{
				dfmSerialNumber, dfmEventSourceSerialNumber,
				dfmEventId, dfmEventName, dfmEventSeverity,
				dfmEventTimestamp, dfmEventMessage, 
				dfmEventMessageDetails,
				dfmEventSourceId, dfmEventSourceTable,
				dfmObjectId, dfmObjectType, dfmObjectFullName,
				dfmObjectStatus, dfmEventSourceProductId,
				dfmHostFullName, dfmCommentFields,
				dfmPhysicalHostId, dfmPhysicalHostFullName
			}
	DESCRIPTION
		"Snapmirror update completed successfully."
	::= 10386
	
	dfmEvtSnapMirrorUpdateAborted		TRAP-TYPE
	ENTERPRISE				netappDataFabricManager
	VARIABLES	{
				dfmSerialNumber, dfmEventSourceSerialNumber,
				dfmEventId, dfmEventName, dfmEventSeverity,
				dfmEventTimestamp, dfmEventMessage, 
				dfmEventMessageDetails,
				dfmEventSourceId, dfmEventSourceTable,
				dfmObjectId, dfmObjectType, dfmObjectFullName,
				dfmObjectStatus, dfmEventSourceProductId,
				dfmHostFullName, dfmCommentFields,
				dfmPhysicalHostId, dfmPhysicalHostFullName
			}
	DESCRIPTION
		"Snapmirror update aborted."
	::= 10387
	
	dfmEvtSnapMirrorUpdateFailed		TRAP-TYPE
	ENTERPRISE				netappDataFabricManager
	VARIABLES	{
				dfmSerialNumber, dfmEventSourceSerialNumber,
				dfmEventId, dfmEventName, dfmEventSeverity,
				dfmEventTimestamp, dfmEventMessage, 
				dfmEventMessageDetails,
				dfmEventSourceId, dfmEventSourceTable,
				dfmObjectId, dfmObjectType, dfmObjectFullName,
				dfmObjectStatus, dfmEventSourceProductId,
				dfmHostFullName, dfmCommentFields,
				dfmPhysicalHostId, dfmPhysicalHostFullName
			}
	DESCRIPTION
		"Snapmirror update failed."
	::= 10388
	
	dfmEvtSnapMirrorBreakCompleted		TRAP-TYPE
	ENTERPRISE				netappDataFabricManager
	VARIABLES	{
				dfmSerialNumber, dfmEventSourceSerialNumber,
				dfmEventId, dfmEventName, dfmEventSeverity,
				dfmEventTimestamp, dfmEventMessage, 
				dfmEventMessageDetails,
				dfmEventSourceId, dfmEventSourceTable,
				dfmObjectId, dfmObjectType, dfmObjectFullName,
				dfmObjectStatus, dfmEventSourceProductId,
				dfmHostFullName, dfmCommentFields,
				dfmPhysicalHostId, dfmPhysicalHostFullName
			}
	DESCRIPTION
		"Snapmirror break completed successfully."
	::= 10389
	
	dfmEvtSnapMirrorBreakFailed		TRAP-TYPE
	ENTERPRISE				netappDataFabricManager
	VARIABLES	{
				dfmSerialNumber, dfmEventSourceSerialNumber,
				dfmEventId, dfmEventName, dfmEventSeverity,
				dfmEventTimestamp, dfmEventMessage, 
				dfmEventMessageDetails,
				dfmEventSourceId, dfmEventSourceTable,
				dfmObjectId, dfmObjectType, dfmObjectFullName,
				dfmObjectStatus, dfmEventSourceProductId,
				dfmHostFullName, dfmCommentFields,
				dfmPhysicalHostId, dfmPhysicalHostFullName
			}
	DESCRIPTION
		"Snapmirror break failed."
	::= 10390
	
	dfmEvtSnapMirrorResyncCompleted		TRAP-TYPE
	ENTERPRISE				netappDataFabricManager
	VARIABLES	{
				dfmSerialNumber, dfmEventSourceSerialNumber,
				dfmEventId, dfmEventName, dfmEventSeverity,
				dfmEventTimestamp, dfmEventMessage, 
				dfmEventMessageDetails,
				dfmEventSourceId, dfmEventSourceTable,
				dfmObjectId, dfmObjectType, dfmObjectFullName,
				dfmObjectStatus, dfmEventSourceProductId,
				dfmHostFullName, dfmCommentFields,
				dfmPhysicalHostId, dfmPhysicalHostFullName
			}
	DESCRIPTION
		"Snapmirror resync completed successfully."
	::= 10391
	
	dfmEvtSnapMirrorResyncAborted		TRAP-TYPE
	ENTERPRISE				netappDataFabricManager
	VARIABLES	{
				dfmSerialNumber, dfmEventSourceSerialNumber,
				dfmEventId, dfmEventName, dfmEventSeverity,
				dfmEventTimestamp, dfmEventMessage, 
				dfmEventMessageDetails,
				dfmEventSourceId, dfmEventSourceTable,
				dfmObjectId, dfmObjectType, dfmObjectFullName,
				dfmObjectStatus, dfmEventSourceProductId,
				dfmHostFullName, dfmCommentFields,
				dfmPhysicalHostId, dfmPhysicalHostFullName
			}
	DESCRIPTION
		"Snapmirror resync aborted."
	::= 10392
	
	dfmEvtSnapMirrorResyncFailed		TRAP-TYPE
	ENTERPRISE				netappDataFabricManager
	VARIABLES	{
				dfmSerialNumber, dfmEventSourceSerialNumber,
				dfmEventId, dfmEventName, dfmEventSeverity,
				dfmEventTimestamp, dfmEventMessage, 
				dfmEventMessageDetails,
				dfmEventSourceId, dfmEventSourceTable,
				dfmObjectId, dfmObjectType, dfmObjectFullName,
				dfmObjectStatus, dfmEventSourceProductId,
				dfmHostFullName, dfmCommentFields,
				dfmPhysicalHostId, dfmPhysicalHostFullName
			}
	DESCRIPTION
		"Snapmirror resync failed."
	::= 10393
	
	dfmEvtSnapMirrorQuiesceCompleted	TRAP-TYPE
	ENTERPRISE				netappDataFabricManager
	VARIABLES	{
				dfmSerialNumber, dfmEventSourceSerialNumber,
				dfmEventId, dfmEventName, dfmEventSeverity,
				dfmEventTimestamp, dfmEventMessage, 
				dfmEventMessageDetails,
				dfmEventSourceId, dfmEventSourceTable,
				dfmObjectId, dfmObjectType, dfmObjectFullName,
				dfmObjectStatus, dfmEventSourceProductId,
				dfmHostFullName, dfmCommentFields,
				dfmPhysicalHostId, dfmPhysicalHostFullName
			}
	DESCRIPTION
		"Snapmirror quiesce completed successfully."
	::= 10394
	
	dfmEvtSnapMirrorQuiesceAborted		TRAP-TYPE
	ENTERPRISE				netappDataFabricManager
	VARIABLES	{
				dfmSerialNumber, dfmEventSourceSerialNumber,
				dfmEventId, dfmEventName, dfmEventSeverity,
				dfmEventTimestamp, dfmEventMessage, 
				dfmEventMessageDetails,
				dfmEventSourceId, dfmEventSourceTable,
				dfmObjectId, dfmObjectType, dfmObjectFullName,
				dfmObjectStatus, dfmEventSourceProductId,
				dfmHostFullName, dfmCommentFields,
				dfmPhysicalHostId, dfmPhysicalHostFullName
			}
	DESCRIPTION
		"Snapmirror quiesce aborted."
	::= 10395
	
	dfmEvtSnapMirrorQuiesceFailed		TRAP-TYPE
	ENTERPRISE				netappDataFabricManager
	VARIABLES	{
				dfmSerialNumber, dfmEventSourceSerialNumber,
				dfmEventId, dfmEventName, dfmEventSeverity,
				dfmEventTimestamp, dfmEventMessage, 
				dfmEventMessageDetails,
				dfmEventSourceId, dfmEventSourceTable,
				dfmObjectId, dfmObjectType, dfmObjectFullName,
				dfmObjectStatus, dfmEventSourceProductId,
				dfmHostFullName, dfmCommentFields,
				dfmPhysicalHostId, dfmPhysicalHostFullName
			}
	DESCRIPTION
		"Snapmirror quiesce failed."
	::= 10396
	
	dfmEvtSnapMirrorResumeCompleted		TRAP-TYPE
	ENTERPRISE				netappDataFabricManager
	VARIABLES	{
				dfmSerialNumber, dfmEventSourceSerialNumber,
				dfmEventId, dfmEventName, dfmEventSeverity,
				dfmEventTimestamp, dfmEventMessage, 
				dfmEventMessageDetails,
				dfmEventSourceId, dfmEventSourceTable,
				dfmObjectId, dfmObjectType, dfmObjectFullName,
				dfmObjectStatus, dfmEventSourceProductId,
				dfmHostFullName, dfmCommentFields,
				dfmPhysicalHostId, dfmPhysicalHostFullName
			}
	DESCRIPTION
		"Snapmirror resume completed successfully."
	::= 10397
	
	dfmEvtSnapMirrorResumeFailed		TRAP-TYPE
	ENTERPRISE				netappDataFabricManager
	VARIABLES	{
				dfmSerialNumber, dfmEventSourceSerialNumber,
				dfmEventId, dfmEventName, dfmEventSeverity,
				dfmEventTimestamp, dfmEventMessage, 
				dfmEventMessageDetails,
				dfmEventSourceId, dfmEventSourceTable,
				dfmObjectId, dfmObjectType, dfmObjectFullName,
				dfmObjectStatus, dfmEventSourceProductId,
				dfmHostFullName, dfmCommentFields,
				dfmPhysicalHostId, dfmPhysicalHostFullName
			}
	DESCRIPTION
		"Snapmirror resume failed."
	::= 10398
	
	dfmEvtSnapMirrorAbortCompleted		TRAP-TYPE
	ENTERPRISE				netappDataFabricManager
	VARIABLES	{
				dfmSerialNumber, dfmEventSourceSerialNumber,
				dfmEventId, dfmEventName, dfmEventSeverity,
				dfmEventTimestamp, dfmEventMessage, 
				dfmEventMessageDetails,
				dfmEventSourceId, dfmEventSourceTable,
				dfmObjectId, dfmObjectType, dfmObjectFullName,
				dfmObjectStatus, dfmEventSourceProductId,
				dfmHostFullName, dfmCommentFields,
				dfmPhysicalHostId, dfmPhysicalHostFullName
			}
	DESCRIPTION
		"Snapmirror abort completed successfully."
	::= 10399
	
	dfmEvtSnapMirrorAbortFailed		TRAP-TYPE
	ENTERPRISE				netappDataFabricManager
	VARIABLES	{
				dfmSerialNumber, dfmEventSourceSerialNumber,
				dfmEventId, dfmEventName, dfmEventSeverity,
				dfmEventTimestamp, dfmEventMessage, 
				dfmEventMessageDetails,
				dfmEventSourceId, dfmEventSourceTable,
				dfmObjectId, dfmObjectType, dfmObjectFullName,
				dfmObjectStatus, dfmEventSourceProductId,
				dfmHostFullName, dfmCommentFields,
				dfmPhysicalHostId, dfmPhysicalHostFullName
			}
	DESCRIPTION
		"Snapmirror abort failed."
	::= 10400
	
	dfmEvtSnapMirrorDeleteCompleted		TRAP-TYPE
	ENTERPRISE				netappDataFabricManager
	VARIABLES	{
				dfmSerialNumber, dfmEventSourceSerialNumber,
				dfmEventId, dfmEventName, dfmEventSeverity,
				dfmEventTimestamp, dfmEventMessage, 
				dfmEventMessageDetails,
				dfmEventSourceId, dfmEventSourceTable,
				dfmObjectId, dfmObjectType, dfmObjectFullName,
				dfmObjectStatus, dfmEventSourceProductId,
				dfmHostFullName, dfmCommentFields,
				dfmPhysicalHostId, dfmPhysicalHostFullName
			}
	DESCRIPTION
		"Snapmirror delete completed successfully."
	::= 10401
	
	dfmEvtSnapMirrorDeleteFailed		TRAP-TYPE
	ENTERPRISE				netappDataFabricManager
	VARIABLES	{
				dfmSerialNumber, dfmEventSourceSerialNumber,
				dfmEventId, dfmEventName, dfmEventSeverity,
				dfmEventTimestamp, dfmEventMessage, 
				dfmEventMessageDetails,
				dfmEventSourceId, dfmEventSourceTable,
				dfmObjectId, dfmObjectType, dfmObjectFullName,
				dfmObjectStatus, dfmEventSourceProductId,
				dfmHostFullName, dfmCommentFields,
				dfmPhysicalHostId, dfmPhysicalHostFullName
			}
	DESCRIPTION
		"Snapmirror delete failed."
	::= 10402

	dfmEvtSnapMirrorDeleteAborted		TRAP-TYPE
	ENTERPRISE				netappDataFabricManager
	VARIABLES	{
				dfmSerialNumber, dfmEventSourceSerialNumber,
				dfmEventId, dfmEventName, dfmEventSeverity,
				dfmEventTimestamp, dfmEventMessage, 
				dfmEventMessageDetails,
				dfmEventSourceId,
				dfmObjectId, dfmObjectType, dfmObjectFullName,
				dfmObjectStatus, dfmEventSourceProductId,
				dfmHostFullName,
				dfmPhysicalHostId, dfmPhysicalHostFullName
			}
	DESCRIPTION
		"Snapmirror delete aborted."
	::= 10403

	-- management station automatic throttling events

	dfmEvtMgmtStLoadOk		TRAP-TYPE
	ENTERPRISE			netappDataFabricManager
	VARIABLES	{
				dfmSerialNumber, dfmEventSourceSerialNumber,
				dfmEventId, dfmEventName, dfmEventSeverity,
				dfmEventTimestamp, dfmEventMessage, 
				dfmEventMessageDetails,
				dfmEventSourceId, dfmEventSourceTable,
				dfmObjectId, dfmObjectType, dfmObjectFullName,
				dfmObjectStatus, dfmEventSourceProductId,
				dfmHostFullName, dfmCommentFields,
				dfmPhysicalHostId, dfmPhysicalHostFullName
			}
	DESCRIPTION	
		"Management station load is low enough to enable
		monitoring at full speed."
	::= 10411

	dfmEvtMgmtStLoadTooHigh		TRAP-TYPE
	ENTERPRISE			netappDataFabricManager
	VARIABLES	{
				dfmSerialNumber, dfmEventSourceSerialNumber,
				dfmEventId, dfmEventName, dfmEventSeverity,
				dfmEventTimestamp, dfmEventMessage, 
				dfmEventMessageDetails,
				dfmEventSourceId, dfmEventSourceTable,
				dfmObjectId, dfmObjectType, dfmObjectFullName,
				dfmObjectStatus, dfmEventSourceProductId,
				dfmHostFullName, dfmCommentFields,
				dfmPhysicalHostId, dfmPhysicalHostFullName
			}
	DESCRIPTION	
		"Management station load is high enough that DataFabric
		Manager is scaling back its monitoring to avoid 
		overwhelming the management station."
	::= 10412


	dfmEvtHostSnmpUp	TRAP-TYPE
	ENTERPRISE		netappDataFabricManager
	VARIABLES	{
				dfmSerialNumber, dfmEventSourceSerialNumber,
				dfmEventId, dfmEventName, dfmEventSeverity,
				dfmEventTimestamp, dfmEventMessage, 
				dfmEventMessageDetails,
				dfmEventSourceId, dfmEventSourceTable,
				dfmObjectId, dfmObjectType, dfmObjectFullName,
				dfmObjectStatus, dfmEventSourceProductId,
				dfmHostFullName, dfmCommentFields,
				dfmPhysicalHostId, dfmPhysicalHostFullName
			}
	DESCRIPTION
		"The SNMP Connectivity to the host is Ok."
	::= 10422

	dfmEvtHostSnmpDown	TRAP-TYPE
	ENTERPRISE		netappDataFabricManager
	VARIABLES	{
				dfmSerialNumber, dfmEventSourceSerialNumber,
				dfmEventId, dfmEventName, dfmEventSeverity,
				dfmEventTimestamp, dfmEventMessage, 
				dfmEventMessageDetails,
				dfmEventSourceId, dfmEventSourceTable,
				dfmObjectId, dfmObjectType, dfmObjectFullName,
				dfmObjectStatus, dfmEventSourceProductId,
				dfmHostFullName, dfmCommentFields,
				dfmPhysicalHostId, dfmPhysicalHostFullName
			}
	DESCRIPTION
		"The SNMP Connectivity to the host is Not Ok."
	::= 10423

	dfmEvtEnvEnclOk		TRAP-TYPE
	ENTERPRISE		netappDataFabricManager
	VARIABLES	{
				dfmSerialNumber, dfmEventSourceSerialNumber,
				dfmEventId, dfmEventName, dfmEventSeverity,
				dfmEventTimestamp, dfmEventMessage, 
				dfmEventMessageDetails,
				dfmEventSourceId, dfmEventSourceTable,
				dfmObjectId, dfmObjectType, dfmObjectFullName,
				dfmObjectStatus, dfmEventSourceProductId,
				dfmHostFullName, dfmCommentFields,
				dfmPhysicalHostId, dfmPhysicalHostFullName
			}
	DESCRIPTION
		"The host enclosures are Ok."
	::= 10432

	dfmEvtEnvEnclFailed	TRAP-TYPE
	ENTERPRISE		netappDataFabricManager
	VARIABLES	{
				dfmSerialNumber, dfmEventSourceSerialNumber,
				dfmEventId, dfmEventName, dfmEventSeverity,
				dfmEventTimestamp, dfmEventMessage, 
				dfmEventMessageDetails,
				dfmEventSourceId, dfmEventSourceTable,
				dfmObjectId, dfmObjectType, dfmObjectFullName,
				dfmObjectStatus, dfmEventSourceProductId,
				dfmHostFullName, dfmCommentFields,
				dfmPhysicalHostId, dfmPhysicalHostFullName
			}
	DESCRIPTION
		"One or more enclosures have failed on the host."
	::= 10433

	dfmEvtEnvEnclFound	TRAP-TYPE
	ENTERPRISE		netappDataFabricManager
	VARIABLES	{
				dfmSerialNumber, dfmEventSourceSerialNumber,
				dfmEventId, dfmEventName, dfmEventSeverity,
				dfmEventTimestamp, dfmEventMessage, 
				dfmEventMessageDetails,
				dfmEventSourceId, dfmEventSourceTable,
				dfmObjectId, dfmObjectType, dfmObjectFullName,
				dfmObjectStatus, dfmEventSourceProductId,
				dfmHostFullName, dfmCommentFields,
				dfmPhysicalHostId, dfmPhysicalHostFullName
			}
	DESCRIPTION
		"One or more enclosures were newly found on the host."
	::= 10434

	dfmEvtEnvEnclDissapeared	TRAP-TYPE
	ENTERPRISE		netappDataFabricManager
	VARIABLES	{
				dfmSerialNumber, dfmEventSourceSerialNumber,
				dfmEventId, dfmEventName, dfmEventSeverity,
				dfmEventTimestamp, dfmEventMessage, 
				dfmEventMessageDetails,
				dfmEventSourceId, dfmEventSourceTable,
				dfmObjectId, dfmObjectType, dfmObjectFullName,
				dfmObjectStatus, dfmEventSourceProductId,
				dfmHostFullName, dfmCommentFields,
				dfmPhysicalHostId, dfmPhysicalHostFullName
			}
	DESCRIPTION
		"One or more enclosures dissapeard on the host."
	::= 10435

	dfmEvtEnvEnclInactive	TRAP-TYPE
	ENTERPRISE		netappDataFabricManager
	VARIABLES	{
				dfmSerialNumber, dfmEventSourceSerialNumber,
				dfmEventId, dfmEventName, dfmEventSeverity,
				dfmEventTimestamp, dfmEventMessage, 
				dfmEventMessageDetails,
				dfmEventSourceId, dfmEventSourceTable,
				dfmObjectId, dfmObjectType, dfmObjectFullName,
				dfmObjectStatus, dfmEventSourceProductId,
				dfmHostFullName, dfmCommentFields,
				dfmPhysicalHostId, dfmPhysicalHostFullName
			}
	DESCRIPTION
		"One or more enclosures became inactive on the host."
	::= 10436

	dfmEvtEnvEnclActive	TRAP-TYPE
	ENTERPRISE		netappDataFabricManager
	VARIABLES	{
				dfmSerialNumber, dfmEventSourceSerialNumber,
				dfmEventId, dfmEventName, dfmEventSeverity,
				dfmEventTimestamp, dfmEventMessage, 
				dfmEventMessageDetails,
				dfmEventSourceId, dfmEventSourceTable,
				dfmObjectId, dfmObjectType, dfmObjectFullName,
				dfmObjectStatus, dfmEventSourceProductId,
				dfmHostFullName, dfmCommentFields,
				dfmPhysicalHostId, dfmPhysicalHostFullName
			}
	DESCRIPTION
		"One or more enclosures became active on the host."
	::= 10437

	-- ::= 10441 was used for dfmEvtNetCacheTakeover

	-- ::= 10442 was used for dfmEvtNetCacheGiveback


	-- aggregate events

	dfmEvtAggregateSpaceOk	TRAP-TYPE
	ENTERPRISE		netappDataFabricManager
	VARIABLES	{
				dfmSerialNumber, dfmEventSourceSerialNumber,
				dfmEventId, dfmEventName, dfmEventSeverity,
				dfmEventTimestamp, dfmEventMessage, 
				dfmEventMessageDetails,
				dfmEventSourceId, dfmEventSourceTable,
				dfmObjectId, dfmObjectType, dfmObjectFullName,
				dfmObjectStatus, dfmEventSourceProductId,
				dfmHostFullName, dfmCommentFields,
				dfmPhysicalHostId, dfmPhysicalHostFullName
			}
	DESCRIPTION	
		"The space utilization on the aggregate being
		 managed by DataFabric Manager is below its 
		 'almostFull' threshold. Variable 
		 dfmObjectId identifies the aggregrate."
	::= 10451

	dfmEvtAggregateAlmostFull	TRAP-TYPE
	ENTERPRISE		netappDataFabricManager
	VARIABLES	{
				dfmSerialNumber, dfmEventSourceSerialNumber,
				dfmEventId, dfmEventName, dfmEventSeverity,
				dfmEventTimestamp, dfmEventMessage, 
				dfmEventMessageDetails,
				dfmEventSourceId, dfmEventSourceTable,
				dfmObjectId, dfmObjectType, dfmObjectFullName,
				dfmObjectStatus, dfmEventSourceProductId,
				dfmHostFullName, dfmCommentFields,
				dfmPhysicalHostId, dfmPhysicalHostFullName
			}
	DESCRIPTION	
		"The space utilization by an aggregate 
		 being managed by DataFabric Manager has crossed 
		 'almostFull' threshold. 
		 Variable dfmObjectId identifies the volume."
	::= 10452
	
	dfmEvtAggregateFull	TRAP-TYPE
	ENTERPRISE		netappDataFabricManager
	VARIABLES	{
				dfmSerialNumber, dfmEventSourceSerialNumber,
				dfmEventId, dfmEventName, dfmEventSeverity,
				dfmEventTimestamp, dfmEventMessage, 
				dfmEventMessageDetails,
				dfmEventSourceId, dfmEventSourceTable,
				dfmObjectId, dfmObjectType, dfmObjectFullName,
				dfmObjectStatus, dfmEventSourceProductId,
				dfmHostFullName, dfmCommentFields,
				dfmPhysicalHostId, dfmPhysicalHostFullName
			}
	DESCRIPTION	
		"The space utilization by an aggregate
		 being managed by DataFabric Manager has crossed 
		 'full' threshold.
		 Variable dfmObjectId identifies the aggregate."
	::= 10453
	

	-- aggregate subscription events

	dfmEvtAggregateOvercommitOk	TRAP-TYPE
	ENTERPRISE		netappDataFabricManager
	VARIABLES	{
				dfmSerialNumber, dfmEventSourceSerialNumber,
				dfmEventId, dfmEventName, dfmEventSeverity,
				dfmEventTimestamp, dfmEventMessage, 
				dfmEventMessageDetails,
				dfmEventSourceId, dfmEventSourceTable,
				dfmObjectId, dfmObjectType, dfmObjectFullName,
				dfmObjectStatus, dfmEventSourceProductId,
				dfmHostFullName, dfmCommentFields,
				dfmPhysicalHostId, dfmPhysicalHostFullName
			}
	DESCRIPTION	
		"The aggregate being managed by DataFabric Manager
		 is below its 'almostOvercommitted' threshold. Variable 
		 dfmObjectId identifies the aggregrate."
	::= 10461

	dfmEvtAggregateAlmostOvercommitted	TRAP-TYPE
	ENTERPRISE		netappDataFabricManager
	VARIABLES	{
				dfmSerialNumber, dfmEventSourceSerialNumber,
				dfmEventId, dfmEventName, dfmEventSeverity,
				dfmEventTimestamp, dfmEventMessage, 
				dfmEventMessageDetails,
				dfmEventSourceId, dfmEventSourceTable,
				dfmObjectId, dfmObjectType, dfmObjectFullName,
				dfmObjectStatus, dfmEventSourceProductId,
				dfmHostFullName, dfmCommentFields,
				dfmPhysicalHostId, dfmPhysicalHostFullName
			}
	DESCRIPTION	
		"The aggregate being managed by DataFabric Manager 
		 has crossed the 'almostOvercommitted' threshold. 
		 Variable dfmObjectId identifies the aggregate."
	::= 10462
	
	dfmEvtAggregateOvercommitted	TRAP-TYPE
	
	ENTERPRISE		netappDataFabricManager
	VARIABLES	{
				dfmSerialNumber, dfmEventSourceSerialNumber,
				dfmEventId, dfmEventName, dfmEventSeverity,
				dfmEventTimestamp, dfmEventMessage, 
				dfmEventMessageDetails,
				dfmEventSourceId, dfmEventSourceTable,
				dfmObjectId, dfmObjectType, dfmObjectFullName,
				dfmObjectStatus, dfmEventSourceProductId,
				dfmHostFullName, dfmCommentFields,
				dfmPhysicalHostId, dfmPhysicalHostFullName
			}
	DESCRIPTION	
		"The aggregate being managed by DataFabric Manager 
		 has crossed the 'overcommitted' threshold.
		 Variable dfmObjectId identifies the aggregate."
	::= 10463

	-- Volume clone events

	dfmEvtVolumeCloneDiscovered		TRAP-TYPE
	ENTERPRISE				netappDataFabricManager
	VARIABLES	{
				dfmSerialNumber, dfmEventSourceSerialNumber,
				dfmEventId, dfmEventName, dfmEventSeverity,
				dfmEventTimestamp, dfmEventMessage, 
				dfmEventMessageDetails,
				dfmEventSourceId, dfmEventSourceTable,
				dfmObjectId, dfmObjectType, dfmObjectFullName,
				dfmObjectStatus, dfmEventSourceProductId,
				dfmHostFullName, dfmCommentFields,
				dfmPhysicalHostId, dfmPhysicalHostFullName
			}
	DESCRIPTION
		"A new volume clone has been discovered by dfm."
	::= 10471

	dfmEvtVolumeCloneDeleted		TRAP-TYPE
	ENTERPRISE				netappDataFabricManager
	VARIABLES	{
				dfmSerialNumber, dfmEventSourceSerialNumber,
				dfmEventId, dfmEventName, dfmEventSeverity,
				dfmEventTimestamp, dfmEventMessage, 
				dfmEventMessageDetails,
				dfmEventSourceId, dfmEventSourceTable,
				dfmObjectId, dfmObjectType, dfmObjectFullName,
				dfmObjectStatus, dfmEventSourceProductId,
				dfmHostFullName, dfmCommentFields,
				dfmPhysicalHostId, dfmPhysicalHostFullName
			}
	DESCRIPTION
		"A volume clone that DFM has been managing is no 
		longer present."
	::= 10472
	
	-- Aggregate events

	dfmEvtAggregateDiscovered		TRAP-TYPE
	ENTERPRISE				netappDataFabricManager
	VARIABLES	{
				dfmSerialNumber, dfmEventSourceSerialNumber,
				dfmEventId, dfmEventName, dfmEventSeverity,
				dfmEventTimestamp, dfmEventMessage, 
				dfmEventMessageDetails,
				dfmEventSourceId, dfmEventSourceTable,
				dfmObjectId, dfmObjectType, dfmObjectFullName,
				dfmObjectStatus, dfmEventSourceProductId,
				dfmHostFullName, dfmCommentFields,
				dfmPhysicalHostId, dfmPhysicalHostFullName
			}
	DESCRIPTION
		"A new aggregate has been discovered by dfm."
	::= 10481

	dfmEvtAggregateDeleted		TRAP-TYPE
	ENTERPRISE				netappDataFabricManager
	VARIABLES	{
				dfmSerialNumber, dfmEventSourceSerialNumber,
				dfmEventId, dfmEventName, dfmEventSeverity,
				dfmEventTimestamp, dfmEventMessage, 
				dfmEventMessageDetails,
				dfmEventSourceId, dfmEventSourceTable,
				dfmObjectId, dfmObjectType, dfmObjectFullName,
				dfmObjectStatus, dfmEventSourceProductId,
				dfmHostFullName, dfmCommentFields,
				dfmPhysicalHostId, dfmPhysicalHostFullName
			}
	DESCRIPTION
		"An aggregate that DFM has been managing is no 
		longer present."
	::= 10482

	-- Trap events
	
	dfmEvtTrapListenerFailed	TRAP-TYPE
	ENTERPRISE		netappDataFabricManager
	VARIABLES	{
				dfmSerialNumber, dfmEventSourceSerialNumber,
				dfmEventId, dfmEventName, dfmEventSeverity,
				dfmEventTimestamp, dfmEventMessage, 
				dfmEventMessageDetails,
				dfmEventSourceId, dfmEventSourceTable,
				dfmObjectId, dfmObjectType, dfmObjectFullName,
				dfmObjectStatus, dfmEventSourceProductId,
				dfmHostFullName, dfmCommentFields,
				dfmPhysicalHostId, dfmPhysicalHostFullName
			}
	DESCRIPTION
		"Trap Listener failed to start may be due to port 
		conflict."
	::= 10491
	
	dfmEvtTrapListenerOk	TRAP-TYPE
	ENTERPRISE		netappDataFabricManager
	VARIABLES	{
				dfmSerialNumber, dfmEventSourceSerialNumber,
				dfmEventId, dfmEventName, dfmEventSeverity,
				dfmEventTimestamp, dfmEventMessage, 
				dfmEventMessageDetails,
				dfmEventSourceId, dfmEventSourceTable,
				dfmObjectId, dfmObjectType, dfmObjectFullName,
				dfmObjectStatus, dfmEventSourceProductId,
				dfmHostFullName, dfmCommentFields,
				dfmPhysicalHostId, dfmPhysicalHostFullName
			}
	DESCRIPTION
		"Startup of Trap Listener is Ok."
	::= 10492

	dfmEvtHostColdStart		TRAP-TYPE
	ENTERPRISE		netappDataFabricManager
	VARIABLES	{
				dfmSerialNumber, dfmEventSourceSerialNumber,
				dfmEventId, dfmEventName, dfmEventSeverity,
				dfmEventTimestamp, dfmEventMessage, 
				dfmEventMessageDetails,
				dfmEventSourceId, dfmEventSourceTable,
				dfmObjectId, dfmObjectType, dfmObjectFullName,
				dfmObjectStatus, dfmEventSourceProductId,
				dfmHostFullName, dfmCommentFields,
				dfmPhysicalHostId, dfmPhysicalHostFullName
			}
	DESCRIPTION
		"Host was possibly restarted."
	::= 10501

	dfmEvtEmergencyTrap		TRAP-TYPE
	ENTERPRISE		netappDataFabricManager
	VARIABLES	{
				dfmSerialNumber, dfmEventSourceSerialNumber,
				dfmEventId, dfmEventName, dfmEventSeverity,
				dfmEventTimestamp, dfmEventMessage, 
				dfmEventMessageDetails,
				dfmEventSourceId, dfmEventSourceTable,
				dfmObjectId, dfmObjectType, dfmObjectFullName,
				dfmObjectStatus, dfmEventSourceProductId,
				dfmHostFullName, dfmCommentFields,
				dfmPhysicalHostId, dfmPhysicalHostFullName
			}
	DESCRIPTION
		"DFM received an emergency trap from an appliance."
	::= 10511
	
	dfmEvtAlertTrap		TRAP-TYPE
	ENTERPRISE		netappDataFabricManager
	VARIABLES	{
				dfmSerialNumber, dfmEventSourceSerialNumber,
				dfmEventId, dfmEventName, dfmEventSeverity,
				dfmEventTimestamp, dfmEventMessage, 
				dfmEventMessageDetails,
				dfmEventSourceId, dfmEventSourceTable,
				dfmObjectId, dfmObjectType, dfmObjectFullName,
				dfmObjectStatus, dfmEventSourceProductId,
				dfmHostFullName, dfmCommentFields,
				dfmPhysicalHostId, dfmPhysicalHostFullName
			}
	DESCRIPTION
		"DFM received an alert trap from an appliance."
	::= 10521

	dfmEvtCriticalTrap		TRAP-TYPE
	ENTERPRISE		netappDataFabricManager
	VARIABLES	{
				dfmSerialNumber, dfmEventSourceSerialNumber,
				dfmEventId, dfmEventName, dfmEventSeverity,
				dfmEventTimestamp, dfmEventMessage, 
				dfmEventMessageDetails,
				dfmEventSourceId, dfmEventSourceTable,
				dfmObjectId, dfmObjectType, dfmObjectFullName,
				dfmObjectStatus, dfmEventSourceProductId,
				dfmHostFullName, dfmCommentFields,
				dfmPhysicalHostId, dfmPhysicalHostFullName
			}
	DESCRIPTION
		"DFM received a critical trap from an appliance."
	::= 10531

	dfmEvtErrorTrap		TRAP-TYPE
	ENTERPRISE		netappDataFabricManager
	VARIABLES	{
				dfmSerialNumber, dfmEventSourceSerialNumber,
				dfmEventId, dfmEventName, dfmEventSeverity,
				dfmEventTimestamp, dfmEventMessage, 
				dfmEventMessageDetails,
				dfmEventSourceId, dfmEventSourceTable,
				dfmObjectId, dfmObjectType, dfmObjectFullName,
				dfmObjectStatus, dfmEventSourceProductId,
				dfmHostFullName, dfmCommentFields,
				dfmPhysicalHostId, dfmPhysicalHostFullName
			}
	DESCRIPTION
		"DFM received an error trap from an appliance."
	::= 10541

	dfmEvtWarningTrap		TRAP-TYPE
	ENTERPRISE		netappDataFabricManager
	VARIABLES	{
				dfmSerialNumber, dfmEventSourceSerialNumber,
				dfmEventId, dfmEventName, dfmEventSeverity,
				dfmEventTimestamp, dfmEventMessage, 
				dfmEventMessageDetails,
				dfmEventSourceId, dfmEventSourceTable,
				dfmObjectId, dfmObjectType, dfmObjectFullName,
				dfmObjectStatus, dfmEventSourceProductId,
				dfmHostFullName, dfmCommentFields,
				dfmPhysicalHostId, dfmPhysicalHostFullName
			}
	DESCRIPTION
		"DFM received a warning trap from an appliance."
	::= 10551

	dfmEvtNotificationTrap		TRAP-TYPE
	ENTERPRISE		netappDataFabricManager
	VARIABLES	{
				dfmSerialNumber, dfmEventSourceSerialNumber,
				dfmEventId, dfmEventName, dfmEventSeverity,
				dfmEventTimestamp, dfmEventMessage, 
				dfmEventMessageDetails,
				dfmEventSourceId, dfmEventSourceTable,
				dfmObjectId, dfmObjectType, dfmObjectFullName,
				dfmObjectStatus, dfmEventSourceProductId,
				dfmHostFullName, dfmCommentFields,
				dfmPhysicalHostId, dfmPhysicalHostFullName
			}
	DESCRIPTION
		"DFM received a notification trap from an appliance."
	::= 10561

	dfmEvtInformationTrap		TRAP-TYPE
	ENTERPRISE		netappDataFabricManager
	VARIABLES	{
				dfmSerialNumber, dfmEventSourceSerialNumber,
				dfmEventId, dfmEventName, dfmEventSeverity,
				dfmEventTimestamp, dfmEventMessage, 
				dfmEventMessageDetails,
				dfmEventSourceId, dfmEventSourceTable,
				dfmObjectId, dfmObjectType, dfmObjectFullName,
				dfmObjectStatus, dfmEventSourceProductId,
				dfmHostFullName, dfmCommentFields,
				dfmPhysicalHostId, dfmPhysicalHostFullName
			}
	DESCRIPTION
		"DFM received an information trap from an appliance."
	::= 10571
	
	-- Interface events

	dfmEvtIfAdminStatusUp		TRAP-TYPE
	ENTERPRISE		netappDataFabricManager
	VARIABLES	{
				dfmSerialNumber, dfmEventSourceSerialNumber,
				dfmEventId, dfmEventName, dfmEventSeverity,
				dfmEventTimestamp, dfmEventMessage, 
				dfmEventMessageDetails,
				dfmEventSourceId, dfmEventSourceTable,
				dfmObjectId, dfmObjectType, dfmObjectFullName,
				dfmObjectStatus, dfmEventSourceProductId,
				dfmHostFullName, dfmCommentFields,
				dfmPhysicalHostId, dfmPhysicalHostFullName
			}
	DESCRIPTION
		"Status of the Interface of an appliance that DFM has been 
		managing is Up."
	::= 10581

	dfmEvtIfAdminStatusDown		TRAP-TYPE
	ENTERPRISE		netappDataFabricManager
	VARIABLES	{
				dfmSerialNumber, dfmEventSourceSerialNumber,
				dfmEventId, dfmEventName, dfmEventSeverity,
				dfmEventTimestamp, dfmEventMessage, 
				dfmEventMessageDetails,
				dfmEventSourceId, dfmEventSourceTable,
				dfmObjectId, dfmObjectType, dfmObjectFullName,
				dfmObjectStatus, dfmEventSourceProductId,
				dfmHostFullName, dfmCommentFields,
				dfmPhysicalHostId, dfmPhysicalHostFullName
			}
	DESCRIPTION
		"Status of the Interface of an appliance that DFM has been 
		managing is Down."
	::= 10582
	
	dfmEvtIfAdminStatusTesting	TRAP-TYPE
	ENTERPRISE		netappDataFabricManager
	VARIABLES	{
				dfmSerialNumber, dfmEventSourceSerialNumber,
				dfmEventId, dfmEventName, dfmEventSeverity,
				dfmEventTimestamp, dfmEventMessage, 
				dfmEventMessageDetails,
				dfmEventSourceId, dfmEventSourceTable,
				dfmObjectId, dfmObjectType, dfmObjectFullName,
				dfmObjectStatus, dfmEventSourceProductId,
				dfmHostFullName, dfmCommentFields,
				dfmPhysicalHostId, dfmPhysicalHostFullName
			}
	DESCRIPTION
		"Status of the Interface of an appliance that DFM has been 
		managing is Testing."
	::= 10583
	
	dfmEvtIfAdminStatusUnknown	TRAP-TYPE
	ENTERPRISE		netappDataFabricManager
	VARIABLES	{
				dfmSerialNumber, dfmEventSourceSerialNumber,
				dfmEventId, dfmEventName, dfmEventSeverity,
				dfmEventTimestamp, dfmEventMessage, 
				dfmEventMessageDetails,
				dfmEventSourceId, dfmEventSourceTable,
				dfmObjectId, dfmObjectType, dfmObjectFullName,
				dfmObjectStatus, dfmEventSourceProductId,
				dfmHostFullName, dfmCommentFields,
				dfmPhysicalHostId, dfmPhysicalHostFullName
			}
	DESCRIPTION
		"Status of the Interface of an appliance that DFM has been 
		managing is Unknown."
	::= 10584

	-- script events

	dfmEvtScriptEmergency		TRAP-TYPE
	ENTERPRISE		netappDataFabricManager
	VARIABLES	{
				dfmSerialNumber, dfmEventSourceSerialNumber,
				dfmEventId, dfmEventName, dfmEventSeverity,
				dfmEventTimestamp, dfmEventMessage, 
				dfmEventMessageDetails,
				dfmEventSourceId, dfmEventSourceTable,
				dfmObjectId, dfmObjectType, dfmObjectFullName,
				dfmObjectStatus, dfmEventSourceProductId,
				dfmHostFullName, dfmCommentFields,
				dfmPhysicalHostId, dfmPhysicalHostFullName
			}
	DESCRIPTION
		"An emergency event generated by a script."
	::= 10591

	dfmEvtScriptCritical		TRAP-TYPE
	ENTERPRISE		netappDataFabricManager
	VARIABLES	{
				dfmSerialNumber, dfmEventSourceSerialNumber,
				dfmEventId, dfmEventName, dfmEventSeverity,
				dfmEventTimestamp, dfmEventMessage, 
				dfmEventMessageDetails,
				dfmEventSourceId, dfmEventSourceTable,
				dfmObjectId, dfmObjectType, dfmObjectFullName,
				dfmObjectStatus, dfmEventSourceProductId,
				dfmHostFullName, dfmCommentFields,
				dfmPhysicalHostId, dfmPhysicalHostFullName
			}
	DESCRIPTION
		"A critical event generated by a script."
	::= 10592

	dfmEvtScriptError		TRAP-TYPE
	ENTERPRISE		netappDataFabricManager
	VARIABLES	{
				dfmSerialNumber, dfmEventSourceSerialNumber,
				dfmEventId, dfmEventName, dfmEventSeverity,
				dfmEventTimestamp, dfmEventMessage, 
				dfmEventMessageDetails,
				dfmEventSourceId, dfmEventSourceTable,
				dfmObjectId, dfmObjectType, dfmObjectFullName,
				dfmObjectStatus, dfmEventSourceProductId,
				dfmHostFullName, dfmCommentFields,
				dfmPhysicalHostId, dfmPhysicalHostFullName
			}
	DESCRIPTION
		"An error event generated by a script."
	::= 10593

	dfmEvtScriptWarning		TRAP-TYPE
	ENTERPRISE		netappDataFabricManager
	VARIABLES	{
				dfmSerialNumber, dfmEventSourceSerialNumber,
				dfmEventId, dfmEventName, dfmEventSeverity,
				dfmEventTimestamp, dfmEventMessage, 
				dfmEventMessageDetails,
				dfmEventSourceId, dfmEventSourceTable,
				dfmObjectId, dfmObjectType, dfmObjectFullName,
				dfmObjectStatus, dfmEventSourceProductId,
				dfmHostFullName, dfmCommentFields,
				dfmPhysicalHostId, dfmPhysicalHostFullName
			}
	DESCRIPTION
		"A warning event generated by a script."
	::= 10594

	dfmEvtScriptInformation		TRAP-TYPE
	ENTERPRISE		netappDataFabricManager
	VARIABLES	{
				dfmSerialNumber, dfmEventSourceSerialNumber,
				dfmEventId, dfmEventName, dfmEventSeverity,
				dfmEventTimestamp, dfmEventMessage, 
				dfmEventMessageDetails,
				dfmEventSourceId, dfmEventSourceTable,
				dfmObjectId, dfmObjectType, dfmObjectFullName,
				dfmObjectStatus, dfmEventSourceProductId,
				dfmHostFullName, dfmCommentFields,
				dfmPhysicalHostId, dfmPhysicalHostFullName
			}
	DESCRIPTION
		"An information event generated by a script."
	::= 10595

	dfmEvtScriptNormal		TRAP-TYPE
	ENTERPRISE		netappDataFabricManager
	VARIABLES	{
				dfmSerialNumber, dfmEventSourceSerialNumber,
				dfmEventId, dfmEventName, dfmEventSeverity,
				dfmEventTimestamp, dfmEventMessage, 
				dfmEventMessageDetails,
				dfmEventSourceId, dfmEventSourceTable,
				dfmObjectId, dfmObjectType, dfmObjectFullName,
				dfmObjectStatus, dfmEventSourceProductId,
				dfmHostFullName, dfmCommentFields,
				dfmPhysicalHostId, dfmPhysicalHostFullName
			}
	DESCRIPTION
		"A normal event generated by a script."
	::= 10596
	
	dfmEvtScriptScheduleEnabled		TRAP-TYPE
	ENTERPRISE		netappDataFabricManager
	VARIABLES	{
				dfmSerialNumber, dfmEventSourceSerialNumber,
				dfmEventId, dfmEventName, dfmEventSeverity,
				dfmEventTimestamp, dfmEventMessage, 
				dfmEventMessageDetails,
				dfmEventSourceId, dfmEventSourceTable,
				dfmObjectId, dfmObjectType, dfmObjectFullName,
				dfmObjectStatus, dfmEventSourceProductId,
				dfmHostFullName, dfmCommentFields,
				dfmPhysicalHostId, dfmPhysicalHostFullName
			}
	DESCRIPTION
		"Script schedule was enabled."
	::= 10597
	
	dfmEvtScriptScheduleDisabled		TRAP-TYPE
	ENTERPRISE		netappDataFabricManager
	VARIABLES	{
				dfmSerialNumber, dfmEventSourceSerialNumber,
				dfmEventId, dfmEventName, dfmEventSeverity,
				dfmEventTimestamp, dfmEventMessage, 
				dfmEventMessageDetails,
				dfmEventSourceId, dfmEventSourceTable,
				dfmObjectId, dfmObjectType, dfmObjectFullName,
				dfmObjectStatus, dfmEventSourceProductId,
				dfmHostFullName, dfmCommentFields,
				dfmPhysicalHostId, dfmPhysicalHostFullName
			}
	DESCRIPTION
		"Script schedule was disabled."
	::= 10598
	
	-- aggr snap reserve events

	dfmEvtAggrSnapReserveOk	TRAP-TYPE
	ENTERPRISE		netappDataFabricManager
	VARIABLES	{
				dfmSerialNumber, dfmEventSourceSerialNumber,
				dfmEventId, dfmEventName, dfmEventSeverity,
				dfmEventTimestamp, dfmEventMessage, 
				dfmEventMessageDetails,
				dfmEventSourceId, dfmEventSourceTable,
				dfmObjectId, dfmObjectType, dfmObjectFullName,
				dfmObjectStatus, dfmEventSourceProductId,
				dfmHostFullName, dfmCommentFields,
				dfmPhysicalHostId, dfmPhysicalHostFullName
			}
	DESCRIPTION	
		"The snapshot reserve usage of an aggregate being
		 managed by DataFabric Manager is below its 
		 'almostFull' threshold. Variable 
		 dfmObjectId identifies the aggregrate."
	::= 10601

	dfmEvtAggrSnapReserveNearlyFull	TRAP-TYPE
	ENTERPRISE		netappDataFabricManager
	VARIABLES	{
				dfmSerialNumber, dfmEventSourceSerialNumber,
				dfmEventId, dfmEventName, dfmEventSeverity,
				dfmEventTimestamp, dfmEventMessage, 
				dfmEventMessageDetails,
				dfmEventSourceId, dfmEventSourceTable,
				dfmObjectId, dfmObjectType, dfmObjectFullName,
				dfmObjectStatus, dfmEventSourceProductId,
				dfmHostFullName, dfmCommentFields,
				dfmPhysicalHostId, dfmPhysicalHostFullName
			}
	DESCRIPTION	
		"The snapshot reserve usage of an aggregate 
		 being managed by DataFabric Manager has crossed 
		 'almostFull' threshold. 
		 Variable dfmObjectId identifies the aggregate."
	::= 10602
	
	dfmEvtAggrSnapReserveFull	TRAP-TYPE
	ENTERPRISE		netappDataFabricManager
	VARIABLES	{
				dfmSerialNumber, dfmEventSourceSerialNumber,
				dfmEventId, dfmEventName, dfmEventSeverity,
				dfmEventTimestamp, dfmEventMessage, 
				dfmEventMessageDetails,
				dfmEventSourceId, dfmEventSourceTable,
				dfmObjectId, dfmObjectType, dfmObjectFullName,
				dfmObjectStatus, dfmEventSourceProductId,
				dfmHostFullName, dfmCommentFields,
				dfmPhysicalHostId, dfmPhysicalHostFullName
			}
	DESCRIPTION	
		"The snapshot reserve usage of an aggregate
		 being managed by DataFabric Manager has crossed 
		 'full' threshold.
		 Variable dfmObjectId identifies the aggregate."
	::= 10603

	-- volume space reserve events

	dfmEvtVolumeSpaceReserveOk	TRAP-TYPE
	ENTERPRISE		netappDataFabricManager
	VARIABLES	{
				dfmSerialNumber, dfmEventSourceSerialNumber,
				dfmEventId, dfmEventName, dfmEventSeverity,
				dfmEventTimestamp, dfmEventMessage, 
				dfmEventMessageDetails,
				dfmEventSourceId, dfmEventSourceTable,
				dfmObjectId, dfmObjectType, dfmObjectFullName,
				dfmObjectStatus, dfmEventSourceProductId,
				dfmHostFullName, dfmCommentFields,
				dfmPhysicalHostId, dfmPhysicalHostFullName
			}
	DESCRIPTION	
		"The space reserve usage of a volume being
		 managed by DataFabric Manager is below its 
		 'almostFull' threshold. Variable 
		 dfmObjectId identifies the volume."
	::= 10611

	dfmEvtVolumeSpaceReserveNearlyFull	TRAP-TYPE
	ENTERPRISE		netappDataFabricManager
	VARIABLES	{
				dfmSerialNumber, dfmEventSourceSerialNumber,
				dfmEventId, dfmEventName, dfmEventSeverity,
				dfmEventTimestamp, dfmEventMessage, 
				dfmEventMessageDetails,
				dfmEventSourceId, dfmEventSourceTable,
				dfmObjectId, dfmObjectType, dfmObjectFullName,
				dfmObjectStatus, dfmEventSourceProductId,
				dfmHostFullName, dfmCommentFields,
				dfmPhysicalHostId, dfmPhysicalHostFullName
			}
	DESCRIPTION	
		"The space reserve usage of a volume being
		 managed by DataFabric Manager has crossed 
		 'almostFull' threshold. Variable 
		 dfmObjectId identifies the volume."
	::= 10612

	dfmEvtVolumeSpaceReserveFull	TRAP-TYPE
	ENTERPRISE		netappDataFabricManager
	VARIABLES	{
				dfmSerialNumber, dfmEventSourceSerialNumber,
				dfmEventId, dfmEventName, dfmEventSeverity,
				dfmEventTimestamp, dfmEventMessage, 
				dfmEventMessageDetails,
				dfmEventSourceId, dfmEventSourceTable,
				dfmObjectId, dfmObjectType, dfmObjectFullName,
				dfmObjectStatus, dfmEventSourceProductId,
				dfmHostFullName, dfmCommentFields,
				dfmPhysicalHostId, dfmPhysicalHostFullName
			}
	DESCRIPTION	
		"The space reserve usage of a volume being
		 managed by DataFabric Manager has crossed 
		 'full' threshold. Variable 
		 dfmObjectId identifies the volume."
	::= 10613

	-- volume first snap events

	dfmEvtVolumeFirstSnapOk		TRAP-TYPE
	ENTERPRISE		netappDataFabricManager
	VARIABLES	{
				dfmSerialNumber, dfmEventSourceSerialNumber,
				dfmEventId, dfmEventName, dfmEventSeverity,
				dfmEventTimestamp, dfmEventMessage, 
				dfmEventMessageDetails,
				dfmEventSourceId, dfmEventSourceTable,
				dfmObjectId, dfmObjectType, dfmObjectFullName,
				dfmObjectStatus, dfmEventSourceProductId,
				dfmHostFullName, dfmCommentFields,
				dfmPhysicalHostId, dfmPhysicalHostFullName
			}
	DESCRIPTION	
		"Possible to take first snapshot of a volume being
		 managed by DataFabric Manager. Space reserve requirement
		 is below its 'almostFull' threshold. Variable 
		 dfmObjectId identifies the volume."
	::= 10621

	dfmEvtVolumeNearlyNoFirstSnap	TRAP-TYPE
	ENTERPRISE		netappDataFabricManager
	VARIABLES	{
				dfmSerialNumber, dfmEventSourceSerialNumber,
				dfmEventId, dfmEventName, dfmEventSeverity,
				dfmEventTimestamp, dfmEventMessage, 
				dfmEventMessageDetails,
				dfmEventSourceId, dfmEventSourceTable,
				dfmObjectId, dfmObjectType, dfmObjectFullName,
				dfmObjectStatus, dfmEventSourceProductId,
				dfmHostFullName, dfmCommentFields,
				dfmPhysicalHostId, dfmPhysicalHostFullName
			}
	DESCRIPTION	
		"Almost not enough space to take first snapshot of a volume
		 being managed by DataFabric Manager. Space reserve
		 requirement has crossed 'almostFull' threshold. Variable
		 dfmObjectId identifies the volume."
	::= 10622

	dfmEvtVolumeNoFirstSnap		TRAP-TYPE
	ENTERPRISE		netappDataFabricManager
	VARIABLES	{
				dfmSerialNumber, dfmEventSourceSerialNumber,
				dfmEventId, dfmEventName, dfmEventSeverity,
				dfmEventTimestamp, dfmEventMessage, 
				dfmEventMessageDetails,
				dfmEventSourceId, dfmEventSourceTable,
				dfmObjectId, dfmObjectType, dfmObjectFullName,
				dfmObjectStatus, dfmEventSourceProductId,
				dfmHostFullName, dfmCommentFields,
				dfmPhysicalHostId, dfmPhysicalHostFullName
			}
	DESCRIPTION	
		"Not possible to take first snapshot of a volume being
		 managed by DataFabric Manager. Space reserve requirement
		 has crossed 'full' threshold. Variable 
		 dfmObjectId identifies the volume."
	::= 10623

	-- volume snapshot events

	dfmEvtVolumeNewSnapshot		TRAP-TYPE
	ENTERPRISE		netappDataFabricManager
	VARIABLES	{
				dfmSerialNumber, dfmEventSourceSerialNumber,
				dfmEventId, dfmEventName, dfmEventSeverity,
				dfmEventTimestamp, dfmEventMessage, 
				dfmEventMessageDetails,
				dfmEventSourceId, dfmEventSourceTable,
				dfmObjectId, dfmObjectType, dfmObjectFullName,
				dfmObjectStatus, dfmEventSourceProductId,
				dfmHostFullName, dfmCommentFields,
				dfmPhysicalHostId, dfmPhysicalHostFullName
			}
	DESCRIPTION	
		"A new snapshot of a volume being
		 managed by DataFabric Manager is discovered. 
		 Variable dfmObjectId identifies the volume."
	::= 10631

	dfmEvtVolumeSnapshotDeleted	TRAP-TYPE
	ENTERPRISE		netappDataFabricManager
	VARIABLES	{
				dfmSerialNumber, dfmEventSourceSerialNumber,
				dfmEventId, dfmEventName, dfmEventSeverity,
				dfmEventTimestamp, dfmEventMessage, 
				dfmEventMessageDetails,
				dfmEventSourceId, dfmEventSourceTable,
				dfmObjectId, dfmObjectType, dfmObjectFullName,
				dfmObjectStatus, dfmEventSourceProductId,
				dfmHostFullName, dfmCommentFields,
				dfmPhysicalHostId, dfmPhysicalHostFullName
			}
	DESCRIPTION	
		"A snapshot of a volume being
		 managed by DataFabric Manager is deleted. 
		 Variable dfmObjectId identifies the volume."
	::= 10632

	-- Storage System Configuration events

	dfmEvtLocalFilerConfigStatusOk	TRAP-TYPE
	ENTERPRISE		netappDataFabricManager
	VARIABLES	{
				dfmSerialNumber, dfmEventSourceSerialNumber,
				dfmEventId, dfmEventName, dfmEventSeverity,
				dfmEventTimestamp, dfmEventMessage, 
				dfmEventMessageDetails,
				dfmEventSourceId, dfmEventSourceTable,
				dfmObjectId, dfmObjectType, dfmObjectFullName,
				dfmObjectStatus, dfmEventSourceProductId,
				dfmHostFullName, dfmCommentFields,
				dfmPhysicalHostId, dfmPhysicalHostFullName
			}
	DESCRIPTION
		"The local configuration on the Storage System being 
		monitored has status value 'ok'."
	::= 10641


	dfmEvtLocalFilerConfigStatusChanged	TRAP-TYPE
	ENTERPRISE			netappDataFabricManager
	VARIABLES	{
				dfmSerialNumber, dfmEventSourceSerialNumber,
				dfmEventId, dfmEventName, dfmEventSeverity,
				dfmEventTimestamp, dfmEventMessage, 
				dfmEventMessageDetails,
				dfmEventSourceId, dfmEventSourceTable,
				dfmObjectId, dfmObjectType, dfmObjectFullName,
				dfmObjectStatus, dfmEventSourceProductId,
				dfmHostFullName, dfmCommentFields,
				dfmPhysicalHostId, dfmPhysicalHostFullName
			}
	DESCRIPTION
		"The local configuration on the Storage System being 
		monitored has status value 'changed'. It was 
		not changed through DataFabric Manager."
	::= 10642


	-- host zapi login events

	dfmEvtFilerLoginOk      TRAP-TYPE
	ENTERPRISE              netappDataFabricManager
	VARIABLES       {
				dfmSerialNumber, dfmEventSourceSerialNumber,
				dfmEventId, dfmEventName, dfmEventSeverity,
				dfmEventTimestamp, dfmEventMessage,
				dfmEventMessageDetails,
				dfmEventSourceId, dfmEventSourceTable,
				dfmObjectId, dfmObjectType, dfmObjectFullName,
				dfmObjectStatus, dfmEventSourceProductId,
				dfmHostFullName, dfmCommentFields,
				dfmPhysicalHostId, dfmPhysicalHostFullName
			}
	DESCRIPTION
		"Login to a storage system managed by DataFabric Manager succeeded."
	::= 10651

	dfmEvtFilerLoginFailed  TRAP-TYPE
	ENTERPRISE              netappDataFabricManager
	VARIABLES       {
				dfmSerialNumber, dfmEventSourceSerialNumber,
				dfmEventId, dfmEventName, dfmEventSeverity,
				dfmEventTimestamp, dfmEventMessage,
				dfmEventMessageDetails,
				dfmEventSourceId, dfmEventSourceTable,
				dfmObjectId, dfmObjectType, dfmObjectFullName,
				dfmObjectStatus, dfmEventSourceProductId,
				dfmHostFullName, dfmCommentFields,
				dfmPhysicalHostId, dfmPhysicalHostFullName
			}
	DESCRIPTION
		"Login to a storage system managed by DataFabric Manager failed."
	::= 10652
	
	-- Ndmp Events

	dfmEvtNdmpStatusUp		TRAP-TYPE
	ENTERPRISE		netappDataFabricManager
	VARIABLES	{
				dfmSerialNumber, dfmEventSourceSerialNumber,
				dfmEventId, dfmEventName, dfmEventSeverity,
				dfmEventTimestamp, dfmEventMessage, 
				dfmEventMessageDetails,
				dfmEventSourceId, dfmEventSourceTable,
				dfmObjectId, dfmObjectType, dfmObjectFullName,
				dfmObjectStatus, dfmEventSourceProductId,
				dfmHostFullName, dfmCommentFields,
				dfmPhysicalHostId, dfmPhysicalHostFullName
			}
	DESCRIPTION
		"An ndmp up event generated ndmp monitor."
	::= 10661

	dfmEvtNdmpStatusDown		TRAP-TYPE
	ENTERPRISE		netappDataFabricManager
	VARIABLES	{
				dfmSerialNumber, dfmEventSourceSerialNumber,
				dfmEventId, dfmEventName, dfmEventSeverity,
				dfmEventTimestamp, dfmEventMessage, 
				dfmEventMessageDetails,
				dfmEventSourceId, dfmEventSourceTable,
				dfmObjectId, dfmObjectType, dfmObjectFullName,
				dfmObjectStatus, dfmEventSourceProductId,
				dfmHostFullName, dfmCommentFields,
				dfmPhysicalHostId, dfmPhysicalHostFullName
			}
	DESCRIPTION
		"An ndmp down event generated ndmp monitor."
	::= 10662


	-- Storage System Configuration Push events

	dfmEvtFilerConfigPushStatusOk	TRAP-TYPE
	ENTERPRISE		netappDataFabricManager
	VARIABLES	{
				dfmSerialNumber, dfmEventSourceSerialNumber,
				dfmEventId, dfmEventName, dfmEventSeverity,
				dfmEventTimestamp, dfmEventMessage, 
				dfmEventMessageDetails,
				dfmEventSourceId, dfmEventSourceTable,
				dfmObjectId, dfmObjectType, dfmObjectFullName,
				dfmObjectStatus, dfmEventSourceProductId,
				dfmHostFullName, dfmCommentFields,
				dfmPhysicalHostId, dfmPhysicalHostFullName
			}
	DESCRIPTION
		"The configuration push on the storage system was successful."
	::= 10671


	dfmEvtFilerConfigPushStatusError	TRAP-TYPE
	ENTERPRISE			netappDataFabricManager
	VARIABLES	{
				dfmSerialNumber, dfmEventSourceSerialNumber,
				dfmEventId, dfmEventName, dfmEventSeverity,
				dfmEventTimestamp, dfmEventMessage, 
				dfmEventMessageDetails,
				dfmEventSourceId, dfmEventSourceTable,
				dfmObjectId, dfmObjectType, dfmObjectFullName,
				dfmObjectStatus, dfmEventSourceProductId,
				dfmHostFullName, dfmCommentFields,
				dfmPhysicalHostId, dfmPhysicalHostFullName
			}
	DESCRIPTION
		"The configuration push on the Storage System failed to  
		push some options."
	::= 10672

	-- vFiler Related Events

	dfmEvtVfilerDiscovered	TRAP-TYPE
	ENTERPRISE		netappDataFabricManager
	VARIABLES	{
				dfmSerialNumber, dfmEventSourceSerialNumber,
				dfmEventId, dfmEventName, dfmEventSeverity,
				dfmEventTimestamp, dfmEventMessage, 
				dfmEventMessageDetails,
				dfmEventSourceId, dfmEventSourceTable,
				dfmObjectId, dfmObjectType, dfmObjectFullName,
				dfmObjectStatus, dfmEventSourceProductId,
				dfmHostFullName, dfmCommentFields,
				dfmPhysicalHostId, dfmPhysicalHostFullName
			}
	DESCRIPTION
		"A vFiler was discovered on a hosting storage system." 
	::= 10681


	dfmEvtVfilerDeleted	TRAP-TYPE
	ENTERPRISE			netappDataFabricManager
	VARIABLES	{
				dfmSerialNumber, dfmEventSourceSerialNumber,
				dfmEventId, dfmEventName, dfmEventSeverity,
				dfmEventTimestamp, dfmEventMessage, 
				dfmEventMessageDetails,
				dfmEventSourceId, dfmEventSourceTable,
				dfmObjectId, dfmObjectType, dfmObjectFullName,
				dfmObjectStatus, dfmEventSourceProductId,
				dfmHostFullName, dfmCommentFields,
				dfmPhysicalHostId, dfmPhysicalHostFullName
			}
	DESCRIPTION
		"A vFiler was deleted on a hosting storage system." 
	::= 10682

	dfmEvtVfilerRenamed	TRAP-TYPE
	ENTERPRISE			netappDataFabricManager
	VARIABLES	{
				dfmSerialNumber, dfmEventSourceSerialNumber,
				dfmEventId, dfmEventName, dfmEventSeverity,
				dfmEventTimestamp, dfmEventMessage, 
				dfmEventMessageDetails,
				dfmEventSourceId, dfmEventSourceTable,
				dfmObjectId, dfmObjectType, dfmObjectFullName,
				dfmObjectStatus, dfmEventSourceProductId,
				dfmHostFullName, dfmCommentFields,
				dfmPhysicalHostId, dfmPhysicalHostFullName
			}
	DESCRIPTION
		"A vFiler was renamed on a hosting storage system." 
	::= 10683

	dfmEvtVfilerStorageUnitAdded TRAP-TYPE
	ENTERPRISE			netappDataFabricManager
	VARIABLES	{
				dfmSerialNumber, dfmEventSourceSerialNumber,
				dfmEventId, dfmEventName, dfmEventSeverity,
				dfmEventTimestamp, dfmEventMessage, 
				dfmEventMessageDetails,
				dfmEventSourceId, dfmEventSourceTable,
				dfmObjectId, dfmObjectType, dfmObjectFullName,
				dfmObjectStatus, dfmEventSourceProductId,
				dfmHostFullName, dfmCommentFields,
				dfmPhysicalHostId, dfmPhysicalHostFullName
			}
	DESCRIPTION
		"A storage unit was added to a vFiler." 
	::= 10684

	dfmEvtVfilerStorageUnitRemoved TRAP-TYPE
	ENTERPRISE			netappDataFabricManager
	VARIABLES	{
				dfmSerialNumber, dfmEventSourceSerialNumber,
				dfmEventId, dfmEventName, dfmEventSeverity,
				dfmEventTimestamp, dfmEventMessage, 
				dfmEventMessageDetails,
				dfmEventSourceId, dfmEventSourceTable,
				dfmObjectId, dfmObjectType, dfmObjectFullName,
				dfmObjectStatus, dfmEventSourceProductId,
				dfmHostFullName, dfmCommentFields,
				dfmPhysicalHostId, dfmPhysicalHostFullName
			}
	DESCRIPTION
		"A storage unit was removed from a vFiler." 
	::= 10685

	dfmEvtVfilerIpAddressAdded TRAP-TYPE
	ENTERPRISE			netappDataFabricManager
	VARIABLES	{
				dfmSerialNumber, dfmEventSourceSerialNumber,
				dfmEventId, dfmEventName, dfmEventSeverity,
				dfmEventTimestamp, dfmEventMessage, 
				dfmEventMessageDetails,
				dfmEventSourceId, dfmEventSourceTable,
				dfmObjectId, dfmObjectType, dfmObjectFullName,
				dfmObjectStatus, dfmEventSourceProductId,
				dfmHostFullName, dfmCommentFields,
				dfmPhysicalHostId, dfmPhysicalHostFullName
			}
	DESCRIPTION
		"An IP Address was added to a vFiler." 
	::= 10686

	dfmEvtVfilerIpAddressRemoved TRAP-TYPE
	ENTERPRISE			netappDataFabricManager
	VARIABLES	{
				dfmSerialNumber, dfmEventSourceSerialNumber,
				dfmEventId, dfmEventName, dfmEventSeverity,
				dfmEventTimestamp, dfmEventMessage, 
				dfmEventMessageDetails,
				dfmEventSourceId, dfmEventSourceTable,
				dfmObjectId, dfmObjectType, dfmObjectFullName,
				dfmObjectStatus, dfmEventSourceProductId,
				dfmHostFullName, dfmCommentFields,
				dfmPhysicalHostId, dfmPhysicalHostFullName
			}
	DESCRIPTION
		"An IP Address was removed from a vFiler." 
	::= 10687

	dfmEvtVfilerHostingFilerLoginOk	 TRAP-TYPE
	ENTERPRISE			netappDataFabricManager
	VARIABLES	{
				dfmSerialNumber, dfmEventSourceSerialNumber,
				dfmEventId, dfmEventName, dfmEventSeverity,
				dfmEventTimestamp, dfmEventMessage, 
				dfmEventMessageDetails,
				dfmEventSourceId, dfmEventSourceTable,
				dfmObjectId, dfmObjectType, dfmObjectFullName,
				dfmObjectStatus, dfmEventSourceProductId,
				dfmHostFullName, dfmCommentFields,
				dfmPhysicalHostId, dfmPhysicalHostFullName
			}
	DESCRIPTION
		"Login succeeded on hosting storage system of vFiler."
	::= 10688

	dfmEvtVfilerHostingFilerLoginFailed TRAP-TYPE
	ENTERPRISE			netappDataFabricManager
	VARIABLES	{
				dfmSerialNumber, dfmEventSourceSerialNumber,
				dfmEventId, dfmEventName, dfmEventSeverity,
				dfmEventTimestamp, dfmEventMessage, 
				dfmEventMessageDetails,
				dfmEventSourceId, dfmEventSourceTable,
				dfmObjectId, dfmObjectType, dfmObjectFullName,
				dfmObjectStatus, dfmEventSourceProductId,
				dfmHostFullName, dfmCommentFields,
				dfmPhysicalHostId, dfmPhysicalHostFullName
			}
	DESCRIPTION
		"Login failed on hosting storage system of vFiler."
	::= 10689
	
	-- Volume and Qtree Growth events

	dfmEvtVolumeGrowthRateAbnormal	TRAP-TYPE
	ENTERPRISE		netappDataFabricManager
	VARIABLES	{
				dfmSerialNumber, dfmEventSourceSerialNumber,
				dfmEventId, dfmEventName, dfmEventSeverity,
				dfmEventTimestamp, dfmEventMessage, 
				dfmEventMessageDetails,
				dfmEventSourceId, dfmEventSourceTable,
				dfmObjectId, dfmObjectType, dfmObjectFullName,
				dfmObjectStatus, dfmEventSourceProductId,
				dfmHostFullName, dfmCommentFields,
				dfmPhysicalHostId, dfmPhysicalHostFullName
			}
	DESCRIPTION
		"The Volume Growth Rate is Abnormal."
	::= 10691

	dfmEvtVolumeGrowthRateOk	TRAP-TYPE
	ENTERPRISE		netappDataFabricManager
	VARIABLES	{
				dfmSerialNumber, dfmEventSourceSerialNumber,
				dfmEventId, dfmEventName, dfmEventSeverity,
				dfmEventTimestamp, dfmEventMessage, 
				dfmEventMessageDetails,
				dfmEventSourceId, dfmEventSourceTable,
				dfmObjectId, dfmObjectType, dfmObjectFullName,
				dfmObjectStatus, dfmEventSourceProductId,
				dfmHostFullName, dfmCommentFields,
				dfmPhysicalHostId, dfmPhysicalHostFullName
			}
	DESCRIPTION
		"The Volume Growth Rate is Normal."
	::= 10692

	dfmEvtQtreeGrowthRateAbnormal	TRAP-TYPE
	ENTERPRISE		netappDataFabricManager
	VARIABLES	{
				dfmSerialNumber, dfmEventSourceSerialNumber,
				dfmEventId, dfmEventName, dfmEventSeverity,
				dfmEventTimestamp, dfmEventMessage, 
				dfmEventMessageDetails,
				dfmEventSourceId, dfmEventSourceTable,
				dfmObjectId, dfmObjectType, dfmObjectFullName,
				dfmObjectStatus, dfmEventSourceProductId,
				dfmHostFullName, dfmCommentFields,
				dfmPhysicalHostId, dfmPhysicalHostFullName
			}
	DESCRIPTION
		"The Qtree Growth Rate is Abnormal."
	::= 10693

	dfmEvtQtreeGrowthRateOk	TRAP-TYPE
	ENTERPRISE		netappDataFabricManager
	VARIABLES	{
				dfmSerialNumber, dfmEventSourceSerialNumber,
				dfmEventId, dfmEventName, dfmEventSeverity,
				dfmEventTimestamp, dfmEventMessage, 
				dfmEventMessageDetails,
				dfmEventSourceId, dfmEventSourceTable,
				dfmObjectId, dfmObjectType, dfmObjectFullName,
				dfmObjectStatus, dfmEventSourceProductId,
				dfmHostFullName, dfmCommentFields,
				dfmPhysicalHostId, dfmPhysicalHostFullName
			}
	DESCRIPTION
		"The Qtree Growth Rate is Normal."
	::= 10694

	-- Snapshot Schedule Events

	dfmEvtSnapSchedModified		TRAP-TYPE
	ENTERPRISE			netappDataFabricManager
	VARIABLES	{
				dfmSerialNumber, dfmEventSourceSerialNumber,
				dfmEventId, dfmEventName, dfmEventSeverity,
				dfmEventTimestamp, dfmEventMessage, 
				dfmEventMessageDetails,
				dfmEventSourceId, dfmEventSourceTable,
				dfmObjectId, dfmObjectType, dfmObjectFullName,
				dfmObjectStatus, dfmEventSourceProductId,
				dfmHostFullName, dfmCommentFields,
				dfmPhysicalHostId, dfmPhysicalHostFullName
			}
	DESCRIPTION
		"The snapshot schedule has been modified on the 
		storage system."
	::= 10701

	dfmEvtSnapSchedSmConflict	TRAP-TYPE
	ENTERPRISE			netappDataFabricManager
	VARIABLES	{
				dfmSerialNumber, dfmEventSourceSerialNumber,
				dfmEventId, dfmEventName, dfmEventSeverity,
				dfmEventTimestamp, dfmEventMessage, 
				dfmEventMessageDetails,
				dfmEventSourceId, dfmEventSourceTable,
				dfmObjectId, dfmObjectType, dfmObjectFullName,
				dfmObjectStatus, dfmEventSourceProductId,
				dfmHostFullName, dfmCommentFields,
				dfmPhysicalHostId, dfmPhysicalHostFullName
			}
	DESCRIPTION
		"The snapshot and snapmirror schedules have conflicts."
	::= 10711

	dfmEvtSnapSchedSmOk		TRAP-TYPE
	ENTERPRISE			netappDataFabricManager
	VARIABLES	{
				dfmSerialNumber, dfmEventSourceSerialNumber,
				dfmEventId, dfmEventName, dfmEventSeverity,
				dfmEventTimestamp, dfmEventMessage, 
				dfmEventMessageDetails,
				dfmEventSourceId, dfmEventSourceTable,
				dfmObjectId, dfmObjectType, dfmObjectFullName,
				dfmObjectStatus, dfmEventSourceProductId,
				dfmHostFullName, dfmCommentFields,
				dfmPhysicalHostId, dfmPhysicalHostFullName
			}
	DESCRIPTION
		"The snapshot and snapmirror schedules have no conflicts."
	::= 10712

	dfmEvtSnapSchedSvConflict	TRAP-TYPE
	ENTERPRISE			netappDataFabricManager
	VARIABLES	{
				dfmSerialNumber, dfmEventSourceSerialNumber,
				dfmEventId, dfmEventName, dfmEventSeverity,
				dfmEventTimestamp, dfmEventMessage, 
				dfmEventMessageDetails,
				dfmEventSourceId, dfmEventSourceTable,
				dfmObjectId, dfmObjectType, dfmObjectFullName,
				dfmObjectStatus, dfmEventSourceProductId,
				dfmHostFullName, dfmCommentFields,
				dfmPhysicalHostId, dfmPhysicalHostFullName
			}
	DESCRIPTION
		"The snapshot and snapvault schedules have conflicts."
	::= 10721

	dfmEvtSnapSchedSvOk		TRAP-TYPE
	ENTERPRISE			netappDataFabricManager
	VARIABLES	{
				dfmSerialNumber, dfmEventSourceSerialNumber,
				dfmEventId, dfmEventName, dfmEventSeverity,
				dfmEventTimestamp, dfmEventMessage, 
				dfmEventMessageDetails,
				dfmEventSourceId, dfmEventSourceTable,
				dfmObjectId, dfmObjectType, dfmObjectFullName,
				dfmObjectStatus, dfmEventSourceProductId,
				dfmHostFullName, dfmCommentFields,
				dfmPhysicalHostId, dfmPhysicalHostFullName
			}
	DESCRIPTION
		"The snapshot and snapvault schedules have no conflicts."
	::= 10722

	dfmEvtTooManySnapshots		TRAP-TYPE
	ENTERPRISE			netappDataFabricManager
	VARIABLES	{
				dfmSerialNumber, dfmEventSourceSerialNumber,
				dfmEventId, dfmEventName, dfmEventSeverity,
				dfmEventTimestamp, dfmEventMessage, 
				dfmEventMessageDetails,
				dfmEventSourceId, dfmEventSourceTable,
				dfmObjectId, dfmObjectType, dfmObjectFullName,
				dfmObjectStatus, dfmEventSourceProductId,
				dfmHostFullName, dfmCommentFields,
				dfmPhysicalHostId, dfmPhysicalHostFullName
			}
	DESCRIPTION
		"Too many snapshots."
	::= 10731

	dfmEvtNotTooManySnapshots	TRAP-TYPE
	ENTERPRISE			netappDataFabricManager
	VARIABLES	{
				dfmSerialNumber, dfmEventSourceSerialNumber,
				dfmEventId, dfmEventName, dfmEventSeverity,
				dfmEventTimestamp, dfmEventMessage, 
				dfmEventMessageDetails,
				dfmEventSourceId, dfmEventSourceTable,
				dfmObjectId, dfmObjectType, dfmObjectFullName,
				dfmObjectStatus, dfmEventSourceProductId,
				dfmHostFullName, dfmCommentFields,
				dfmPhysicalHostId, dfmPhysicalHostFullName
			}
	DESCRIPTION
		"Not Too many snapshots."
	::= 10732

	dfmEvtSnapDisabled		TRAP-TYPE
	ENTERPRISE			netappDataFabricManager
	VARIABLES	{
				dfmSerialNumber, dfmEventSourceSerialNumber,
				dfmEventId, dfmEventName, dfmEventSeverity,
				dfmEventTimestamp, dfmEventMessage, 
				dfmEventMessageDetails,
				dfmEventSourceId, dfmEventSourceTable,
				dfmObjectId, dfmObjectType, dfmObjectFullName,
				dfmObjectStatus, dfmEventSourceProductId,
				dfmHostFullName, dfmCommentFields,
				dfmPhysicalHostId, dfmPhysicalHostFullName
			}
	DESCRIPTION
		"Snapshots Disabled."
	::= 10741

	dfmEvtSnapEnabled		TRAP-TYPE
	ENTERPRISE			netappDataFabricManager
	VARIABLES	{
				dfmSerialNumber, dfmEventSourceSerialNumber,
				dfmEventId, dfmEventName, dfmEventSeverity,
				dfmEventTimestamp, dfmEventMessage, 
				dfmEventMessageDetails,
				dfmEventSourceId, dfmEventSourceTable,
				dfmObjectId, dfmObjectType, dfmObjectFullName,
				dfmObjectStatus, dfmEventSourceProductId,
				dfmHostFullName, dfmCommentFields,
				dfmPhysicalHostId, dfmPhysicalHostFullName
			}
	DESCRIPTION
		"Snapshots Enabled."
	::= 10742

	-- Database backup related events

	dfmEvtDatabaseBackupSucceeded	TRAP-TYPE
	ENTERPRISE			netappDataFabricManager
	VARIABLES	{
				dfmSerialNumber, dfmEventSourceSerialNumber,
				dfmEventId, dfmEventName, dfmEventSeverity,
				dfmEventTimestamp, dfmEventMessage, 
				dfmEventMessageDetails,
				dfmEventSourceId, dfmEventSourceTable,
				dfmObjectId, dfmObjectType, dfmObjectFullName,
				dfmObjectStatus, dfmEventSourceProductId,
				dfmHostFullName, dfmCommentFields,
				dfmPhysicalHostId, dfmPhysicalHostFullName
			}
	DESCRIPTION	
		 "Database backup creation succeeded."

	::= 10751

	dfmEvtDatabaseBackupFailed	TRAP-TYPE
	ENTERPRISE			netappDataFabricManager
	VARIABLES	{
				dfmSerialNumber, dfmEventSourceSerialNumber,
				dfmEventId, dfmEventName, dfmEventSeverity,
				dfmEventTimestamp, dfmEventMessage, 
				dfmEventMessageDetails,
				dfmEventSourceId, dfmEventSourceTable,
				dfmObjectId, dfmObjectType, dfmObjectFullName,
				dfmObjectStatus, dfmEventSourceProductId,
				dfmHostFullName, dfmCommentFields,
				dfmPhysicalHostId, dfmPhysicalHostFullName
			}
	DESCRIPTION	
		 "Database backup creation failed."

	::= 10752

	dfmEvtDatabaseRestoreSucceeded	TRAP-TYPE
	ENTERPRISE			netappDataFabricManager
	VARIABLES	{
				dfmSerialNumber, dfmEventSourceSerialNumber,
				dfmEventId, dfmEventName, dfmEventSeverity,
				dfmEventTimestamp, dfmEventMessage, 
				dfmEventMessageDetails,
				dfmEventSourceId, dfmEventSourceTable,
				dfmObjectId, dfmObjectType, dfmObjectFullName,
				dfmObjectStatus, dfmEventSourceProductId,
				dfmHostFullName, dfmCommentFields,
				dfmPhysicalHostId, dfmPhysicalHostFullName
			}
	DESCRIPTION	
		 "Database backup restore succeeded."

	::= 10753

	dfmEvtDatabaseRestoreFailed	TRAP-TYPE
	ENTERPRISE			netappDataFabricManager
	VARIABLES	{
				dfmSerialNumber, dfmEventSourceSerialNumber,
				dfmEventId, dfmEventName, dfmEventSeverity,
				dfmEventTimestamp, dfmEventMessage, 
				dfmEventMessageDetails,
				dfmEventSourceId, dfmEventSourceTable,
				dfmObjectId, dfmObjectType, dfmObjectFullName,
				dfmObjectStatus, dfmEventSourceProductId,
				dfmHostFullName, dfmCommentFields,
				dfmPhysicalHostId, dfmPhysicalHostFullName
			}
	DESCRIPTION	
		 "Database backup restore failed."

	::= 10754

	-- Max dir size related events

	dfmEvtMaxdirsizeReached	TRAP-TYPE
	ENTERPRISE			netappDataFabricManager
	VARIABLES	{
				dfmSerialNumber, dfmEventSourceSerialNumber,
				dfmEventId, dfmEventName, dfmEventSeverity,
				dfmEventTimestamp, dfmEventMessage, 
				dfmEventMessageDetails,
				dfmEventSourceId, dfmEventSourceTable,
				dfmObjectId, dfmObjectType, dfmObjectFullName,
				dfmObjectStatus, dfmEventSourceProductId,
				dfmHostFullName, dfmCommentFields,
				dfmPhysicalHostId, dfmPhysicalHostFullName
			}
	DESCRIPTION	
		"A directory has reached it's maxdirsize limit. Either 
		increase the maxdirsize or clean up the directory."
		
	::= 10761

	dfmEvtMaxdirsizeNearlyReached	TRAP-TYPE
	ENTERPRISE			netappDataFabricManager
	VARIABLES	{
				dfmSerialNumber, dfmEventSourceSerialNumber,
				dfmEventId, dfmEventName, dfmEventSeverity,
				dfmEventTimestamp, dfmEventMessage, 
				dfmEventMessageDetails,
				dfmEventSourceId, dfmEventSourceTable,
				dfmObjectId, dfmObjectType, dfmObjectFullName,
				dfmObjectStatus, dfmEventSourceProductId,
				dfmHostFullName, dfmCommentFields,
				dfmPhysicalHostId, dfmPhysicalHostFullName
			}
	DESCRIPTION	
		"A directory is getting close to it's maxdirsize limit. Either
		increase the maxdirsize or clean up the directory."

	::= 10762

	
	dfmEvtSnapTooOld	TRAP-TYPE
	ENTERPRISE			netappDataFabricManager
	VARIABLES	{
				dfmSerialNumber, dfmEventSourceSerialNumber,
				dfmEventId, dfmEventName, dfmEventSeverity,
				dfmEventTimestamp, dfmEventMessage, 
				dfmEventMessageDetails,
				dfmEventSourceId, dfmEventSourceTable,
				dfmObjectId, dfmObjectType, dfmObjectFullName,
				dfmObjectStatus, dfmEventSourceProductId,
				dfmHostFullName, dfmCommentFields,
				dfmPhysicalHostId, dfmPhysicalHostFullName
			}
	DESCRIPTION	
		 "Too Old Snapshots on the volume"

	::= 10771

	dfmEvtSnapNotTooOld	TRAP-TYPE
	ENTERPRISE			netappDataFabricManager
	VARIABLES	{
				dfmSerialNumber, dfmEventSourceSerialNumber,
				dfmEventId, dfmEventName, dfmEventSeverity,
				dfmEventTimestamp, dfmEventMessage, 
				dfmEventMessageDetails,
				dfmEventSourceId, dfmEventSourceTable,
				dfmObjectId, dfmObjectType, dfmObjectFullName,
				dfmObjectStatus, dfmEventSourceProductId,
				dfmHostFullName, dfmCommentFields,
				dfmPhysicalHostId, dfmPhysicalHostFullName
			}
	DESCRIPTION	
		 "No Old Snapshots on the volume"

	::= 10772

	-- traps for rpm events

	dfmEvtRpmOnline		TRAP-TYPE
	ENTERPRISE		netappDataFabricManager
	VARIABLES	{
				dfmSerialNumber, dfmEventSourceSerialNumber,
				dfmEventId, dfmEventName, dfmEventSeverity,
				dfmEventTimestamp, dfmEventMessage, 
				dfmEventMessageDetails,
				dfmEventSourceId, dfmEventSourceTable,
				dfmObjectId, dfmObjectType, dfmObjectFullName,
				dfmObjectStatus, dfmEventSourceProductId,
				dfmHostFullName, dfmCommentFields,
				dfmPhysicalHostId, dfmPhysicalHostFullName
			}
	DESCRIPTION
		"The status of RPM card is online."
	::= 10781

	dfmEvtRpmUnavailable	TRAP-TYPE
	ENTERPRISE		netappDataFabricManager
	VARIABLES	{
				dfmSerialNumber, dfmEventSourceSerialNumber,
				dfmEventId, dfmEventName, dfmEventSeverity,
				dfmEventTimestamp, dfmEventMessage, 
				dfmEventMessageDetails,
				dfmEventSourceId, dfmEventSourceTable,
				dfmObjectId, dfmObjectType, dfmObjectFullName,
				dfmObjectStatus, dfmEventSourceProductId,
				dfmHostFullName, dfmCommentFields,
				dfmPhysicalHostId, dfmPhysicalHostFullName
			}
	DESCRIPTION
		"The status of RPM card is unavailable."
	::= 10782

	-- traps for aggregate state

	dfmEvtAggregateStateFailed		TRAP-TYPE
	ENTERPRISE		netappDataFabricManager
	VARIABLES	{
				dfmSerialNumber, dfmEventSourceSerialNumber,
				dfmEventId, dfmEventName, dfmEventSeverity,
				dfmEventTimestamp, dfmEventMessage, 
				dfmEventMessageDetails,
				dfmEventSourceId, dfmEventSourceTable,
				dfmObjectId, dfmObjectType, dfmObjectFullName,
				dfmObjectStatus, dfmEventSourceProductId,
				dfmHostFullName, dfmCommentFields,
				dfmPhysicalHostId, dfmPhysicalHostFullName
			}
	DESCRIPTION	
		"The aggregate being managed by DataFabric Manager 
		 has failed. Variable dfmObjectId identifies the 
		 aggregate."
	::= 10791

	dfmEvtAggregateStateOnline		TRAP-TYPE
	ENTERPRISE		netappDataFabricManager
	VARIABLES	{
				dfmSerialNumber, dfmEventSourceSerialNumber,
				dfmEventId, dfmEventName, dfmEventSeverity,
				dfmEventTimestamp, dfmEventMessage, 
				dfmEventMessageDetails,
				dfmEventSourceId, dfmEventSourceTable,
				dfmObjectId, dfmObjectType, dfmObjectFullName,
				dfmObjectStatus, dfmEventSourceProductId,
				dfmHostFullName, dfmCommentFields,
				dfmPhysicalHostId, dfmPhysicalHostFullName
			}
	DESCRIPTION	
		"The aggregate being managed by DataFabric Manager 
		 is online. Variable dfmObjectId identifies the 
		 aggregate."
	::= 10792

	dfmEvtAggregateStateOffline		TRAP-TYPE
	ENTERPRISE		netappDataFabricManager
	VARIABLES	{
				dfmSerialNumber, dfmEventSourceSerialNumber,
				dfmEventId, dfmEventName, dfmEventSeverity,
				dfmEventTimestamp, dfmEventMessage, 
				dfmEventMessageDetails,
				dfmEventSourceId, dfmEventSourceTable,
				dfmObjectId, dfmObjectType, dfmObjectFullName,
				dfmObjectStatus, dfmEventSourceProductId,
				dfmHostFullName, dfmCommentFields,
				dfmPhysicalHostId, dfmPhysicalHostFullName
			}
	DESCRIPTION	
		"The aggregate being managed by DataFabric Manager 
		 is offline. Variable dfmObjectId identifies the 
		 aggregate."
	::= 10793

	dfmEvtAggregateStateRestricted		TRAP-TYPE
	ENTERPRISE		netappDataFabricManager
	VARIABLES	{
				dfmSerialNumber, dfmEventSourceSerialNumber,
				dfmEventId, dfmEventName, dfmEventSeverity,
				dfmEventTimestamp, dfmEventMessage, 
				dfmEventMessageDetails,
				dfmEventSourceId, dfmEventSourceTable,
				dfmObjectId, dfmObjectType, dfmObjectFullName,
				dfmObjectStatus, dfmEventSourceProductId,
				dfmHostFullName, dfmCommentFields,
				dfmPhysicalHostId, dfmPhysicalHostFullName
			}
	DESCRIPTION	
		"The aggregate being managed by DataFabric Manager 
		 is restricted. Variable dfmObjectId identifies the 
		 aggregate."
	::= 10794

	-- traps for dataset related events

	dfmEvtDatasetCreated		TRAP-TYPE
	ENTERPRISE			netappDataFabricManager
	VARIABLES	{
				dfmSerialNumber, dfmEventSourceSerialNumber,
				dfmEventId, dfmEventName, dfmEventSeverity,
				dfmEventTimestamp, dfmEventMessage, 
				dfmEventMessageDetails,
				dfmEventSourceId,
				dfmObjectId, dfmObjectType, dfmObjectFullName,
				dfmObjectStatus, dfmEventSourceProductId,
				dfmHostFullName,
				dfmPhysicalHostId, dfmPhysicalHostFullName
			}
	DESCRIPTION
		"A data set has been created."
	::= 10801

	dfmEvtDatasetDeleted		TRAP-TYPE
	ENTERPRISE			netappDataFabricManager
	VARIABLES	{
				dfmSerialNumber, dfmEventSourceSerialNumber,
				dfmEventId, dfmEventName, dfmEventSeverity,
				dfmEventTimestamp, dfmEventMessage, 
				dfmEventMessageDetails,
				dfmEventSourceId,
				dfmObjectId, dfmObjectType, dfmObjectFullName,
				dfmObjectStatus, dfmEventSourceProductId,
				dfmHostFullName,
				dfmPhysicalHostId, dfmPhysicalHostFullName
			}
	DESCRIPTION
		"A data set has been deleted."
	::= 10811

	dfmEvtDatasetModified		TRAP-TYPE
	ENTERPRISE			netappDataFabricManager
	VARIABLES	{
				dfmSerialNumber, dfmEventSourceSerialNumber,
				dfmEventId, dfmEventName, dfmEventSeverity,
				dfmEventTimestamp, dfmEventMessage, 
				dfmEventMessageDetails,
				dfmEventSourceId,
				dfmObjectId, dfmObjectType, dfmObjectFullName,
				dfmObjectStatus, dfmEventSourceProductId,
				dfmHostFullName,
				dfmPhysicalHostId, dfmPhysicalHostFullName
			}
	DESCRIPTION
		"A data set has been modified."
	::= 10821

	dfmEvtSnapshotCreated		TRAP-TYPE
	ENTERPRISE			netappDataFabricManager
	VARIABLES	{
				dfmSerialNumber, dfmEventSourceSerialNumber,
				dfmEventId, dfmEventName, dfmEventSeverity,
				dfmEventTimestamp, dfmEventMessage, 
				dfmEventMessageDetails,
				dfmEventSourceId,
				dfmObjectId, dfmObjectType, dfmObjectFullName,
				dfmObjectStatus, dfmEventSourceProductId,
				dfmHostFullName,
				dfmPhysicalHostId, dfmPhysicalHostFullName
			}
	DESCRIPTION
		"A snapshot was successfully created."
	::= 10831

	-- Trap 10832 not used (was dfmEvtLocalSnapshotAborted)

	dfmEvtSnapshotFailed		TRAP-TYPE
	ENTERPRISE			netappDataFabricManager
	VARIABLES	{
				dfmSerialNumber, dfmEventSourceSerialNumber,
				dfmEventId, dfmEventName, dfmEventSeverity,
				dfmEventTimestamp, dfmEventMessage, 
				dfmEventMessageDetails,
				dfmEventSourceId,
				dfmObjectId, dfmObjectType, dfmObjectFullName,
				dfmObjectStatus, dfmEventSourceProductId,
				dfmHostFullName,
				dfmPhysicalHostId, dfmPhysicalHostFullName
			}
	DESCRIPTION
		"An attempt to create a snapshot failed."
	::= 10833

	dfmEvtDatasetProvisioningOk		TRAP-TYPE
	ENTERPRISE			netappDataFabricManager
	VARIABLES	{
				dfmSerialNumber, dfmEventSourceSerialNumber,
				dfmEventId, dfmEventName, dfmEventSeverity,
				dfmEventTimestamp, dfmEventMessage, 
				dfmEventMessageDetails,
				dfmEventSourceId,
				dfmObjectId, dfmObjectType, dfmObjectFullName,
				dfmObjectStatus, dfmEventSourceProductId,
				dfmHostFullName,
				dfmPhysicalHostId, dfmPhysicalHostFullName
			}
	DESCRIPTION
		"Provisioning for the data set is Ok."
	::= 10841

	dfmEvtDatasetProvisioningFailed		TRAP-TYPE
	ENTERPRISE			netappDataFabricManager
	VARIABLES	{
				dfmSerialNumber, dfmEventSourceSerialNumber,
				dfmEventId, dfmEventName, dfmEventSeverity,
				dfmEventTimestamp, dfmEventMessage, 
				dfmEventMessageDetails,
				dfmEventSourceId,
				dfmObjectId, dfmObjectType, dfmObjectFullName,
				dfmObjectStatus, dfmEventSourceProductId,
				dfmHostFullName,
				dfmPhysicalHostId, dfmPhysicalHostFullName
			}
	DESCRIPTION
		"Provisioning for the data set has failed."
	::= 10842

	dfmEvtDatasetProtectionProtected		TRAP-TYPE
	ENTERPRISE			netappDataFabricManager
	VARIABLES	{
				dfmSerialNumber, dfmEventSourceSerialNumber,
				dfmEventId, dfmEventName, dfmEventSeverity,
				dfmEventTimestamp, dfmEventMessage, 
				dfmEventMessageDetails,
				dfmEventSourceId,
				dfmObjectId, dfmObjectType, dfmObjectFullName,
				dfmObjectStatus, dfmEventSourceProductId,
				dfmHostFullName,
				dfmPhysicalHostId, dfmPhysicalHostFullName
			}
	DESCRIPTION
		"Protection for the data set is successful."

	::= 10851

	dfmEvtDatasetProtectionFailure		TRAP-TYPE
	ENTERPRISE			netappDataFabricManager
	VARIABLES	{
				dfmSerialNumber, dfmEventSourceSerialNumber,
				dfmEventId, dfmEventName, dfmEventSeverity,
				dfmEventTimestamp, dfmEventMessage, 
				dfmEventMessageDetails,
				dfmEventSourceId,
				dfmObjectId, dfmObjectType, dfmObjectFullName,
				dfmObjectStatus, dfmEventSourceProductId,
				dfmHostFullName,
				dfmPhysicalHostId, dfmPhysicalHostFullName
			}
	DESCRIPTION
		"Protection for the data set has failed."
	::= 10852

	dfmEvtDatasetProtectionSuspended	TRAP-TYPE
	ENTERPRISE			netappDataFabricManager
	VARIABLES	{
				dfmSerialNumber, dfmEventSourceSerialNumber,
				dfmEventId, dfmEventName, dfmEventSeverity,
				dfmEventTimestamp, dfmEventMessage, 
				dfmEventMessageDetails,
				dfmEventSourceId,
				dfmObjectId, dfmObjectType, dfmObjectFullName,
				dfmObjectStatus, dfmEventSourceProductId,
				dfmHostFullName,
				dfmPhysicalHostId, dfmPhysicalHostFullName
			}
	DESCRIPTION
		"Protection for the data set has been suspended."
	::= 10853

	dfmEvtDatasetProtectionLagError		TRAP-TYPE
	ENTERPRISE			netappDataFabricManager
	VARIABLES	{
				dfmSerialNumber, dfmEventSourceSerialNumber,
				dfmEventId, dfmEventName, dfmEventSeverity,
				dfmEventTimestamp, dfmEventMessage, 
				dfmEventMessageDetails,
				dfmEventSourceId,
				dfmObjectId, dfmObjectType, dfmObjectFullName,
				dfmObjectStatus, dfmEventSourceProductId,
				dfmHostFullName,
				dfmPhysicalHostId, dfmPhysicalHostFullName
			}
	DESCRIPTION
		"Protection for the data set has lag error."
	::= 10854

	dfmEvtDatasetProtectionLagWarning		TRAP-TYPE
	ENTERPRISE			netappDataFabricManager
	VARIABLES	{
				dfmSerialNumber, dfmEventSourceSerialNumber,
				dfmEventId, dfmEventName, dfmEventSeverity,
				dfmEventTimestamp, dfmEventMessage, 
				dfmEventMessageDetails,
				dfmEventSourceId,
				dfmObjectId, dfmObjectType, dfmObjectFullName,
				dfmObjectStatus, dfmEventSourceProductId,
				dfmHostFullName,
				dfmPhysicalHostId, dfmPhysicalHostFullName
			}
	DESCRIPTION
		"Protection for the data set has lag warning."
	::= 10855

	dfmEvtDatasetProtectionUninitialized		TRAP-TYPE
	ENTERPRISE			netappDataFabricManager
	VARIABLES	{
				dfmSerialNumber, dfmEventSourceSerialNumber,
				dfmEventId, dfmEventName, dfmEventSeverity,
				dfmEventTimestamp, dfmEventMessage, 
				dfmEventMessageDetails,
				dfmEventSourceId,
				dfmObjectId, dfmObjectType, dfmObjectFullName,
				dfmObjectStatus, dfmEventSourceProductId,
				dfmHostFullName,
				dfmPhysicalHostId, dfmPhysicalHostFullName
			}
	DESCRIPTION
		"Protection for the data set is uninitialized."

	::= 10856

	dfmEvtDatasetConformant		TRAP-TYPE
	ENTERPRISE			netappDataFabricManager
	VARIABLES	{
				dfmSerialNumber, dfmEventSourceSerialNumber,
				dfmEventId, dfmEventName, dfmEventSeverity,
				dfmEventTimestamp, dfmEventMessage, 
				dfmEventMessageDetails,
				dfmEventSourceId,
				dfmObjectId, dfmObjectType, dfmObjectFullName,
				dfmObjectStatus, dfmEventSourceProductId,
				dfmHostFullName,
				dfmPhysicalHostId, dfmPhysicalHostFullName
			}
	DESCRIPTION
		"A data set conforms to its protection policy."
	::= 10861

	dfmEvtDatasetConforming		TRAP-TYPE
	ENTERPRISE			netappDataFabricManager
	VARIABLES	{
				dfmSerialNumber, dfmEventSourceSerialNumber,
				dfmEventId, dfmEventName, dfmEventSeverity,
				dfmEventTimestamp, dfmEventMessage, 
				dfmEventMessageDetails,
				dfmEventSourceId,
				dfmObjectId, dfmObjectType, dfmObjectFullName,
				dfmObjectStatus, dfmEventSourceProductId,
				dfmHostFullName,
				dfmPhysicalHostId, dfmPhysicalHostFullName
			}
	DESCRIPTION
		"A data set is in the process of conforming to its protection policy."
	::= 10862

	dfmEvtDatasetNonConformant		TRAP-TYPE
	ENTERPRISE			netappDataFabricManager
	VARIABLES	{
				dfmSerialNumber, dfmEventSourceSerialNumber,
				dfmEventId, dfmEventName, dfmEventSeverity,
				dfmEventTimestamp, dfmEventMessage, 
				dfmEventMessageDetails,
				dfmEventSourceId,
				dfmObjectId, dfmObjectType, dfmObjectFullName,
				dfmObjectStatus, dfmEventSourceProductId,
				dfmHostFullName,
				dfmPhysicalHostId, dfmPhysicalHostFullName
			}
	DESCRIPTION
		"A data set does not conform to its protection policy."
	::= 10863

	dfmEvtDatasetCloneSnapshotFound		TRAP-TYPE
	ENTERPRISE			netappDataFabricManager
	VARIABLES	{
				dfmSerialNumber, dfmEventSourceSerialNumber,
				dfmEventId, dfmEventName, dfmEventSeverity,
				dfmEventTimestamp, dfmEventMessage, 
				dfmEventMessageDetails,
				dfmEventSourceId,
				dfmObjectId, dfmObjectType, dfmObjectFullName,
				dfmObjectStatus, dfmEventSourceProductId,
				dfmHostFullName,
				dfmPhysicalHostId, dfmPhysicalHostFullName
			}
	DESCRIPTION
		"Clone snapshots are found on data set members. "
	::= 10864

	dfmEvtDatasetNoCloneSnapshotFound	TRAP-TYPE
	ENTERPRISE			netappDataFabricManager
	VARIABLES	{
				dfmSerialNumber, dfmEventSourceSerialNumber,
				dfmEventId, dfmEventName, dfmEventSeverity,
				dfmEventTimestamp, dfmEventMessage, 
				dfmEventMessageDetails,
				dfmEventSourceId,
				dfmObjectId, dfmObjectType, dfmObjectFullName,
				dfmObjectStatus, dfmEventSourceProductId,
				dfmHostFullName,
				dfmPhysicalHostId, dfmPhysicalHostFullName
			}
	DESCRIPTION
		"No clone snapshots are found on data set members. "
	::= 10865

	dfmEvtDatasetWriteCheckWarning		TRAP-TYPE
	ENTERPRISE			netappDataFabricManager
	VARIABLES	{
				dfmSerialNumber, dfmEventSourceSerialNumber,
				dfmEventId, dfmEventName, dfmEventSeverity,
				dfmEventTimestamp, dfmEventMessage, 
				dfmEventMessageDetails,
				dfmEventSourceId,
				dfmObjectId, dfmObjectType, dfmObjectFullName,
				dfmObjectStatus, dfmEventSourceProductId,
				dfmHostFullName,
				dfmPhysicalHostId, dfmPhysicalHostFullName
			}
	DESCRIPTION
		"Data set members may need resizing for write guarantees. "
	::= 10866

	dfmEvtDatasetWriteCheckOk		TRAP-TYPE
	ENTERPRISE			netappDataFabricManager
	VARIABLES	{
				dfmSerialNumber, dfmEventSourceSerialNumber,
				dfmEventId, dfmEventName, dfmEventSeverity,
				dfmEventTimestamp, dfmEventMessage, 
				dfmEventMessageDetails,
				dfmEventSourceId,
				dfmObjectId, dfmObjectType, dfmObjectFullName,
				dfmObjectStatus, dfmEventSourceProductId,
				dfmHostFullName,
				dfmPhysicalHostId, dfmPhysicalHostFullName
			}
	DESCRIPTION
		"Data set member write guarantee check OK. "
	::= 10867

	-- traps for resource pool related events

	dfmEvtResourcePoolCreated		TRAP-TYPE
	ENTERPRISE			netappDataFabricManager
	VARIABLES	{
				dfmSerialNumber, dfmEventSourceSerialNumber,
				dfmEventId, dfmEventName, dfmEventSeverity,
				dfmEventTimestamp, dfmEventMessage, 
				dfmEventMessageDetails,
				dfmEventSourceId,
				dfmObjectId, dfmObjectType, dfmObjectFullName,
				dfmObjectStatus, dfmEventSourceProductId,
				dfmHostFullName,
				dfmPhysicalHostId, dfmPhysicalHostFullName
			}
	DESCRIPTION
		"A resource pool has been created."
	::= 10871

	dfmEvtResourcePoolDeleted		TRAP-TYPE
	ENTERPRISE			netappDataFabricManager
	VARIABLES	{
				dfmSerialNumber, dfmEventSourceSerialNumber,
				dfmEventId, dfmEventName, dfmEventSeverity,
				dfmEventTimestamp, dfmEventMessage, 
				dfmEventMessageDetails,
				dfmEventSourceId,
				dfmObjectId, dfmObjectType, dfmObjectFullName,
				dfmObjectStatus, dfmEventSourceProductId,
				dfmHostFullName,
				dfmPhysicalHostId, dfmPhysicalHostFullName
			}
	DESCRIPTION
		"A resource pool has been deleted."
	::= 10881

	dfmEvtResourcePoolModified		TRAP-TYPE
	ENTERPRISE			netappDataFabricManager
	VARIABLES	{
				dfmSerialNumber, dfmEventSourceSerialNumber,
				dfmEventId, dfmEventName, dfmEventSeverity,
				dfmEventTimestamp, dfmEventMessage, 
				dfmEventMessageDetails,
				dfmEventSourceId,
				dfmObjectId, dfmObjectType, dfmObjectFullName,
				dfmObjectStatus, dfmEventSourceProductId,
				dfmHostFullName,
				dfmPhysicalHostId, dfmPhysicalHostFullName
			}
	DESCRIPTION
		"A resource pool has been modified."
	::= 10891

	dfmEvtResourcePoolSpaceOk		TRAP-TYPE
	ENTERPRISE			netappDataFabricManager
	VARIABLES	{
				dfmSerialNumber, dfmEventSourceSerialNumber,
				dfmEventId, dfmEventName, dfmEventSeverity,
				dfmEventTimestamp, dfmEventMessage, 
				dfmEventMessageDetails,
				dfmEventSourceId,
				dfmObjectId, dfmObjectType, dfmObjectFullName,
				dfmObjectStatus, dfmEventSourceProductId,
				dfmHostFullName,
				dfmPhysicalHostId, dfmPhysicalHostFullName
			}
	DESCRIPTION
		"The space utilization on the resource pool being managed 
		by DataFabric Manager is below its 'nearlyFull' threshold.
		Variable dfmObjectId identifies the resource pool."
	::= 10901

	dfmEvtResourcePoolSpaceNearlyFull		TRAP-TYPE
	ENTERPRISE			netappDataFabricManager
	VARIABLES	{
				dfmSerialNumber, dfmEventSourceSerialNumber,
				dfmEventId, dfmEventName, dfmEventSeverity,
				dfmEventTimestamp, dfmEventMessage, 
				dfmEventMessageDetails,
				dfmEventSourceId,
				dfmObjectId, dfmObjectType, dfmObjectFullName,
				dfmObjectStatus, dfmEventSourceProductId,
				dfmHostFullName,
				dfmPhysicalHostId, dfmPhysicalHostFullName
			}
	DESCRIPTION
		"The space utilization on the resource pool being managed 
		by DataFabric Manager has crossed its 'nearlyFull' threshold.
		Variable dfmObjectId identifies the resource pool."
	::= 10902

	dfmEvtResourcePoolSpaceFull		TRAP-TYPE
	ENTERPRISE			netappDataFabricManager
	VARIABLES	{
				dfmSerialNumber, dfmEventSourceSerialNumber,
				dfmEventId, dfmEventName, dfmEventSeverity,
				dfmEventTimestamp, dfmEventMessage, 
				dfmEventMessageDetails,
				dfmEventSourceId,
				dfmObjectId, dfmObjectType, dfmObjectFullName,
				dfmObjectStatus, dfmEventSourceProductId,
				dfmHostFullName,
				dfmPhysicalHostId, dfmPhysicalHostFullName
			}
	DESCRIPTION
		"The space utilization on the resource pool being managed 
		by DataFabric Manager has crossed its 'full' threshold.
		Variable dfmObjectId identifies the resource pool."
	::= 10903
	
	-- traps for protection policy related events
	
	dfmEvtDataProtectionPolicyCreated		TRAP-TYPE
	ENTERPRISE			netappDataFabricManager
	VARIABLES	{
				dfmSerialNumber, dfmEventSourceSerialNumber,
				dfmEventId, dfmEventName, dfmEventSeverity,
				dfmEventTimestamp, dfmEventMessage, 
				dfmEventMessageDetails,
				dfmEventSourceId,
				dfmObjectId, dfmObjectType, dfmObjectFullName,
				dfmObjectStatus, dfmEventSourceProductId,
				dfmHostFullName,
				dfmPhysicalHostId, dfmPhysicalHostFullName
			}
	DESCRIPTION
		"A protection policy has been created."
	::= 10911

	dfmEvtDataProtectionPolicyDeleted		TRAP-TYPE
	ENTERPRISE			netappDataFabricManager
	VARIABLES	{
				dfmSerialNumber, dfmEventSourceSerialNumber,
				dfmEventId, dfmEventName, dfmEventSeverity,
				dfmEventTimestamp, dfmEventMessage, 
				dfmEventMessageDetails,
				dfmEventSourceId,
				dfmObjectId, dfmObjectType, dfmObjectFullName,
				dfmObjectStatus, dfmEventSourceProductId,
				dfmHostFullName,
				dfmPhysicalHostId, dfmPhysicalHostFullName
			}
	DESCRIPTION
		"A protection policy has been deleted."
	::= 10921

	dfmEvtDataProtectionPolicyModified		TRAP-TYPE
	ENTERPRISE			netappDataFabricManager
	VARIABLES	{
				dfmSerialNumber, dfmEventSourceSerialNumber,
				dfmEventId, dfmEventName, dfmEventSeverity,
				dfmEventTimestamp, dfmEventMessage, 
				dfmEventMessageDetails,
				dfmEventSourceId,
				dfmObjectId, dfmObjectType, dfmObjectFullName,
				dfmObjectStatus, dfmEventSourceProductId,
				dfmHostFullName,
				dfmPhysicalHostId, dfmPhysicalHostFullName
			}
	DESCRIPTION
		"A protection policy has been modified."
	::= 10931

	-- traps for protection schedule related events

	dfmEvtDataProtectionScheduleCreated		TRAP-TYPE
	ENTERPRISE			netappDataFabricManager
	VARIABLES	{
				dfmSerialNumber, dfmEventSourceSerialNumber,
				dfmEventId, dfmEventName, dfmEventSeverity,
				dfmEventTimestamp, dfmEventMessage, 
				dfmEventMessageDetails,
				dfmEventSourceId,
				dfmObjectId, dfmObjectType, dfmObjectFullName,
				dfmObjectStatus, dfmEventSourceProductId,
				dfmHostFullName,
				dfmPhysicalHostId, dfmPhysicalHostFullName
			}
	DESCRIPTION
		"A protection schedule has been created."
	::= 10941

	dfmEvtDataProtectionScheduleDeleted		TRAP-TYPE
	ENTERPRISE			netappDataFabricManager
	VARIABLES	{
				dfmSerialNumber, dfmEventSourceSerialNumber,
				dfmEventId, dfmEventName, dfmEventSeverity,
				dfmEventTimestamp, dfmEventMessage, 
				dfmEventMessageDetails,
				dfmEventSourceId,
				dfmObjectId, dfmObjectType, dfmObjectFullName,
				dfmObjectStatus, dfmEventSourceProductId,
				dfmHostFullName,
				dfmPhysicalHostId, dfmPhysicalHostFullName
			}
	DESCRIPTION
		"A protection schedule has been deleted."
	::= 10951

	dfmEvtDataProtectionScheduleModified		TRAP-TYPE
	ENTERPRISE			netappDataFabricManager
	VARIABLES	{
				dfmSerialNumber, dfmEventSourceSerialNumber,
				dfmEventId, dfmEventName, dfmEventSeverity,
				dfmEventTimestamp, dfmEventMessage, 
				dfmEventMessageDetails,
				dfmEventSourceId,
				dfmObjectId, dfmObjectType, dfmObjectFullName,
				dfmObjectStatus, dfmEventSourceProductId,
				dfmHostFullName,
				dfmPhysicalHostId, dfmPhysicalHostFullName
			}
	DESCRIPTION
		"A protection schedule has been modified."
	::= 10961

	-- Ndmp credentials Events

	dfmEvtNdmpCredentialsGood		TRAP-TYPE
	ENTERPRISE		netappDataFabricManager
	VARIABLES	{
				dfmSerialNumber, dfmEventSourceSerialNumber,
				dfmEventId, dfmEventName, dfmEventSeverity,
				dfmEventTimestamp, dfmEventMessage, 
				dfmEventMessageDetails,
				dfmEventSourceId, dfmEventSourceTable,
				dfmObjectId, dfmObjectType, dfmObjectFullName,
				dfmObjectStatus, dfmEventSourceProductId,
				dfmHostFullName,
				dfmPhysicalHostId, dfmPhysicalHostFullName
			}
	DESCRIPTION
		"An ndmp authentication success event generated ndmp monitor."
	::= 10971

	dfmEvtNdmpCredentialsBad		TRAP-TYPE
	ENTERPRISE		netappDataFabricManager
	VARIABLES	{
				dfmSerialNumber, dfmEventSourceSerialNumber,
				dfmEventId, dfmEventName, dfmEventSeverity,
				dfmEventTimestamp, dfmEventMessage, 
				dfmEventMessageDetails,
				dfmEventSourceId, dfmEventSourceTable,
				dfmObjectId, dfmObjectType, dfmObjectFullName,
				dfmObjectStatus, dfmEventSourceProductId,
				dfmHostFullName,
				dfmPhysicalHostId, dfmPhysicalHostFullName
			}
	DESCRIPTION
		"An ndmp authentication failure event generated ndmp monitor."
	::= 10972

	-- Data Protection Job Started Event

	dfmEvtDataProtectionJobStarted		TRAP-TYPE
	ENTERPRISE		netappDataFabricManager
	VARIABLES	{
				dfmSerialNumber, dfmEventSourceSerialNumber,
				dfmEventId, dfmEventName, dfmEventSeverity,
				dfmEventTimestamp, dfmEventMessage, 
				dfmEventMessageDetails,
				dfmEventSourceId, dfmEventSourceTable,
				dfmObjectId, dfmObjectType, dfmObjectFullName,
				dfmObjectStatus, dfmEventSourceProductId,
				dfmHostFullName,
				dfmPhysicalHostId, dfmPhysicalHostFullName
			}
	DESCRIPTION
		"A data protection job started on a data set."
	::= 10981

	-- host deleted events
	dfmEvtHostDeleted				TRAP-TYPE
	ENTERPRISE			netappDataFabricManager
	VARIABLES	{
				dfmSerialNumber, dfmEventSourceSerialNumber,
				dfmEventId, dfmEventName, dfmEventSeverity,
				dfmEventTimestamp, dfmEventMessage, 
				dfmEventMessageDetails,
				dfmEventSourceId,
				dfmObjectId, dfmObjectType, dfmObjectFullName,
				dfmObjectStatus, dfmEventSourceProductId,
				dfmHostFullName,
				dfmPhysicalHostId, dfmPhysicalHostFullName
			}

	DESCRIPTION
		"A managed host was deleted."
	::= 10991


	-- host modified events
	dfmEvtHostModified				TRAP-TYPE
	ENTERPRISE			netappDataFabricManager
	VARIABLES	{
				dfmSerialNumber, dfmEventSourceSerialNumber,
				dfmEventId, dfmEventName, dfmEventSeverity,
				dfmEventTimestamp, dfmEventMessage, 
				dfmEventMessageDetails,
				dfmEventSourceId,
				dfmObjectId, dfmObjectType, dfmObjectFullName,
				dfmObjectStatus, dfmEventSourceProductId,
				dfmHostFullName,
				dfmPhysicalHostId, dfmPhysicalHostFullName
			}

	DESCRIPTION
		"A managed host was modified."
	::= 11001

	-- traps for resource group related events

	dfmEvtResourceGroupCreated		TRAP-TYPE
	ENTERPRISE			netappDataFabricManager
	VARIABLES	{
				dfmSerialNumber, dfmEventSourceSerialNumber,
				dfmEventId, dfmEventName, dfmEventSeverity,
				dfmEventTimestamp, dfmEventMessage, 
				dfmEventMessageDetails,
				dfmEventSourceId,
				dfmObjectId, dfmObjectType, dfmObjectFullName,
				dfmObjectStatus, dfmEventSourceProductId,
				dfmHostFullName,
				dfmPhysicalHostId, dfmPhysicalHostFullName
			}
	DESCRIPTION
		"A resource group has been created."
	::= 11011

	dfmEvtResourceGroupDeleted		TRAP-TYPE
	ENTERPRISE			netappDataFabricManager
	VARIABLES	{
				dfmSerialNumber, dfmEventSourceSerialNumber,
				dfmEventId, dfmEventName, dfmEventSeverity,
				dfmEventTimestamp, dfmEventMessage, 
				dfmEventMessageDetails,
				dfmEventSourceId,
				dfmObjectId, dfmObjectType, dfmObjectFullName,
				dfmObjectStatus, dfmEventSourceProductId,
				dfmHostFullName,
				dfmPhysicalHostId, dfmPhysicalHostFullName
			}
	DESCRIPTION
		"A resource group has been deleted."
	::= 11021

	dfmEvtResourceGroupModified		TRAP-TYPE
	ENTERPRISE			netappDataFabricManager
	VARIABLES	{
				dfmSerialNumber, dfmEventSourceSerialNumber,
				dfmEventId, dfmEventName, dfmEventSeverity,
				dfmEventTimestamp, dfmEventMessage, 
				dfmEventMessageDetails,
				dfmEventSourceId,
				dfmObjectId, dfmObjectType, dfmObjectFullName,
				dfmObjectStatus, dfmEventSourceProductId,
				dfmHostFullName,
				dfmPhysicalHostId, dfmPhysicalHostFullName
			}
	DESCRIPTION
		"A resource group has been modified."
	::= 11031

	-- traps for alarm related events

	dfmEvtAlarmCreated		TRAP-TYPE
	ENTERPRISE			netappDataFabricManager
	VARIABLES	{
				dfmSerialNumber, dfmEventSourceSerialNumber,
				dfmEventId, dfmEventName, dfmEventSeverity,
				dfmEventTimestamp, dfmEventMessage, 
				dfmEventMessageDetails,
				dfmEventSourceId,
				dfmObjectId, dfmObjectType, dfmObjectFullName,
				dfmObjectStatus, dfmEventSourceProductId,
				dfmHostFullName,
				dfmPhysicalHostId, dfmPhysicalHostFullName
			}
	DESCRIPTION
		"An alarm has been created."
	::= 11041

	dfmEvtAlarmDeleted		TRAP-TYPE
	ENTERPRISE			netappDataFabricManager
	VARIABLES	{
				dfmSerialNumber, dfmEventSourceSerialNumber,
				dfmEventId, dfmEventName, dfmEventSeverity,
				dfmEventTimestamp, dfmEventMessage, 
				dfmEventMessageDetails,
				dfmEventSourceId,
				dfmObjectId, dfmObjectType, dfmObjectFullName,
				dfmObjectStatus, dfmEventSourceProductId,
				dfmHostFullName,
				dfmPhysicalHostId, dfmPhysicalHostFullName
			}
	DESCRIPTION
		"An alarm has been deleted."
	::= 11051

	dfmEvtAlarmModified		TRAP-TYPE
	ENTERPRISE			netappDataFabricManager
	VARIABLES	{
				dfmSerialNumber, dfmEventSourceSerialNumber,
				dfmEventId, dfmEventName, dfmEventSeverity,
				dfmEventTimestamp, dfmEventMessage, 
				dfmEventMessageDetails,
				dfmEventSourceId,
				dfmObjectId, dfmObjectType, dfmObjectFullName,
				dfmObjectStatus, dfmEventSourceProductId,
				dfmHostFullName,
				dfmPhysicalHostId, dfmPhysicalHostFullName
			}
	DESCRIPTION
		"An alarm has been modified."
	::= 11061

	-- Ndmp communication Events

	dfmEvtNdmpCommunicationUp		TRAP-TYPE
	ENTERPRISE		netappDataFabricManager
	VARIABLES	{
				dfmSerialNumber, dfmEventSourceSerialNumber,
				dfmEventId, dfmEventName, dfmEventSeverity,
				dfmEventTimestamp, dfmEventMessage, 
				dfmEventMessageDetails,
				dfmEventSourceId, dfmEventSourceTable,
				dfmObjectId, dfmObjectType, dfmObjectFullName,
				dfmObjectStatus, dfmEventSourceProductId,
				dfmHostFullName,
				dfmPhysicalHostId, dfmPhysicalHostFullName
			}
	DESCRIPTION
		"An ndmp communication establishment event detected by ndmp monitor."
	::= 11071

	dfmEvtNdmpCommunicationDown		TRAP-TYPE
	ENTERPRISE		netappDataFabricManager
	VARIABLES	{
				dfmSerialNumber, dfmEventSourceSerialNumber,
				dfmEventId, dfmEventName, dfmEventSeverity,
				dfmEventTimestamp, dfmEventMessage, 
				dfmEventMessageDetails,
				dfmEventSourceId, dfmEventSourceTable,
				dfmObjectId, dfmObjectType, dfmObjectFullName,
				dfmObjectStatus, dfmEventSourceProductId,
				dfmHostFullName,
				dfmPhysicalHostId, dfmPhysicalHostFullName
			}
	DESCRIPTION
		"An ndmp communication failure event generated by ndmp monitor."
	::= 11081

	dfmEvtDatasetBackupCompleted		TRAP-TYPE
	ENTERPRISE				netappDataFabricManager
	VARIABLES	{
				dfmSerialNumber, dfmEventSourceSerialNumber,
				dfmEventId, dfmEventName, dfmEventSeverity,
				dfmEventTimestamp, dfmEventMessage, 
				dfmEventMessageDetails,
				dfmEventSourceId, dfmEventSourceTable,
				dfmObjectId, dfmObjectType, dfmObjectFullName,
				dfmObjectStatus, dfmEventSourceProductId,
				dfmHostFullName, dfmCommentFields,
				dfmPhysicalHostId, dfmPhysicalHostFullName
			}
	DESCRIPTION
		"A backup of an established relationship has been
		successfully performed by DFM."
	::= 11090
	
	dfmEvtDatasetBackupAborted		TRAP-TYPE
	ENTERPRISE				netappDataFabricManager
	VARIABLES	{
				dfmSerialNumber, dfmEventSourceSerialNumber,
				dfmEventId, dfmEventName, dfmEventSeverity,
				dfmEventTimestamp, dfmEventMessage, 
				dfmEventMessageDetails,
				dfmEventSourceId, dfmEventSourceTable,
				dfmObjectId, dfmObjectType, dfmObjectFullName,
				dfmObjectStatus, dfmEventSourceProductId,
				dfmHostFullName, dfmCommentFields,
				dfmPhysicalHostId, dfmPhysicalHostFullName
			}
	DESCRIPTION
		"A backup has been aborted."
	::= 11091
	
	dfmEvtDatasetBackupFailed		TRAP-TYPE
	ENTERPRISE				netappDataFabricManager
	VARIABLES	{
				dfmSerialNumber, dfmEventSourceSerialNumber,
				dfmEventId, dfmEventName, dfmEventSeverity,
				dfmEventTimestamp, dfmEventMessage, 
				dfmEventMessageDetails,
				dfmEventSourceId, dfmEventSourceTable,
				dfmObjectId, dfmObjectType, dfmObjectFullName,
				dfmObjectStatus, dfmEventSourceProductId,
				dfmHostFullName, dfmCommentFields,
				dfmPhysicalHostId, dfmPhysicalHostFullName
			}
	DESCRIPTION
		"A backup has failed."
	::= 11092
	
	-- host zapi communication evetns

	dfmEvtFilerCommunicationOk      TRAP-TYPE
	ENTERPRISE              netappDataFabricManager
	VARIABLES       {
				dfmSerialNumber, dfmEventSourceSerialNumber,
				dfmEventId, dfmEventName, dfmEventSeverity,
				dfmEventTimestamp, dfmEventMessage,
				dfmEventMessageDetails,
				dfmEventSourceId, dfmEventSourceTable,
				dfmObjectId, dfmObjectType, dfmObjectFullName,
				dfmObjectStatus, dfmEventSourceProductId,
				dfmHostFullName, dfmCommentFields,
				dfmPhysicalHostId, dfmPhysicalHostFullName
			}
	DESCRIPTION
		"Connection to the ZAPI port on a storage system managed by DataFabric 
		Manager succeeded."
	::= 11100

	dfmEvtFilerCommunicationFailed  TRAP-TYPE
	ENTERPRISE              netappDataFabricManager
	VARIABLES       {
				dfmSerialNumber, dfmEventSourceSerialNumber,
				dfmEventId, dfmEventName, dfmEventSeverity,
				dfmEventTimestamp, dfmEventMessage,
				dfmEventMessageDetails,
				dfmEventSourceId, dfmEventSourceTable,
				dfmObjectId, dfmObjectType, dfmObjectFullName,
				dfmObjectStatus, dfmEventSourceProductId,
				dfmHostFullName, dfmCommentFields,
				dfmPhysicalHostId, dfmPhysicalHostFullName
			}
	DESCRIPTION
		"Connection to the ZAPI port on a storage system managed by DataFabric 
		Manager failed."
	::= 11101
	
	-- vFiler Configuration events

	dfmEvtLocalVfilerConfigStatusOk	TRAP-TYPE
	ENTERPRISE		netappDataFabricManager
	VARIABLES	{
				dfmSerialNumber, dfmEventSourceSerialNumber,
				dfmEventId, dfmEventName, dfmEventSeverity,
				dfmEventTimestamp, dfmEventMessage, 
				dfmEventMessageDetails,
				dfmEventSourceId, dfmEventSourceTable,
				dfmObjectId, dfmObjectType, dfmObjectFullName,
				dfmObjectStatus, dfmEventSourceProductId,
				dfmHostFullName, dfmCommentFields,
				dfmPhysicalHostId, dfmPhysicalHostFullName
			}
	DESCRIPTION
		"The local configuration on the vFiler being 
		monitored has status value 'ok'."
	::= 11111


	dfmEvtLocalVfilerConfigStatusChanged	TRAP-TYPE
	ENTERPRISE			netappDataFabricManager
	VARIABLES	{
				dfmSerialNumber, dfmEventSourceSerialNumber,
				dfmEventId, dfmEventName, dfmEventSeverity,
				dfmEventTimestamp, dfmEventMessage, 
				dfmEventMessageDetails,
				dfmEventSourceId, dfmEventSourceTable,
				dfmObjectId, dfmObjectType, dfmObjectFullName,
				dfmObjectStatus, dfmEventSourceProductId,
				dfmHostFullName, dfmCommentFields,
				dfmPhysicalHostId, dfmPhysicalHostFullName
			}
	DESCRIPTION
		"The local configuration on the vFiler being 
		monitored has status value 'changed'. It was 
		not changed through DataFabric Manager."
	::= 11112

	-- vFiler Configuration Push events
	
	dfmEvtVfilerConfigPushStatusOk	TRAP-TYPE
	ENTERPRISE		netappDataFabricManager
	VARIABLES	{
				dfmSerialNumber, dfmEventSourceSerialNumber,
				dfmEventId, dfmEventName, dfmEventSeverity,
				dfmEventTimestamp, dfmEventMessage, 
				dfmEventMessageDetails,
				dfmEventSourceId, dfmEventSourceTable,
				dfmObjectId, dfmObjectType, dfmObjectFullName,
				dfmObjectStatus, dfmEventSourceProductId,
				dfmHostFullName, dfmCommentFields,
				dfmPhysicalHostId, dfmPhysicalHostFullName
			}
	DESCRIPTION
		"The configuration push on the vfiler was successful."
	::= 11113


	dfmEvtVfilerConfigPushStatusError	TRAP-TYPE
	ENTERPRISE			netappDataFabricManager
	VARIABLES	{
				dfmSerialNumber, dfmEventSourceSerialNumber,
				dfmEventId, dfmEventName, dfmEventSeverity,
				dfmEventTimestamp, dfmEventMessage, 
				dfmEventMessageDetails,
				dfmEventSourceId, dfmEventSourceTable,
				dfmObjectId, dfmObjectType, dfmObjectFullName,
				dfmObjectStatus, dfmEventSourceProductId,
				dfmHostFullName, dfmCommentFields,
				dfmPhysicalHostId, dfmPhysicalHostFullName
			}
	DESCRIPTION
		"The configuration push on the vFiler failed to  
		push some options."
	::= 11114

	-- Report Scheduling related events
	
	dfmEvtScheduledReportOk			TRAP-TYPE
	ENTERPRISE			netappDataFabricManager
	VARIABLES	{
				dfmSerialNumber, dfmEventSourceSerialNumber,
				dfmEventId, dfmEventName, dfmEventSeverity,
				dfmEventTimestamp, dfmEventMessage, 
				dfmEventMessageDetails,
				dfmEventSourceId, dfmEventSourceTable,
				dfmObjectId, dfmObjectType, dfmObjectFullName,
				dfmObjectStatus, dfmEventSourceProductId,
				dfmHostFullName, dfmCommentFields,
				dfmPhysicalHostId, dfmPhysicalHostFullName
			}
	DESCRIPTION
		"The scheduled report run was successful."
	::= 11121	
	
	dfmEvtScheduledReportFailed		TRAP-TYPE
	ENTERPRISE			netappDataFabricManager
	VARIABLES	{
				dfmSerialNumber, dfmEventSourceSerialNumber,
				dfmEventId, dfmEventName, dfmEventSeverity,
				dfmEventTimestamp, dfmEventMessage, 
				dfmEventMessageDetails,
				dfmEventSourceId, dfmEventSourceTable,
				dfmObjectId, dfmObjectType, dfmObjectFullName,
				dfmObjectStatus, dfmEventSourceProductId,
				dfmHostFullName, dfmCommentFields,
				dfmPhysicalHostId, dfmPhysicalHostFullName
			}
	DESCRIPTION
		"The scheduled report run was not successful."
	::= 11122
	
	dfmEvtReportScheduleEnabled		TRAP-TYPE
	ENTERPRISE			netappDataFabricManager
	VARIABLES	{
				dfmSerialNumber, dfmEventSourceSerialNumber,
				dfmEventId, dfmEventName, dfmEventSeverity,
				dfmEventTimestamp, dfmEventMessage, 
				dfmEventMessageDetails,
				dfmEventSourceId, dfmEventSourceTable,
				dfmObjectId, dfmObjectType, dfmObjectFullName,
				dfmObjectStatus, dfmEventSourceProductId,
				dfmHostFullName, dfmCommentFields,
				dfmPhysicalHostId, dfmPhysicalHostFullName
			}
	DESCRIPTION
		"The report schedule was enabled."
	::= 11123	
	
	dfmEvtReportScheduleDisabled		TRAP-TYPE
	ENTERPRISE			netappDataFabricManager
	VARIABLES	{
				dfmSerialNumber, dfmEventSourceSerialNumber,
				dfmEventId, dfmEventName, dfmEventSeverity,
				dfmEventTimestamp, dfmEventMessage, 
				dfmEventMessageDetails,
				dfmEventSourceId, dfmEventSourceTable,
				dfmObjectId, dfmObjectType, dfmObjectFullName,
				dfmObjectStatus, dfmEventSourceProductId,
				dfmHostFullName, dfmCommentFields,
				dfmPhysicalHostId, dfmPhysicalHostFullName
			}
	DESCRIPTION
		"The report schedule was disabled."
	::= 11124	

		
	-- Host RBAC Monitoring related events

	dfmEvtHostRoleDiscovered		TRAP-TYPE
	ENTERPRISE			netappDataFabricManager
	VARIABLES	{
				dfmSerialNumber, dfmEventSourceSerialNumber,
				dfmEventId, dfmEventName, dfmEventSeverity,
				dfmEventTimestamp, dfmEventMessage, 
				dfmEventMessageDetails,
				dfmEventSourceId, dfmEventSourceTable,
				dfmObjectId, dfmObjectType, dfmObjectFullName,
				dfmObjectStatus, dfmEventSourceProductId,
				dfmHostFullName, dfmCommentFields,
				dfmPhysicalHostId, dfmPhysicalHostFullName
			}
	DESCRIPTION
		"A role on the host has been discovered."
	::= 11131

	dfmEvtHostRoleDeleted			TRAP-TYPE
	ENTERPRISE			netappDataFabricManager
	VARIABLES	{
				dfmSerialNumber, dfmEventSourceSerialNumber,
				dfmEventId, dfmEventName, dfmEventSeverity,
				dfmEventTimestamp, dfmEventMessage, 
				dfmEventMessageDetails,
				dfmEventSourceId, dfmEventSourceTable,
				dfmObjectId, dfmObjectType, dfmObjectFullName,
				dfmObjectStatus, dfmEventSourceProductId,
				dfmHostFullName, dfmCommentFields,
				dfmPhysicalHostId, dfmPhysicalHostFullName
			}
	DESCRIPTION
		"A role on the host has been deleted."
	::= 11132

	dfmEvtHostRoleModified			TRAP-TYPE
	ENTERPRISE			netappDataFabricManager
	VARIABLES	{
				dfmSerialNumber, dfmEventSourceSerialNumber,
				dfmEventId, dfmEventName, dfmEventSeverity,
				dfmEventTimestamp, dfmEventMessage, 
				dfmEventMessageDetails,
				dfmEventSourceId, dfmEventSourceTable,
				dfmObjectId, dfmObjectType, dfmObjectFullName,
				dfmObjectStatus, dfmEventSourceProductId,
				dfmHostFullName, dfmCommentFields,
				dfmPhysicalHostId, dfmPhysicalHostFullName
			}
	DESCRIPTION
		"A role on the host has been modified."
	::= 11133

	dfmEvtHostUsergroupDiscovered		TRAP-TYPE
	ENTERPRISE			netappDataFabricManager
	VARIABLES	{
				dfmSerialNumber, dfmEventSourceSerialNumber,
				dfmEventId, dfmEventName, dfmEventSeverity,
				dfmEventTimestamp, dfmEventMessage, 
				dfmEventMessageDetails,
				dfmEventSourceId, dfmEventSourceTable,
				dfmObjectId, dfmObjectType, dfmObjectFullName,
				dfmObjectStatus, dfmEventSourceProductId,
				dfmHostFullName, dfmCommentFields,
				dfmPhysicalHostId, dfmPhysicalHostFullName
			}
	DESCRIPTION
		"A usergroup on the host has been discovered."
	::= 11134

	dfmEvtHostUsergroupDeleted		TRAP-TYPE
	ENTERPRISE			netappDataFabricManager
	VARIABLES	{
				dfmSerialNumber, dfmEventSourceSerialNumber,
				dfmEventId, dfmEventName, dfmEventSeverity,
				dfmEventTimestamp, dfmEventMessage, 
				dfmEventMessageDetails,
				dfmEventSourceId, dfmEventSourceTable,
				dfmObjectId, dfmObjectType, dfmObjectFullName,
				dfmObjectStatus, dfmEventSourceProductId,
				dfmHostFullName, dfmCommentFields,
				dfmPhysicalHostId, dfmPhysicalHostFullName
			}
	DESCRIPTION
		"A usergroup on the host has been deleted."
	::= 11135

	dfmEvtHostUsergroupModified		TRAP-TYPE
	ENTERPRISE			netappDataFabricManager
	VARIABLES	{
				dfmSerialNumber, dfmEventSourceSerialNumber,
				dfmEventId, dfmEventName, dfmEventSeverity,
				dfmEventTimestamp, dfmEventMessage, 
				dfmEventMessageDetails,
				dfmEventSourceId, dfmEventSourceTable,
				dfmObjectId, dfmObjectType, dfmObjectFullName,
				dfmObjectStatus, dfmEventSourceProductId,
				dfmHostFullName, dfmCommentFields,
				dfmPhysicalHostId, dfmPhysicalHostFullName
			}
	DESCRIPTION
		"A usergroup on the host has been modified."
	::= 11136

	dfmEvtHostUserDiscovered		TRAP-TYPE
	ENTERPRISE			netappDataFabricManager
	VARIABLES	{
				dfmSerialNumber, dfmEventSourceSerialNumber,
				dfmEventId, dfmEventName, dfmEventSeverity,
				dfmEventTimestamp, dfmEventMessage, 
				dfmEventMessageDetails,
				dfmEventSourceId, dfmEventSourceTable,
				dfmObjectId, dfmObjectType, dfmObjectFullName,
				dfmObjectStatus, dfmEventSourceProductId,
				dfmHostFullName, dfmCommentFields,
				dfmPhysicalHostId, dfmPhysicalHostFullName
			}
	DESCRIPTION
		"A user on the host has been discovered."
	::= 11137

	dfmEvtHostUserDeleted			TRAP-TYPE
	ENTERPRISE			netappDataFabricManager
	VARIABLES	{
				dfmSerialNumber, dfmEventSourceSerialNumber,
				dfmEventId, dfmEventName, dfmEventSeverity,
				dfmEventTimestamp, dfmEventMessage, 
				dfmEventMessageDetails,
				dfmEventSourceId, dfmEventSourceTable,
				dfmObjectId, dfmObjectType, dfmObjectFullName,
				dfmObjectStatus, dfmEventSourceProductId,
				dfmHostFullName, dfmCommentFields,
				dfmPhysicalHostId, dfmPhysicalHostFullName
			}
	DESCRIPTION
		"A user on the host has been deleted."
	::= 11138

	dfmEvtHostUserModified			TRAP-TYPE
	ENTERPRISE			netappDataFabricManager
	VARIABLES	{
				dfmSerialNumber, dfmEventSourceSerialNumber,
				dfmEventId, dfmEventName, dfmEventSeverity,
				dfmEventTimestamp, dfmEventMessage, 
				dfmEventMessageDetails,
				dfmEventSourceId, dfmEventSourceTable,
				dfmObjectId, dfmObjectType, dfmObjectFullName,
				dfmObjectStatus, dfmEventSourceProductId,
				dfmHostFullName, dfmCommentFields,
				dfmPhysicalHostId, dfmPhysicalHostFullName
			}
	DESCRIPTION
		"A user on the host has been modified."
	::= 11139

	dfmEvtHostDomainUserModified		TRAP-TYPE
	ENTERPRISE			netappDataFabricManager
	VARIABLES	{
				dfmSerialNumber, dfmEventSourceSerialNumber,
				dfmEventId, dfmEventName, dfmEventSeverity,
				dfmEventTimestamp, dfmEventMessage, 
				dfmEventMessageDetails,
				dfmEventSourceId, dfmEventSourceTable,
				dfmObjectId, dfmObjectType, dfmObjectFullName,
				dfmObjectStatus, dfmEventSourceProductId,
				dfmHostFullName, dfmCommentFields,
				dfmPhysicalHostId, dfmPhysicalHostFullName
			}
	DESCRIPTION
		"A domain user on the host has been modified."
	::= 11140

	-- Volume Overcommit events

	dfmEvtVolumeQuotaOvercommitOk	TRAP-TYPE
	ENTERPRISE		netappDataFabricManager
	VARIABLES	{
				dfmSerialNumber, dfmEventSourceSerialNumber,
				dfmEventId, dfmEventName, dfmEventSeverity,
				dfmEventTimestamp, dfmEventMessage, 
				dfmEventMessageDetails,
				dfmEventSourceId, dfmEventSourceTable,
				dfmObjectId, dfmObjectType, dfmObjectFullName,
				dfmObjectStatus, dfmEventSourceProductId,
				dfmHostFullName, dfmCommentFields,
				dfmPhysicalHostId, dfmPhysicalHostFullName
			}
	DESCRIPTION	
		"The volume being managed by DataFabric Manager
		 is below its 'almostOvercommitted' threshold. Variable 
		 dfmObjectId identifies the volume."
	::= 11151

	dfmEvtVolumeQuotaAlmostOvercommitted	TRAP-TYPE
	ENTERPRISE		netappDataFabricManager
	VARIABLES	{
				dfmSerialNumber, dfmEventSourceSerialNumber,
				dfmEventId, dfmEventName, dfmEventSeverity,
				dfmEventTimestamp, dfmEventMessage, 
				dfmEventMessageDetails,
				dfmEventSourceId, dfmEventSourceTable,
				dfmObjectId, dfmObjectType, dfmObjectFullName,
				dfmObjectStatus, dfmEventSourceProductId,
				dfmHostFullName, dfmCommentFields,
				dfmPhysicalHostId, dfmPhysicalHostFullName
			}
	DESCRIPTION	
		"The volume being managed by DataFabric Manager 
		 has crossed the 'almostOvercommitted' threshold. 
		 Variable dfmObjectId identifies the volume."
	::= 11152
	
	dfmEvtVolumeQuotaOvercommitted	TRAP-TYPE
	ENTERPRISE		netappDataFabricManager
	VARIABLES	{
				dfmSerialNumber, dfmEventSourceSerialNumber,
				dfmEventId, dfmEventName, dfmEventSeverity,
				dfmEventTimestamp, dfmEventMessage, 
				dfmEventMessageDetails,
				dfmEventSourceId, dfmEventSourceTable,
				dfmObjectId, dfmObjectType, dfmObjectFullName,
				dfmObjectStatus, dfmEventSourceProductId,
				dfmHostFullName, dfmCommentFields,
				dfmPhysicalHostId, dfmPhysicalHostFullName
			}
	DESCRIPTION
		"The volume being managed by DataFabric Manager 
		 has crossed the 'overcommitted' threshold.
		 Variable dfmObjectId identifies the volume."
	::= 11153

	-- events for data set member resize

	dfmEvtDatasetMemberResized	TRAP-TYPE
	ENTERPRISE			netappDataFabricManager
	VARIABLES	{
				dfmSerialNumber, dfmEventSourceSerialNumber,
				dfmEventId, dfmEventName, dfmEventSeverity,
				dfmEventTimestamp, dfmEventMessage, 
				dfmEventMessageDetails,
				dfmEventSourceId,
				dfmObjectId, dfmObjectType, dfmObjectFullName,
				dfmObjectStatus, dfmEventSourceProductId,
				dfmHostFullName,
				dfmPhysicalHostId, dfmPhysicalHostFullName
			}
	DESCRIPTION
		"Data set member resized successfully."
	::= 11171

	dfmEvtDatasetMemberResizeFailed		TRAP-TYPE
	ENTERPRISE			netappDataFabricManager
	VARIABLES	{
				dfmSerialNumber, dfmEventSourceSerialNumber,
				dfmEventId, dfmEventName, dfmEventSeverity,
				dfmEventTimestamp, dfmEventMessage, 
				dfmEventMessageDetails,
				dfmEventSourceId,
				dfmObjectId, dfmObjectType, dfmObjectFullName,
				dfmObjectStatus, dfmEventSourceProductId,
				dfmHostFullName,
				dfmPhysicalHostId, dfmPhysicalHostFullName
			}
	DESCRIPTION
		"Data set member resize operation failed."
	::= 11172

	dfmEvtProvisioningPolicyCreated		TRAP-TYPE
	ENTERPRISE			netappDataFabricManager
	VARIABLES	{
				dfmSerialNumber, dfmEventSourceSerialNumber,
				dfmEventId, dfmEventName, dfmEventSeverity,
				dfmEventTimestamp, dfmEventMessage, 
				dfmEventMessageDetails,
				dfmEventSourceId,
				dfmObjectId, dfmObjectType, dfmObjectFullName,
				dfmObjectStatus, dfmEventSourceProductId,
				dfmHostFullName,
				dfmPhysicalHostId, dfmPhysicalHostFullName
			}
	DESCRIPTION
		"A provisioning policy has been created."
	::= 11181

	dfmEvtProvisioningPolicyDeleted		TRAP-TYPE
	ENTERPRISE			netappDataFabricManager
	VARIABLES	{
				dfmSerialNumber, dfmEventSourceSerialNumber,
				dfmEventId, dfmEventName, dfmEventSeverity,
				dfmEventTimestamp, dfmEventMessage, 
				dfmEventMessageDetails,
				dfmEventSourceId,
				dfmObjectId, dfmObjectType, dfmObjectFullName,
				dfmObjectStatus, dfmEventSourceProductId,
				dfmHostFullName,
				dfmPhysicalHostId, dfmPhysicalHostFullName
			}
	DESCRIPTION
		"A provisioning policy has been deleted."
	::= 11182

	dfmEvtProvisioningPolicyModified	TRAP-TYPE
	ENTERPRISE			netappDataFabricManager
	VARIABLES	{
				dfmSerialNumber, dfmEventSourceSerialNumber,
				dfmEventId, dfmEventName, dfmEventSeverity,
				dfmEventTimestamp, dfmEventMessage, 
				dfmEventMessageDetails,
				dfmEventSourceId,
				dfmObjectId, dfmObjectType, dfmObjectFullName,
				dfmObjectStatus, dfmEventSourceProductId,
				dfmHostFullName,
				dfmPhysicalHostId, dfmPhysicalHostFullName
			}
	DESCRIPTION
		"A provisioning policy has been modified."
	::= 11183

       dfmEvtVFilerTemplateCreated         TRAP-TYPE
        ENTERPRISE                      netappDataFabricManager
        VARIABLES       {
                                dfmSerialNumber, dfmEventSourceSerialNumber,
                                dfmEventId, dfmEventName, dfmEventSeverity,
                                dfmEventTimestamp, dfmEventMessage,
                                dfmEventMessageDetails,
                                dfmEventSourceId,
                                dfmObjectId, dfmObjectType, dfmObjectFullName,
                                dfmObjectStatus, dfmEventSourceProductId,
                                dfmHostFullName,
				dfmPhysicalHostId, dfmPhysicalHostFullName
                        }
        DESCRIPTION
                "A vfiler template has been created."
       ::= 11191

	dfmEvtVFilerTemplateDeleted         TRAP-TYPE
        ENTERPRISE                      netappDataFabricManager
        VARIABLES       {
                                dfmSerialNumber, dfmEventSourceSerialNumber,
                                dfmEventId, dfmEventName, dfmEventSeverity,
                                dfmEventTimestamp, dfmEventMessage,
                                dfmEventMessageDetails,
                                dfmEventSourceId,
                                dfmObjectId, dfmObjectType, dfmObjectFullName,
                                dfmObjectStatus, dfmEventSourceProductId,
                                dfmHostFullName,
				dfmPhysicalHostId, dfmPhysicalHostFullName
                        }
        DESCRIPTION
                "A vfiler template has been deleted."
        ::= 11192

        dfmEvtVFilerTemplateModified        TRAP-TYPE
        ENTERPRISE                      netappDataFabricManager
        VARIABLES       {
                                dfmSerialNumber, dfmEventSourceSerialNumber,
                                dfmEventId, dfmEventName, dfmEventSeverity,
                                dfmEventTimestamp, dfmEventMessage,
                                dfmEventMessageDetails,
                                dfmEventSourceId,
                                dfmObjectId, dfmObjectType, dfmObjectFullName,
                                dfmObjectStatus, dfmEventSourceProductId,
                                dfmHostFullName,
				dfmPhysicalHostId, dfmPhysicalHostFullName
                        }
        DESCRIPTION
                "A vfiler template has been modified."
        ::= 11193

	dfmEvtDatasetSpaceOk		TRAP-TYPE
	ENTERPRISE			netappDataFabricManager
	VARIABLES	{
				dfmSerialNumber, dfmEventSourceSerialNumber,
				dfmEventId, dfmEventName, dfmEventSeverity,
				dfmEventTimestamp, dfmEventMessage, 
				dfmEventMessageDetails,
				dfmEventSourceId,
				dfmObjectId, dfmObjectType, dfmObjectFullName,
				dfmObjectStatus, dfmEventSourceProductId,
				dfmHostFullName,
				dfmPhysicalHostId, dfmPhysicalHostFullName
			}
	DESCRIPTION
		"Data set space status is normal."
	::= 11201

	dfmEvtDatasetSpaceWarning		TRAP-TYPE
	ENTERPRISE			netappDataFabricManager
	VARIABLES	{
				dfmSerialNumber, dfmEventSourceSerialNumber,
				dfmEventId, dfmEventName, dfmEventSeverity,
				dfmEventTimestamp, dfmEventMessage, 
				dfmEventMessageDetails,
				dfmEventSourceId,
				dfmObjectId, dfmObjectType, dfmObjectFullName,
				dfmObjectStatus, dfmEventSourceProductId,
				dfmHostFullName,
				dfmPhysicalHostId, dfmPhysicalHostFullName
			}
	DESCRIPTION
		"Data set space status is in warning state."
	::= 11202

	dfmEvtDatasetSpaceError		TRAP-TYPE
	ENTERPRISE			netappDataFabricManager
	VARIABLES	{
				dfmSerialNumber, dfmEventSourceSerialNumber,
				dfmEventId, dfmEventName, dfmEventSeverity,
				dfmEventTimestamp, dfmEventMessage, 
				dfmEventMessageDetails,
				dfmEventSourceId,
				dfmObjectId, dfmObjectType, dfmObjectFullName,
				dfmObjectStatus, dfmEventSourceProductId,
				dfmHostFullName,
				dfmPhysicalHostId, dfmPhysicalHostFullName
			}
	DESCRIPTION
		"Data set space status is in error state."
	::= 11203

	dfmEvtVolumeAutosized		TRAP-TYPE
	ENTERPRISE			netappDataFabricManager
	VARIABLES	{
				dfmSerialNumber, dfmEventSourceSerialNumber,
				dfmEventId, dfmEventName, dfmEventSeverity,
				dfmEventTimestamp, dfmEventMessage, 
				dfmEventMessageDetails,
				dfmEventSourceId,
				dfmObjectId, dfmObjectType, dfmObjectFullName,
				dfmObjectStatus, dfmEventSourceProductId,
				dfmHostFullName,
				dfmPhysicalHostId, dfmPhysicalHostFullName
			}
	DESCRIPTION
		"Volume was autosized."
	::= 11211

	dfmEvtVolumeSnapshotsAutoDeleted		TRAP-TYPE
	ENTERPRISE			netappDataFabricManager
	VARIABLES	{
				dfmSerialNumber, dfmEventSourceSerialNumber,
				dfmEventId, dfmEventName, dfmEventSeverity,
				dfmEventTimestamp, dfmEventMessage, 
				dfmEventMessageDetails,
				dfmEventSourceId,
				dfmObjectId, dfmObjectType, dfmObjectFullName,
				dfmObjectStatus, dfmEventSourceProductId,
				dfmHostFullName,
				dfmPhysicalHostId, dfmPhysicalHostFullName
			}
	DESCRIPTION
		"Snapshots in the volume were automatically deleted."
	::= 11221

	dfmEvtVolumeNextSnapshotNotPossible TRAP-TYPE
	ENTERPRISE			netappDataFabricManager
	VARIABLES	{
				dfmSerialNumber, dfmEventSourceSerialNumber,
				dfmEventId, dfmEventName, dfmEventSeverity,
				dfmEventTimestamp, dfmEventMessage, 
				dfmEventMessageDetails,
				dfmEventSourceId,
				dfmObjectId, dfmObjectType, dfmObjectFullName,
				dfmObjectStatus, dfmEventSourceProductId,
				dfmHostFullName,
				dfmPhysicalHostId, dfmPhysicalHostFullName
			}
	DESCRIPTION
		"The next snapshot cannot be taken on the volume due to lack of
		space."
	::= 11231

	dfmEvtVolumeNextSnapshotPossible TRAP-TYPE
	ENTERPRISE			netappDataFabricManager
	VARIABLES	{
				dfmSerialNumber, dfmEventSourceSerialNumber,
				dfmEventId, dfmEventName, dfmEventSeverity,
				dfmEventTimestamp, dfmEventMessage, 
				dfmEventMessageDetails,
				dfmEventSourceId,
				dfmObjectId, dfmObjectType, dfmObjectFullName,
				dfmObjectStatus, dfmEventSourceProductId,
				dfmHostFullName,
				dfmPhysicalHostId, dfmPhysicalHostFullName
			}
	DESCRIPTION
		"The next snapshot can be taken on the volume."
	::= 11232

	-- events for data set member destroy

	dfmEvtDatasetMemberDestroyed	TRAP-TYPE
	ENTERPRISE			netappDataFabricManager
	VARIABLES	{
				dfmSerialNumber, dfmEventSourceSerialNumber,
				dfmEventId, dfmEventName, dfmEventSeverity,
				dfmEventTimestamp, dfmEventMessage, 
				dfmEventMessageDetails,
				dfmEventSourceId,
				dfmObjectId, dfmObjectType, dfmObjectFullName,
				dfmObjectStatus, dfmEventSourceProductId,
				dfmHostFullName,
				dfmPhysicalHostId, dfmPhysicalHostFullName
			}
	DESCRIPTION
		"Data set member destroyed successfully."
	::= 11241

	dfmEvtDatasetMemberDestroyFailed		TRAP-TYPE
	ENTERPRISE			netappDataFabricManager
	VARIABLES	{
				dfmSerialNumber, dfmEventSourceSerialNumber,
				dfmEventId, dfmEventName, dfmEventSeverity,
				dfmEventTimestamp, dfmEventMessage, 
				dfmEventMessageDetails,
				dfmEventSourceId,
				dfmObjectId, dfmObjectType, dfmObjectFullName,
				dfmObjectStatus, dfmEventSourceProductId,
				dfmHostFullName,
				dfmPhysicalHostId, dfmPhysicalHostFullName
			}
	DESCRIPTION
		"Data set member destroy operation failed."
	::= 11242

	-- events for DR Failover State transitions

	dfmEvtDatasetDrStateReady		TRAP-TYPE
	ENTERPRISE			netappDataFabricManager
	VARIABLES	{
				dfmSerialNumber, dfmEventSourceSerialNumber,
				dfmEventId, dfmEventName, dfmEventSeverity,
				dfmEventTimestamp, dfmEventMessage, 
				dfmEventMessageDetails,
				dfmEventSourceId,
				dfmObjectId, dfmObjectType, dfmObjectFullName,
				dfmObjectStatus, dfmEventSourceProductId,
				dfmHostFullName,
				dfmPhysicalHostId, dfmPhysicalHostFullName
			}
	DESCRIPTION
		"Data set Disaster Recovery state is ready."
	::= 11400


	dfmEvtDatasetDrStateFailingOver		TRAP-TYPE
	ENTERPRISE			netappDataFabricManager
	VARIABLES	{
				dfmSerialNumber, dfmEventSourceSerialNumber,
				dfmEventId, dfmEventName, dfmEventSeverity,
				dfmEventTimestamp, dfmEventMessage, 
				dfmEventMessageDetails,
				dfmEventSourceId,
				dfmObjectId, dfmObjectType, dfmObjectFullName,
				dfmObjectStatus, dfmEventSourceProductId,
				dfmHostFullName,
				dfmPhysicalHostId, dfmPhysicalHostFullName
			}
	DESCRIPTION
		"Data set Disaster Recovery state is failing over."
	::= 11401

	dfmEvtDatasetDrStateFailedOver		TRAP-TYPE
	ENTERPRISE			netappDataFabricManager
	VARIABLES	{
				dfmSerialNumber, dfmEventSourceSerialNumber,
				dfmEventId, dfmEventName, dfmEventSeverity,
				dfmEventTimestamp, dfmEventMessage, 
				dfmEventMessageDetails,
				dfmEventSourceId,
				dfmObjectId, dfmObjectType, dfmObjectFullName,
				dfmObjectStatus, dfmEventSourceProductId,
				dfmHostFullName,
				dfmPhysicalHostId, dfmPhysicalHostFullName
			}
	DESCRIPTION
		"Data set Disaster Recovery state is failed over."
	::= 11402

	dfmEvtDatasetDrStateFailoverError		TRAP-TYPE
	ENTERPRISE			netappDataFabricManager
	VARIABLES	{
				dfmSerialNumber, dfmEventSourceSerialNumber,
				dfmEventId, dfmEventName, dfmEventSeverity,
				dfmEventTimestamp, dfmEventMessage, 
				dfmEventMessageDetails,
				dfmEventSourceId,
				dfmObjectId, dfmObjectType, dfmObjectFullName,
				dfmObjectStatus, dfmEventSourceProductId,
				dfmHostFullName,
				dfmPhysicalHostId, dfmPhysicalHostFullName
			}
	DESCRIPTION
		"Data set Disaster Recovery state is failover error."
	::= 11403


	-- events for DR Failover Status transitions

	dfmEvtDatasetDrStatusNormal		TRAP-TYPE
	ENTERPRISE			netappDataFabricManager
	VARIABLES	{
				dfmSerialNumber, dfmEventSourceSerialNumber,
				dfmEventId, dfmEventName, dfmEventSeverity,
				dfmEventTimestamp, dfmEventMessage, 
				dfmEventMessageDetails,
				dfmEventSourceId,
				dfmObjectId, dfmObjectType, dfmObjectFullName,
				dfmObjectStatus, dfmEventSourceProductId,
				dfmHostFullName,
				dfmPhysicalHostId, dfmPhysicalHostFullName
			}
	DESCRIPTION
		"Data set Disaster Recovery status is normal."
	::= 11410


	dfmEvtDatasetDrStatusWarning		TRAP-TYPE
	ENTERPRISE			netappDataFabricManager
	VARIABLES	{
				dfmSerialNumber, dfmEventSourceSerialNumber,
				dfmEventId, dfmEventName, dfmEventSeverity,
				dfmEventTimestamp, dfmEventMessage, 
				dfmEventMessageDetails,
				dfmEventSourceId,
				dfmObjectId, dfmObjectType, dfmObjectFullName,
				dfmObjectStatus, dfmEventSourceProductId,
				dfmHostFullName,
				dfmPhysicalHostId, dfmPhysicalHostFullName
			}
	DESCRIPTION
		"Data set Disaster Recovery status is warning."
	::= 11411

	dfmEvtDatasetDrStatusError		TRAP-TYPE
	ENTERPRISE			netappDataFabricManager
	VARIABLES	{
				dfmSerialNumber, dfmEventSourceSerialNumber,
				dfmEventId, dfmEventName, dfmEventSeverity,
				dfmEventTimestamp, dfmEventMessage, 
				dfmEventMessageDetails,
				dfmEventSourceId,
				dfmObjectId, dfmObjectType, dfmObjectFullName,
				dfmObjectStatus, dfmEventSourceProductId,
				dfmHostFullName,
				dfmPhysicalHostId, dfmPhysicalHostFullName
			}
	DESCRIPTION
		"Data set Disaster Recovery status is error."
	::= 11412

	-- Data Export events

	dfmEvtDataExportOk TRAP-TYPE
	ENTERPRISE		netappDataFabricManager
	VARIABLES	{
				dfmSerialNumber, dfmEventSourceSerialNumber,
				dfmEventId, dfmEventName, dfmEventSeverity,
				dfmEventTimestamp, dfmEventMessage, 
				dfmEventMessageDetails,
				dfmEventSourceId, dfmEventSourceTable,
				dfmObjectId, dfmObjectType, dfmObjectFullName,
				dfmObjectStatus, dfmEventSourceProductId,
				dfmHostFullName, dfmCommentFields,
				dfmPhysicalHostId, dfmPhysicalHostFullName
			}
	DESCRIPTION	
		"The data export run has succeeded."

	::= 11161

	dfmEvtDataExportFailed TRAP-TYPE
	ENTERPRISE		netappDataFabricManager
	VARIABLES	{
				dfmSerialNumber, dfmEventSourceSerialNumber,
				dfmEventId, dfmEventName, dfmEventSeverity,
				dfmEventTimestamp, dfmEventMessage, 
				dfmEventMessageDetails,
				dfmEventSourceId, dfmEventSourceTable,
				dfmObjectId, dfmObjectType, dfmObjectFullName,
				dfmObjectStatus, dfmEventSourceProductId,
				dfmHostFullName, dfmCommentFields,
				dfmPhysicalHostId, dfmPhysicalHostFullName
			}
	DESCRIPTION	
		"The data export run has failed."

	::= 11162

	dfmEvtMgmtStProvMgrNodeLimitOk	TRAP-TYPE
	ENTERPRISE		netappDataFabricManager
	VARIABLES	{
				dfmSerialNumber, dfmEventSourceSerialNumber,
				dfmEventId, dfmEventName, dfmEventSeverity,
				dfmEventTimestamp, dfmEventMessage, 
				dfmEventMessageDetails,
				dfmEventSourceId, dfmEventSourceTable,
				dfmObjectId, dfmObjectType, dfmObjectFullName,
				dfmObjectStatus, dfmEventSourceProductId,
				dfmHostFullName, dfmCommentFields,
				dfmPhysicalHostId, dfmPhysicalHostFullName
			}
	DESCRIPTION	
		"The number of nodes being managed by
		 Provisioning Manager is below the node 
		 limit specified in the license key."
	::= 11262

	dfmEvtMgmtStProvMgrNodeLimitNearlyReached	TRAP-TYPE
	ENTERPRISE		netappDataFabricManager
	VARIABLES	{
				dfmSerialNumber, dfmEventSourceSerialNumber,
				dfmEventId, dfmEventName, dfmEventSeverity,
				dfmEventTimestamp, dfmEventMessage, 
				dfmEventMessageDetails,
				dfmEventSourceId, dfmEventSourceTable,
				dfmObjectId, dfmObjectType, dfmObjectFullName,
				dfmObjectStatus, dfmEventSourceProductId,
				dfmHostFullName, dfmCommentFields,
				dfmPhysicalHostId, dfmPhysicalHostFullName
			}
	DESCRIPTION	
		"The number of nodes being managed by
		 Provisioning Manager has nearly reached 
		 the node limit specified in the 
		 license key."
	::= 11263

	dfmEvtMgmtStProvMgrNodeLimitReached	TRAP-TYPE
	ENTERPRISE		netappDataFabricManager
	VARIABLES	{
				dfmSerialNumber, dfmEventSourceSerialNumber,
				dfmEventId, dfmEventName, dfmEventSeverity,
				dfmEventTimestamp, dfmEventMessage, 
				dfmEventMessageDetails,
				dfmEventSourceId, dfmEventSourceTable,
				dfmObjectId, dfmObjectType, dfmObjectFullName,
				dfmObjectStatus, dfmEventSourceProductId,
				dfmHostFullName, dfmCommentFields,
				dfmPhysicalHostId, dfmPhysicalHostFullName
			}
	DESCRIPTION	
		"The number of nodes being managed by
		 Provisioning Manager has reached the node 
		 limit specified in the license key."
	::= 11264

	dfmEvtMgmtStProtMgrNodeLimitOk	TRAP-TYPE
	ENTERPRISE		netappDataFabricManager
	VARIABLES	{
				dfmSerialNumber, dfmEventSourceSerialNumber,
				dfmEventId, dfmEventName, dfmEventSeverity,
				dfmEventTimestamp, dfmEventMessage, 
				dfmEventMessageDetails,
				dfmEventSourceId, dfmEventSourceTable,
				dfmObjectId, dfmObjectType, dfmObjectFullName,
				dfmObjectStatus, dfmEventSourceProductId,
				dfmHostFullName, dfmCommentFields,
				dfmPhysicalHostId, dfmPhysicalHostFullName
			}
	DESCRIPTION	
		"The number of nodes being managed by
		 Protection Manager is below the node 
		 limit specified in the license key."
	::= 11265

	dfmEvtMgmtStProtMgrNodeLimitNearlyReached	TRAP-TYPE
	ENTERPRISE		netappDataFabricManager
	VARIABLES	{
				dfmSerialNumber, dfmEventSourceSerialNumber,
				dfmEventId, dfmEventName, dfmEventSeverity,
				dfmEventTimestamp, dfmEventMessage, 
				dfmEventMessageDetails,
				dfmEventSourceId, dfmEventSourceTable,
				dfmObjectId, dfmObjectType, dfmObjectFullName,
				dfmObjectStatus, dfmEventSourceProductId,
				dfmHostFullName, dfmCommentFields,
				dfmPhysicalHostId, dfmPhysicalHostFullName
			}
	DESCRIPTION	
		"The number of nodes being managed by
		 Protection Manager has nearly reached 
		 the node limit specified in the 
		 license key."
	::= 11266

	dfmEvtMgmtStProtMgrNodeLimitReached	TRAP-TYPE
	ENTERPRISE		netappDataFabricManager
	VARIABLES	{
				dfmSerialNumber, dfmEventSourceSerialNumber,
				dfmEventId, dfmEventName, dfmEventSeverity,
				dfmEventTimestamp, dfmEventMessage, 
				dfmEventMessageDetails,
				dfmEventSourceId, dfmEventSourceTable,
				dfmObjectId, dfmObjectType, dfmObjectFullName,
				dfmObjectStatus, dfmEventSourceProductId,
				dfmHostFullName, dfmCommentFields,
				dfmPhysicalHostId, dfmPhysicalHostFullName
			}
	DESCRIPTION	
		"The number of nodes being managed by
		 Protection Manager has reached the node 
		 limit specified in the license key."
	::= 11267
	
	dfmEvtDatasetNotMigrating TRAP-TYPE
	ENTERPRISE		netappDataFabricManager
	VARIABLES	{
				dfmSerialNumber, dfmEventSourceSerialNumber,
				dfmEventId, dfmEventName, dfmEventSeverity,
				dfmEventTimestamp, dfmEventMessage, 
				dfmEventMessageDetails,
				dfmEventSourceId, dfmEventSourceTable,
				dfmObjectId, dfmObjectType, dfmObjectFullName,
				dfmObjectStatus, dfmEventSourceProductId,
				dfmHostFullName, dfmCommentFields,
				dfmPhysicalHostId, dfmPhysicalHostFullName
			}
	DESCRIPTION	
		"The dataset is not migrating."

	::= 11270

	dfmEvtDatasetMigrating TRAP-TYPE
	ENTERPRISE		netappDataFabricManager
	VARIABLES	{
				dfmSerialNumber, dfmEventSourceSerialNumber,
				dfmEventId, dfmEventName, dfmEventSeverity,
				dfmEventTimestamp, dfmEventMessage, 
				dfmEventMessageDetails,
				dfmEventSourceId, dfmEventSourceTable,
				dfmObjectId, dfmObjectType, dfmObjectFullName,
				dfmObjectStatus, dfmEventSourceProductId,
				dfmHostFullName, dfmCommentFields,
				dfmPhysicalHostId, dfmPhysicalHostFullName
			}
	DESCRIPTION	
		"The dataset is migrating."

	::= 11271

	dfmEvtDatasetMigrateFailed TRAP-TYPE
	ENTERPRISE		netappDataFabricManager
	VARIABLES	{
				dfmSerialNumber, dfmEventSourceSerialNumber,
				dfmEventId, dfmEventName, dfmEventSeverity,
				dfmEventTimestamp, dfmEventMessage, 
				dfmEventMessageDetails,
				dfmEventSourceId, dfmEventSourceTable,
				dfmObjectId, dfmObjectType, dfmObjectFullName,
				dfmObjectStatus, dfmEventSourceProductId,
				dfmHostFullName, dfmCommentFields,
				dfmPhysicalHostId, dfmPhysicalHostFullName
			}
	DESCRIPTION	
		"Dataset migration failed."

	::= 11272

	dfmEvtDatasetMigratedWithErrors TRAP-TYPE
	ENTERPRISE		netappDataFabricManager
	VARIABLES	{
				dfmSerialNumber, dfmEventSourceSerialNumber,
				dfmEventId, dfmEventName, dfmEventSeverity,
				dfmEventTimestamp, dfmEventMessage, 
				dfmEventMessageDetails,
				dfmEventSourceId, dfmEventSourceTable,
				dfmObjectId, dfmObjectType, dfmObjectFullName,
				dfmObjectStatus, dfmEventSourceProductId,
				dfmHostFullName, dfmCommentFields,
				dfmPhysicalHostId, dfmPhysicalHostFullName
			}
	DESCRIPTION	
		"The dataset is migrated with errors."

	::= 11273

	dfmEvtDatasetMigrated TRAP-TYPE
	ENTERPRISE		netappDataFabricManager
	VARIABLES	{
				dfmSerialNumber, dfmEventSourceSerialNumber,
				dfmEventId, dfmEventName, dfmEventSeverity,
				dfmEventTimestamp, dfmEventMessage, 
				dfmEventMessageDetails,
				dfmEventSourceId, dfmEventSourceTable,
				dfmObjectId, dfmObjectType, dfmObjectFullName,
				dfmObjectStatus, dfmEventSourceProductId,
				dfmHostFullName, dfmCommentFields,
				dfmPhysicalHostId, dfmPhysicalHostFullName
			}
	DESCRIPTION	
		"The dataset is migrated."

	::= 11274

	dfmEvtDatasetRollbackWithErrors TRAP-TYPE
	ENTERPRISE		netappDataFabricManager
	VARIABLES	{
				dfmSerialNumber, dfmEventSourceSerialNumber,
				dfmEventId, dfmEventName, dfmEventSeverity,
				dfmEventTimestamp, dfmEventMessage, 
				dfmEventMessageDetails,
				dfmEventSourceId, dfmEventSourceTable,
				dfmObjectId, dfmObjectType, dfmObjectFullName,
				dfmObjectStatus, dfmEventSourceProductId,
				dfmHostFullName, dfmCommentFields
			}
	DESCRIPTION	
		"The dataset is rolledback with errors."

	::= 11275

	dfmEvtDatasetRollback TRAP-TYPE
	ENTERPRISE		netappDataFabricManager
	VARIABLES	{
				dfmSerialNumber, dfmEventSourceSerialNumber,
				dfmEventId, dfmEventName, dfmEventSeverity,
				dfmEventTimestamp, dfmEventMessage, 
				dfmEventMessageDetails,
				dfmEventSourceId, dfmEventSourceTable,
				dfmObjectId, dfmObjectType, dfmObjectFullName,
				dfmObjectStatus, dfmEventSourceProductId,
				dfmHostFullName, dfmCommentFields
			}
	DESCRIPTION	
		"The dataset is rolledback."


	::= 11279
	dfmEvtVfilerNotMigrating TRAP-TYPE
	ENTERPRISE		netappDataFabricManager
	VARIABLES	{
				dfmSerialNumber, dfmEventSourceSerialNumber,
				dfmEventId, dfmEventName, dfmEventSeverity,
				dfmEventTimestamp, dfmEventMessage, 
				dfmEventMessageDetails,
				dfmEventSourceId, dfmEventSourceTable,
				dfmObjectId, dfmObjectType, dfmObjectFullName,
				dfmObjectStatus, dfmEventSourceProductId,
				dfmHostFullName, dfmCommentFields,
				dfmPhysicalHostId, dfmPhysicalHostFullName
			}
	DESCRIPTION	
		"The vfiler unit is not migrating."

	::= 11280

	dfmEvtVfilerMigrating TRAP-TYPE
	ENTERPRISE		netappDataFabricManager
	VARIABLES	{
				dfmSerialNumber, dfmEventSourceSerialNumber,
				dfmEventId, dfmEventName, dfmEventSeverity,
				dfmEventTimestamp, dfmEventMessage, 
				dfmEventMessageDetails,
				dfmEventSourceId, dfmEventSourceTable,
				dfmObjectId, dfmObjectType, dfmObjectFullName,
				dfmObjectStatus, dfmEventSourceProductId,
				dfmHostFullName, dfmCommentFields,
				dfmPhysicalHostId, dfmPhysicalHostFullName
			}
	DESCRIPTION	
		"The vfiler unit is migrating."

	::= 11281

	dfmEvtVfilerMigrateFailed TRAP-TYPE
	ENTERPRISE		netappDataFabricManager
	VARIABLES	{
				dfmSerialNumber, dfmEventSourceSerialNumber,
				dfmEventId, dfmEventName, dfmEventSeverity,
				dfmEventTimestamp, dfmEventMessage, 
				dfmEventMessageDetails,
				dfmEventSourceId, dfmEventSourceTable,
				dfmObjectId, dfmObjectType, dfmObjectFullName,
				dfmObjectStatus, dfmEventSourceProductId,
				dfmHostFullName, dfmCommentFields,
				dfmPhysicalHostId, dfmPhysicalHostFullName
			}
	DESCRIPTION	
		"The vfiler unit is migrate failed."

	::= 11282

	dfmEvtVfilerMigratedWithErrors TRAP-TYPE
	ENTERPRISE		netappDataFabricManager
	VARIABLES	{
				dfmSerialNumber, dfmEventSourceSerialNumber,
				dfmEventId, dfmEventName, dfmEventSeverity,
				dfmEventTimestamp, dfmEventMessage, 
				dfmEventMessageDetails,
				dfmEventSourceId, dfmEventSourceTable,
				dfmObjectId, dfmObjectType, dfmObjectFullName,
				dfmObjectStatus, dfmEventSourceProductId,
				dfmHostFullName, dfmCommentFields,
				dfmPhysicalHostId, dfmPhysicalHostFullName
			}
	DESCRIPTION	
		"The vfiler unit is migrated with errors."

	::= 11283

	dfmEvtVfilerMigrated TRAP-TYPE
	ENTERPRISE		netappDataFabricManager
	VARIABLES	{
				dfmSerialNumber, dfmEventSourceSerialNumber,
				dfmEventId, dfmEventName, dfmEventSeverity,
				dfmEventTimestamp, dfmEventMessage, 
				dfmEventMessageDetails,
				dfmEventSourceId, dfmEventSourceTable,
				dfmObjectId, dfmObjectType, dfmObjectFullName,
				dfmObjectStatus, dfmEventSourceProductId,
				dfmHostFullName, dfmCommentFields,
				dfmPhysicalHostId, dfmPhysicalHostFullName
			}
	DESCRIPTION	
		"The vfiler unit is migrated."

	::= 11284

	-- Deduplication related events

	dfmEvtVolumeOverDeduplicated TRAP-TYPE
	ENTERPRISE		netappDataFabricManager
	VARIABLES	{
				dfmSerialNumber, dfmEventSourceSerialNumber,
				dfmEventId, dfmEventName, dfmEventSeverity,
				dfmEventTimestamp, dfmEventMessage, 
				dfmEventMessageDetails,
				dfmEventSourceId, dfmEventSourceTable,
				dfmObjectId, dfmObjectType, dfmObjectFullName,
				dfmObjectStatus, dfmEventSourceProductId,
				dfmHostFullName, dfmCommentFields,
				dfmPhysicalHostId, dfmPhysicalHostFullName
			}
	DESCRIPTION	
		"The volume has over deduplicated."

	::= 11285

	dfmEvtVfilerRollbackWithErrors TRAP-TYPE
	ENTERPRISE		netappDataFabricManager
	VARIABLES	{
				dfmSerialNumber, dfmEventSourceSerialNumber,
				dfmEventId, dfmEventName, dfmEventSeverity,
				dfmEventTimestamp, dfmEventMessage, 
				dfmEventMessageDetails,
				dfmEventSourceId, dfmEventSourceTable,
				dfmObjectId, dfmObjectType, dfmObjectFullName,
				dfmObjectStatus, dfmEventSourceProductId,
				dfmHostFullName, dfmCommentFields
			}
	DESCRIPTION	
		"The vfiler is rolledback with errors."

	::= 11286

	dfmEvtVfilerRollback TRAP-TYPE
	ENTERPRISE		netappDataFabricManager
	VARIABLES	{
				dfmSerialNumber, dfmEventSourceSerialNumber,
				dfmEventId, dfmEventName, dfmEventSeverity,
				dfmEventTimestamp, dfmEventMessage, 
				dfmEventMessageDetails,
				dfmEventSourceId, dfmEventSourceTable,
				dfmObjectId, dfmObjectType, dfmObjectFullName,
				dfmObjectStatus, dfmEventSourceProductId,
				dfmHostFullName, dfmCommentFields
			}
	DESCRIPTION
		"The vfiler is rolledback."

	::= 11291

	dfmEvtVolumeNearlyOverDeduplicated TRAP-TYPE
	ENTERPRISE		netappDataFabricManager
	VARIABLES	{
				dfmSerialNumber, dfmEventSourceSerialNumber,
				dfmEventId, dfmEventName, dfmEventSeverity,
				dfmEventTimestamp, dfmEventMessage, 
				dfmEventMessageDetails,
				dfmEventSourceId, dfmEventSourceTable,
				dfmObjectId, dfmObjectType, dfmObjectFullName,
				dfmObjectStatus, dfmEventSourceProductId,
				dfmHostFullName, dfmCommentFields,
				dfmPhysicalHostId, dfmPhysicalHostFullName
			}
	DESCRIPTION	
		"The volume has nearly over deduplicated."

	::= 11292
	
	dfmEvtVolumeNotOverDeduplicated TRAP-TYPE
	ENTERPRISE		netappDataFabricManager
	VARIABLES	{
				dfmSerialNumber, dfmEventSourceSerialNumber,
				dfmEventId, dfmEventName, dfmEventSeverity,
				dfmEventTimestamp, dfmEventMessage, 
				dfmEventMessageDetails,
				dfmEventSourceId, dfmEventSourceTable,
				dfmObjectId, dfmObjectType, dfmObjectFullName,
				dfmObjectStatus, dfmEventSourceProductId,
				dfmHostFullName, dfmCommentFields,
				dfmPhysicalHostId, dfmPhysicalHostFullName
			}
	DESCRIPTION	
		"The volume has not over deduplicated."

	::= 11293
	
	dfmEvtAggregateOverDeduplicated TRAP-TYPE
	ENTERPRISE		netappDataFabricManager
	VARIABLES	{
				dfmSerialNumber, dfmEventSourceSerialNumber,
				dfmEventId, dfmEventName, dfmEventSeverity,
				dfmEventTimestamp, dfmEventMessage, 
				dfmEventMessageDetails,
				dfmEventSourceId, dfmEventSourceTable,
				dfmObjectId, dfmObjectType, dfmObjectFullName,
				dfmObjectStatus, dfmEventSourceProductId,
				dfmHostFullName, dfmCommentFields,
				dfmPhysicalHostId, dfmPhysicalHostFullName
			}
	DESCRIPTION	
		"The aggregate has over deduplicated."
		
	::= 11294


	dfmEvtAggregateNearlyOverDeduplicated TRAP-TYPE
	ENTERPRISE		netappDataFabricManager
	VARIABLES	{
				dfmSerialNumber, dfmEventSourceSerialNumber,
				dfmEventId, dfmEventName, dfmEventSeverity,
				dfmEventTimestamp, dfmEventMessage, 
				dfmEventMessageDetails,
				dfmEventSourceId, dfmEventSourceTable,
				dfmObjectId, dfmObjectType, dfmObjectFullName,
				dfmObjectStatus, dfmEventSourceProductId,
				dfmHostFullName, dfmCommentFields,
				dfmPhysicalHostId, dfmPhysicalHostFullName
			}
	DESCRIPTION	
		"The aggregate has nearly over deduplicated."
		
	::= 11295
	
	dfmEvtAggregateNotOverDeduplicated TRAP-TYPE
	ENTERPRISE		netappDataFabricManager
	VARIABLES	{
				dfmSerialNumber, dfmEventSourceSerialNumber,
				dfmEventId, dfmEventName, dfmEventSeverity,
				dfmEventTimestamp, dfmEventMessage, 
				dfmEventMessageDetails,
				dfmEventSourceId, dfmEventSourceTable,
				dfmObjectId, dfmObjectType, dfmObjectFullName,
				dfmObjectStatus, dfmEventSourceProductId,
				dfmHostFullName, dfmCommentFields,
				dfmPhysicalHostId, dfmPhysicalHostFullName
			}
	DESCRIPTION	
		"The aggregate has not over deduplicated."
		
	::= 11296
	
	dfmEvtDatasetMemberDeduplicated TRAP-TYPE
	ENTERPRISE		netappDataFabricManager
	VARIABLES	{
				dfmSerialNumber, dfmEventSourceSerialNumber,
				dfmEventId, dfmEventName, dfmEventSeverity,
				dfmEventTimestamp, dfmEventMessage, 
				dfmEventMessageDetails,
				dfmEventSourceId, dfmEventSourceTable,
				dfmObjectId, dfmObjectType, dfmObjectFullName,
				dfmObjectStatus, dfmEventSourceProductId,
				dfmHostFullName, dfmCommentFields,
				dfmPhysicalHostId, dfmPhysicalHostFullName
			}
	DESCRIPTION	
		"The dataset member deduplication is successful."
		
	::= 11297

	dfmEvtDatasetMemberDeduplicationFailed TRAP-TYPE
	ENTERPRISE		netappDataFabricManager
	VARIABLES	{
				dfmSerialNumber, dfmEventSourceSerialNumber,
				dfmEventId, dfmEventName, dfmEventSeverity,
				dfmEventTimestamp, dfmEventMessage, 
				dfmEventMessageDetails,
				dfmEventSourceId, dfmEventSourceTable,
				dfmObjectId, dfmObjectType, dfmObjectFullName,
				dfmObjectStatus, dfmEventSourceProductId,
				dfmHostFullName, dfmCommentFields,
				dfmPhysicalHostId, dfmPhysicalHostFullName
			}
	DESCRIPTION	
		"The dataset member deduplication failed."

	::= 11298


	dfmEvtDatasetMemberUndeduplicated TRAP-TYPE
	ENTERPRISE		netappDataFabricManager
	VARIABLES	{
				dfmSerialNumber, dfmEventSourceSerialNumber,
				dfmEventId, dfmEventName, dfmEventSeverity,
				dfmEventTimestamp, dfmEventMessage, 
				dfmEventMessageDetails,
				dfmEventSourceId, dfmEventSourceTable,
				dfmObjectId, dfmObjectType, dfmObjectFullName,
				dfmObjectStatus, dfmEventSourceProductId,
				dfmHostFullName, dfmCommentFields,
				dfmPhysicalHostId, dfmPhysicalHostFullName
			}
	DESCRIPTION	
		"The dataset member undeduplication was successful."

	::= 11299

	dfmEvtDatasetMemberUndeduplicationFailed TRAP-TYPE
	ENTERPRISE		netappDataFabricManager
	VARIABLES	{
				dfmSerialNumber, dfmEventSourceSerialNumber,
				dfmEventId, dfmEventName, dfmEventSeverity,
				dfmEventTimestamp, dfmEventMessage, 
				dfmEventMessageDetails,
				dfmEventSourceId, dfmEventSourceTable,
				dfmObjectId, dfmObjectType, dfmObjectFullName,
				dfmObjectStatus, dfmEventSourceProductId,
				dfmHostFullName, dfmCommentFields,
				dfmPhysicalHostId, dfmPhysicalHostFullName
			}
	DESCRIPTION	
		"The dataset member undeduplication failed."

	::= 11300

	dfmEvtHostNfsServiceStatusUp	TRAP-TYPE	
	ENTERPRISE		netappDataFabricManager
	VARIABLES	{
				dfmSerialNumber, dfmEventSourceSerialNumber,
				dfmEventId, dfmEventName, dfmEventSeverity,
				dfmEventTimestamp, dfmEventMessage, 
				dfmEventMessageDetails,
				dfmEventSourceId, dfmEventSourceTable,
				dfmObjectId, dfmObjectType, dfmObjectFullName,
				dfmObjectStatus, dfmEventSourceProductId,
				dfmHostFullName, dfmCommentFields,
				dfmPhysicalHostId, dfmPhysicalHostFullName
			}
	DESCRIPTION	
		"The NFS protocol service is up on the host."

	::= 11310
	
	dfmEvtHostNfsServiceStatusDown	TRAP-TYPE	
	ENTERPRISE		netappDataFabricManager
	VARIABLES	{
				dfmSerialNumber, dfmEventSourceSerialNumber,
				dfmEventId, dfmEventName, dfmEventSeverity,
				dfmEventTimestamp, dfmEventMessage, 
				dfmEventMessageDetails,
				dfmEventSourceId, dfmEventSourceTable,
				dfmObjectId, dfmObjectType, dfmObjectFullName,
				dfmObjectStatus, dfmEventSourceProductId,
				dfmHostFullName, dfmCommentFields,
				dfmPhysicalHostId, dfmPhysicalHostFullName
			}
	DESCRIPTION	
		"The NFS protocol service is down on the host."

	::= 11371

	dfmEvtHostCifsServiceStatusUp	TRAP-TYPE	
	ENTERPRISE		netappDataFabricManager
	VARIABLES	{
				dfmSerialNumber, dfmEventSourceSerialNumber,
				dfmEventId, dfmEventName, dfmEventSeverity,
				dfmEventTimestamp, dfmEventMessage, 
				dfmEventMessageDetails,
				dfmEventSourceId, dfmEventSourceTable,
				dfmObjectId, dfmObjectType, dfmObjectFullName,
				dfmObjectStatus, dfmEventSourceProductId,
				dfmHostFullName, dfmCommentFields,
				dfmPhysicalHostId, dfmPhysicalHostFullName
			}
	DESCRIPTION	
		"The CIFS protocol service is up on the host."

	::= 11372
	
	dfmEvtHostCifsServiceStatusDown	TRAP-TYPE	
	ENTERPRISE		netappDataFabricManager
	VARIABLES	{
				dfmSerialNumber, dfmEventSourceSerialNumber,
				dfmEventId, dfmEventName, dfmEventSeverity,
				dfmEventTimestamp, dfmEventMessage, 
				dfmEventMessageDetails,
				dfmEventSourceId, dfmEventSourceTable,
				dfmObjectId, dfmObjectType, dfmObjectFullName,
				dfmObjectStatus, dfmEventSourceProductId,
				dfmHostFullName, dfmCommentFields,
				dfmPhysicalHostId, dfmPhysicalHostFullName
			}
	DESCRIPTION	
		"The CIFS protocol service is down on the host."

	::= 11373
	
	dfmEvtHostIscsiServiceStatusUp	TRAP-TYPE	
	ENTERPRISE		netappDataFabricManager
	VARIABLES	{
				dfmSerialNumber, dfmEventSourceSerialNumber,
				dfmEventId, dfmEventName, dfmEventSeverity,
				dfmEventTimestamp, dfmEventMessage, 
				dfmEventMessageDetails,
				dfmEventSourceId, dfmEventSourceTable,
				dfmObjectId, dfmObjectType, dfmObjectFullName,
				dfmObjectStatus, dfmEventSourceProductId,
				dfmHostFullName, dfmCommentFields,
				dfmPhysicalHostId, dfmPhysicalHostFullName
			}
	DESCRIPTION	
		"The iSCSI protocol service is up on the host."

	::= 11374
	
	dfmEvtHostIscsiServiceStatusDown TRAP-TYPE	
	ENTERPRISE		netappDataFabricManager
	VARIABLES	{
				dfmSerialNumber, dfmEventSourceSerialNumber,
				dfmEventId, dfmEventName, dfmEventSeverity,
				dfmEventTimestamp, dfmEventMessage, 
				dfmEventMessageDetails,
				dfmEventSourceId, dfmEventSourceTable,
				dfmObjectId, dfmObjectType, dfmObjectFullName,
				dfmObjectStatus, dfmEventSourceProductId,
				dfmHostFullName, dfmCommentFields,
				dfmPhysicalHostId, dfmPhysicalHostFullName
			}
	DESCRIPTION	
		"The iSCSI protocol service is down on the host."

	::= 11375

	dfmEvtHostFcpServiceStatusUp	TRAP-TYPE
	ENTERPRISE		netappDataFabricManager
	VARIABLES	{
				dfmSerialNumber, dfmEventSourceSerialNumber,
				dfmEventId, dfmEventName, dfmEventSeverity,
				dfmEventTimestamp, dfmEventMessage, 
				dfmEventMessageDetails,
				dfmEventSourceId, dfmEventSourceTable,
				dfmObjectId, dfmObjectType, dfmObjectFullName,
				dfmObjectStatus, dfmEventSourceProductId,
				dfmHostFullName, dfmCommentFields,
				dfmPhysicalHostId, dfmPhysicalHostFullName
			}
	DESCRIPTION	
		"The FCP protocol service is up on the host."

	::= 11376
	
	dfmEvtHostFcpServiceStatusDown	TRAP-TYPE	
	ENTERPRISE		netappDataFabricManager
	VARIABLES	{
				dfmSerialNumber, dfmEventSourceSerialNumber,
				dfmEventId, dfmEventName, dfmEventSeverity,
				dfmEventTimestamp, dfmEventMessage, 
				dfmEventMessageDetails,
				dfmEventSourceId, dfmEventSourceTable,
				dfmObjectId, dfmObjectType, dfmObjectFullName,
				dfmObjectStatus, dfmEventSourceProductId,
				dfmHostFullName, dfmCommentFields,
				dfmPhysicalHostId, dfmPhysicalHostFullName
			}
	DESCRIPTION	
		"The FCP protocol service is down on the host."

	::= 11377

	dfmEvtCommentFieldCreated	TRAP-TYPE
	ENTERPRISE			netappDataFabricManager
	VARIABLES	{
				dfmSerialNumber, dfmEventSourceSerialNumber,
				dfmEventId, dfmEventName, dfmEventSeverity,
				dfmEventTimestamp, dfmEventMessage, 
				dfmEventMessageDetails,
				dfmEventSourceId, dfmEventSourceTable,
				dfmObjectId, dfmObjectType, dfmObjectFullName,
				dfmObjectStatus, dfmEventSourceProductId,
				dfmHostFullName, dfmCommentFields,
				dfmPhysicalHostId, dfmPhysicalHostFullName
			}
	DESCRIPTION
		"A comment field has been created."
	::= 11378

	dfmEvtCommentFieldModified	TRAP-TYPE
	ENTERPRISE			netappDataFabricManager
	VARIABLES	{
				dfmSerialNumber, dfmEventSourceSerialNumber,
				dfmEventId, dfmEventName, dfmEventSeverity,
				dfmEventTimestamp, dfmEventMessage, 
				dfmEventMessageDetails,
				dfmEventSourceId, dfmEventSourceTable,
				dfmObjectId, dfmObjectType, dfmObjectFullName,
				dfmObjectStatus, dfmEventSourceProductId,
				dfmHostFullName, dfmCommentFields,
				dfmPhysicalHostId, dfmPhysicalHostFullName
			}
	DESCRIPTION
		"A comment field has been modified."
	::= 11379

	dfmEvtCommentFieldDestroyed	TRAP-TYPE
	ENTERPRISE			netappDataFabricManager
	VARIABLES	{
				dfmSerialNumber, dfmEventSourceSerialNumber,
				dfmEventId, dfmEventName, dfmEventSeverity,
				dfmEventTimestamp, dfmEventMessage, 
				dfmEventMessageDetails,
				dfmEventSourceId, dfmEventSourceTable,
				dfmObjectId, dfmObjectType, dfmObjectFullName,
				dfmObjectStatus, dfmEventSourceProductId,
				dfmHostFullName, dfmCommentFields,
				dfmPhysicalHostId, dfmPhysicalHostFullName
			}
	DESCRIPTION
		"A comment field has been destroyed."
	::= 11380

	dfmEvtNfsPerClientStatsEnabled	TRAP-TYPE
	ENTERPRISE			netappDataFabricManager
	VARIABLES	{
				dfmSerialNumber, dfmEventSourceSerialNumber,
				dfmEventId, dfmEventName, dfmEventSeverity,
				dfmEventTimestamp, dfmEventMessage, 
				dfmEventMessageDetails,
				dfmEventSourceId, dfmEventSourceTable,
				dfmObjectId, dfmObjectType, dfmObjectFullName,
				dfmObjectStatus, dfmEventSourceProductId,
				dfmHostFullName, dfmCommentFields,
				dfmPhysicalHostId, dfmPhysicalHostFullName
			}
	DESCRIPTION
		"NFS per-client statistics collection enabled for the object."
	::= 11390

	dfmEvtNfsPerClientStatsDisabled	TRAP-TYPE
	ENTERPRISE			netappDataFabricManager
	VARIABLES	{
				dfmSerialNumber, dfmEventSourceSerialNumber,
				dfmEventId, dfmEventName, dfmEventSeverity,
				dfmEventTimestamp, dfmEventMessage, 
				dfmEventMessageDetails,
				dfmEventSourceId, dfmEventSourceTable,
				dfmObjectId, dfmObjectType, dfmObjectFullName,
				dfmObjectStatus, dfmEventSourceProductId,
				dfmHostFullName, dfmCommentFields,
				dfmPhysicalHostId, dfmPhysicalHostFullName
			}
	DESCRIPTION
		"NFS per-client statistics collection disabled for the object."
	::= 11391

	dfmEvtCifsPerClientStatsEnabled	TRAP-TYPE
	ENTERPRISE			netappDataFabricManager
	VARIABLES	{
				dfmSerialNumber, dfmEventSourceSerialNumber,
				dfmEventId, dfmEventName, dfmEventSeverity,
				dfmEventTimestamp, dfmEventMessage, 
				dfmEventMessageDetails,
				dfmEventSourceId, dfmEventSourceTable,
				dfmObjectId, dfmObjectType, dfmObjectFullName,
				dfmObjectStatus, dfmEventSourceProductId,
				dfmHostFullName, dfmCommentFields,
				dfmPhysicalHostId, dfmPhysicalHostFullName
			}
	DESCRIPTION
		"CIFS per-client statistics collection enabled for the object."
	::= 11392

	dfmEvtCifsPerClientStatsDisabled	TRAP-TYPE
	ENTERPRISE			netappDataFabricManager
	VARIABLES	{
				dfmSerialNumber, dfmEventSourceSerialNumber,
				dfmEventId, dfmEventName, dfmEventSeverity,
				dfmEventTimestamp, dfmEventMessage, 
				dfmEventMessageDetails,
				dfmEventSourceId, dfmEventSourceTable,
				dfmObjectId, dfmObjectType, dfmObjectFullName,
				dfmObjectStatus, dfmEventSourceProductId,
				dfmHostFullName, dfmCommentFields,
				dfmPhysicalHostId, dfmPhysicalHostFullName
			}
	DESCRIPTION
		"CIFS per-client statistics collection disabled for the object."
	::= 11393
	
	-- Virtual Server Related Events

	dfmEvtVserverDiscovered	TRAP-TYPE
	ENTERPRISE		netappDataFabricManager
	VARIABLES	{
				dfmSerialNumber, dfmEventSourceSerialNumber,
				dfmEventId, dfmEventName, dfmEventSeverity,
				dfmEventTimestamp, dfmEventMessage, 
				dfmEventMessageDetails,
				dfmEventSourceId, dfmEventSourceTable,
				dfmObjectId, dfmObjectType, dfmObjectFullName,
				dfmObjectStatus, dfmEventSourceProductId,
				dfmHostFullName, dfmCommentFields
			}
	DESCRIPTION
		"A Virtual Server was discovered on a cluster." 
	::= 11421


	dfmEvtVserverDeleted	TRAP-TYPE
	ENTERPRISE			netappDataFabricManager
	VARIABLES	{
				dfmSerialNumber, dfmEventSourceSerialNumber,
				dfmEventId, dfmEventName, dfmEventSeverity,
				dfmEventTimestamp, dfmEventMessage, 
				dfmEventMessageDetails,
				dfmEventSourceId, dfmEventSourceTable,
				dfmObjectId, dfmObjectType, dfmObjectFullName,
				dfmObjectStatus, dfmEventSourceProductId,
				dfmHostFullName, dfmCommentFields
			}
	DESCRIPTION
		"A Virtual Server was deleted on a cluster." 
	::= 11422

	dfmEvtVserverRenamed	TRAP-TYPE
	ENTERPRISE			netappDataFabricManager
	VARIABLES	{
				dfmSerialNumber, dfmEventSourceSerialNumber,
				dfmEventId, dfmEventName, dfmEventSeverity,
				dfmEventTimestamp, dfmEventMessage, 
				dfmEventMessageDetails,
				dfmEventSourceId, dfmEventSourceTable,
				dfmObjectId, dfmObjectType, dfmObjectFullName,
				dfmObjectStatus, dfmEventSourceProductId,
				dfmHostFullName, dfmCommentFields
			}
	DESCRIPTION
		"A Virtual Server was renamed on a cluster." 
	::= 11423

	-- Cluster Related Events

	dfmEvtClusterDiscovered	TRAP-TYPE
	ENTERPRISE		netappDataFabricManager
	VARIABLES	{
				dfmSerialNumber, dfmEventSourceSerialNumber,
				dfmEventId, dfmEventName, dfmEventSeverity,
				dfmEventTimestamp, dfmEventMessage, 
				dfmEventMessageDetails,
				dfmEventSourceId, dfmEventSourceTable,
				dfmObjectId, dfmObjectType, dfmObjectFullName,
				dfmObjectStatus, dfmEventSourceProductId,
				dfmHostFullName, dfmCommentFields
			}
	DESCRIPTION
		"A Cluster was discovered." 
	::= 11431

	dfmEvtClusterRenamed	TRAP-TYPE
	ENTERPRISE		netappDataFabricManager
	VARIABLES	{
				dfmSerialNumber, dfmEventSourceSerialNumber,
				dfmEventId, dfmEventName, dfmEventSeverity,
				dfmEventTimestamp, dfmEventMessage, 
				dfmEventMessageDetails,
				dfmEventSourceId, dfmEventSourceTable,
				dfmObjectId, dfmObjectType, dfmObjectFullName,
				dfmObjectStatus, dfmEventSourceProductId,
				dfmHostFullName, dfmCommentFields
			}
	DESCRIPTION
		"A Cluster was renamed." 
	::= 11432

	dfmEvtClusterNodeAdded	TRAP-TYPE
	ENTERPRISE		netappDataFabricManager
	VARIABLES	{
				dfmSerialNumber, dfmEventSourceSerialNumber,
				dfmEventId, dfmEventName, dfmEventSeverity,
				dfmEventTimestamp, dfmEventMessage, 
				dfmEventMessageDetails,
				dfmEventSourceId, dfmEventSourceTable,
				dfmObjectId, dfmObjectType, dfmObjectFullName,
				dfmObjectStatus, dfmEventSourceProductId,
				dfmHostFullName, dfmCommentFields
			}
	DESCRIPTION
		"A Node was added to this Cluster." 
	::= 11433

	dfmEvtClusterNodeRemoved	TRAP-TYPE
	ENTERPRISE		netappDataFabricManager
	VARIABLES	{
				dfmSerialNumber, dfmEventSourceSerialNumber,
				dfmEventId, dfmEventName, dfmEventSeverity,
				dfmEventTimestamp, dfmEventMessage, 
				dfmEventMessageDetails,
				dfmEventSourceId, dfmEventSourceTable,
				dfmObjectId, dfmObjectType, dfmObjectFullName,
				dfmObjectStatus, dfmEventSourceProductId,
				dfmHostFullName, dfmCommentFields
			}
	DESCRIPTION
		"A Node was removed from this Cluster." 
	::= 11434

	-- Net Port events

	dfmEvtPortStatusUndef		TRAP-TYPE
	ENTERPRISE		netappDataFabricManager
	VARIABLES	{
				dfmSerialNumber, dfmEventSourceSerialNumber,
				dfmEventId, dfmEventName, dfmEventSeverity,
				dfmEventTimestamp, dfmEventMessage, 
				dfmEventMessageDetails,
				dfmEventSourceId, dfmEventSourceTable,
				dfmObjectId, dfmObjectType, dfmObjectFullName,
				dfmObjectStatus, dfmEventSourceProductId,
				dfmHostFullName, dfmCommentFields
			}
	DESCRIPTION
		"Status of the Port of an appliance that DFM has been 
		managing is Undefined."
	::= 11435
	
	dfmEvtPortStatusUp		TRAP-TYPE
	ENTERPRISE		netappDataFabricManager
	VARIABLES	{
				dfmSerialNumber, dfmEventSourceSerialNumber,
				dfmEventId, dfmEventName, dfmEventSeverity,
				dfmEventTimestamp, dfmEventMessage, 
				dfmEventMessageDetails,
				dfmEventSourceId, dfmEventSourceTable,
				dfmObjectId, dfmObjectType, dfmObjectFullName,
				dfmObjectStatus, dfmEventSourceProductId,
				dfmHostFullName, dfmCommentFields
			}
	DESCRIPTION
		"Status of the Port of an appliance that DFM has been 
		managing is Up."
	::= 11436

	dfmEvtPortStatusDown		TRAP-TYPE
	ENTERPRISE		netappDataFabricManager
	VARIABLES	{
				dfmSerialNumber, dfmEventSourceSerialNumber,
				dfmEventId, dfmEventName, dfmEventSeverity,
				dfmEventTimestamp, dfmEventMessage, 
				dfmEventMessageDetails,
				dfmEventSourceId, dfmEventSourceTable,
				dfmObjectId, dfmObjectType, dfmObjectFullName,
				dfmObjectStatus, dfmEventSourceProductId,
				dfmHostFullName, dfmCommentFields
			}
	DESCRIPTION
		"Status of the Port of an appliance that DFM has been 
		managing is Down."
	::= 11437
	
	dfmEvtPortStatusUnknown		TRAP-TYPE
	ENTERPRISE		netappDataFabricManager
	VARIABLES	{
				dfmSerialNumber, dfmEventSourceSerialNumber,
				dfmEventId, dfmEventName, dfmEventSeverity,
				dfmEventTimestamp, dfmEventMessage, 
				dfmEventMessageDetails,
				dfmEventSourceId, dfmEventSourceTable,
				dfmObjectId, dfmObjectType, dfmObjectFullName,
				dfmObjectStatus, dfmEventSourceProductId,
				dfmHostFullName, dfmCommentFields
			}
	DESCRIPTION
		"Status of the Port of an appliance that DFM has been 
	       	managing is Unknown."
		
	::= 11438

	dfmEvtPortRoleChange	TRAP-TYPE
	ENTERPRISE		netappDataFabricManager
	VARIABLES	{
				dfmSerialNumber, dfmEventSourceSerialNumber,
				dfmEventId, dfmEventName, dfmEventSeverity,
				dfmEventTimestamp, dfmEventMessage, 
				dfmEventMessageDetails,
				dfmEventSourceId, dfmEventSourceTable,
				dfmObjectId, dfmObjectType, dfmObjectFullName,
				dfmObjectStatus, dfmEventSourceProductId,
				dfmHostFullName, dfmCommentFields
			}
	DESCRIPTION
		"A cluster Port role has changed."
	::= 11439

	-- Logical Interface events

	dfmEvtLifStatusUp		TRAP-TYPE
	ENTERPRISE		netappDataFabricManager
	VARIABLES	{
				dfmSerialNumber, dfmEventSourceSerialNumber,
				dfmEventId, dfmEventName, dfmEventSeverity,
				dfmEventTimestamp, dfmEventMessage, 
				dfmEventMessageDetails,
				dfmEventSourceId, dfmEventSourceTable,
				dfmObjectId, dfmObjectType, dfmObjectFullName,
				dfmObjectStatus, dfmEventSourceProductId,
				dfmHostFullName, dfmCommentFields
			}
	DESCRIPTION
		"Status of the Logical Interface that DFM has been 
		managing is Up."
	::= 11440

	dfmEvtLifStatusDown		TRAP-TYPE
	ENTERPRISE		netappDataFabricManager
	VARIABLES	{
				dfmSerialNumber, dfmEventSourceSerialNumber,
				dfmEventId, dfmEventName, dfmEventSeverity,
				dfmEventTimestamp, dfmEventMessage, 
				dfmEventMessageDetails,
				dfmEventSourceId, dfmEventSourceTable,
				dfmObjectId, dfmObjectType, dfmObjectFullName,
				dfmObjectStatus, dfmEventSourceProductId,
				dfmHostFullName, dfmCommentFields
			}
	DESCRIPTION
		"Status of the Logical Interface that DFM has been 
		managing is Down."
	::= 11441
	
	dfmEvtLifStatusUnknown	TRAP-TYPE
	ENTERPRISE		netappDataFabricManager
	VARIABLES	{
				dfmSerialNumber, dfmEventSourceSerialNumber,
				dfmEventId, dfmEventName, dfmEventSeverity,
				dfmEventTimestamp, dfmEventMessage, 
				dfmEventMessageDetails,
				dfmEventSourceId, dfmEventSourceTable,
				dfmObjectId, dfmObjectType, dfmObjectFullName,
				dfmObjectStatus, dfmEventSourceProductId,
				dfmHostFullName, dfmCommentFields
			}
	DESCRIPTION
		"Status of the Logical Interface that DFM has been 
		managing is Unknown."
	::= 11442

	dfmEvtLifMigrated		TRAP-TYPE
	ENTERPRISE		netappDataFabricManager
	VARIABLES	{
				dfmSerialNumber, dfmEventSourceSerialNumber,
				dfmEventId, dfmEventName, dfmEventSeverity,
				dfmEventTimestamp, dfmEventMessage, 
				dfmEventMessageDetails,
				dfmEventSourceId, dfmEventSourceTable,
				dfmObjectId, dfmObjectType, dfmObjectFullName,
				dfmObjectStatus, dfmEventSourceProductId,
				dfmHostFullName, dfmCommentFields
			}
	DESCRIPTION
		"Logical Interface that DFM has been managing is migrated to diffrent node."
	::= 11443

	dfmEvtSpaceManagementJobStarted TRAP-TYPE
	ENTERPRISE		netappDataFabricManager
	VARIABLES	{
				dfmSerialNumber, dfmEventSourceSerialNumber,
				dfmEventId, dfmEventName, dfmEventSeverity,
				dfmEventTimestamp, dfmEventMessage, 
				dfmEventMessageDetails,
				dfmEventSourceId, dfmEventSourceTable,
				dfmObjectId, dfmObjectType, dfmObjectFullName,
				dfmObjectStatus, dfmEventSourceProductId,
				dfmHostFullName, dfmCommentFields
			}
	DESCRIPTION
		"Space management job started."
	::= 11451

	dfmEvtSpaceManagementJobSucceeded TRAP-TYPE
	ENTERPRISE		netappDataFabricManager
	VARIABLES	{
				dfmSerialNumber, dfmEventSourceSerialNumber,
				dfmEventId, dfmEventName, dfmEventSeverity,
				dfmEventTimestamp, dfmEventMessage, 
				dfmEventMessageDetails,
				dfmEventSourceId, dfmEventSourceTable,
				dfmObjectId, dfmObjectType, dfmObjectFullName,
				dfmObjectStatus, dfmEventSourceProductId,
				dfmHostFullName, dfmCommentFields
			}
	DESCRIPTION
		"Space management job succeeded."
	::= 11452

	dfmEvtSpaceManagementJobFailed TRAP-TYPE
	ENTERPRISE		netappDataFabricManager
	VARIABLES	{
				dfmSerialNumber, dfmEventSourceSerialNumber,
				dfmEventId, dfmEventName, dfmEventSeverity,
				dfmEventTimestamp, dfmEventMessage, 
				dfmEventMessageDetails,
				dfmEventSourceId, dfmEventSourceTable,
				dfmObjectId, dfmObjectType, dfmObjectFullName,
				dfmObjectStatus, dfmEventSourceProductId,
				dfmHostFullName, dfmCommentFields
			}
	DESCRIPTION
		"Space management job failed."
	::= 11453

	dfmEvtStorageServiceCreated	TRAP-TYPE
	ENTERPRISE		netappDataFabricManager
	VARIABLES	{
				dfmSerialNumber, dfmEventSourceSerialNumber,
				dfmEventId, dfmEventName, dfmEventSeverity,
				dfmEventTimestamp, dfmEventMessage, 
				dfmEventMessageDetails,
				dfmEventSourceId, dfmEventSourceTable,
				dfmObjectId, dfmObjectType, dfmObjectFullName,
				dfmObjectStatus, dfmEventSourceProductId,
				dfmHostFullName, dfmCommentFields
			}
	DESCRIPTION
		"A storage service is created."
	::= 11461
	
	dfmEvtStorageServiceModified	TRAP-TYPE
	ENTERPRISE		netappDataFabricManager
	VARIABLES	{
				dfmSerialNumber, dfmEventSourceSerialNumber,
				dfmEventId, dfmEventName, dfmEventSeverity,
				dfmEventTimestamp, dfmEventMessage, 
				dfmEventMessageDetails,
				dfmEventSourceId, dfmEventSourceTable,
				dfmObjectId, dfmObjectType, dfmObjectFullName,
				dfmObjectStatus, dfmEventSourceProductId,
				dfmHostFullName, dfmCommentFields
			}
	DESCRIPTION
		"The storage service is modified."
	::= 11462
	
	dfmEvtStorageServiceDeleted	TRAP-TYPE
	ENTERPRISE		netappDataFabricManager
	VARIABLES	{
				dfmSerialNumber, dfmEventSourceSerialNumber,
				dfmEventId, dfmEventName, dfmEventSeverity,
				dfmEventTimestamp, dfmEventMessage, 
				dfmEventMessageDetails,
				dfmEventSourceId, dfmEventSourceTable,
				dfmObjectId, dfmObjectType, dfmObjectFullName,
				dfmObjectStatus, dfmEventSourceProductId,
				dfmHostFullName, dfmCommentFields
			}
	DESCRIPTION
		"The storage service is destroyed."
	::= 11463
	
	dfmEvtStorageServiceDatasetProvisioned	TRAP-TYPE
	ENTERPRISE		netappDataFabricManager
	VARIABLES	{
				dfmSerialNumber, dfmEventSourceSerialNumber,
				dfmEventId, dfmEventName, dfmEventSeverity,
				dfmEventTimestamp, dfmEventMessage, 
				dfmEventMessageDetails,
				dfmEventSourceId, dfmEventSourceTable,
				dfmObjectId, dfmObjectType, dfmObjectFullName,
				dfmObjectStatus, dfmEventSourceProductId,
				dfmHostFullName, dfmCommentFields
			}
	DESCRIPTION
		"A dataset has been provisioned from the storage service."
	::= 11464
	
	dfmEvtStorageServiceDatasetDetached	TRAP-TYPE
	ENTERPRISE		netappDataFabricManager
	VARIABLES	{
				dfmSerialNumber, dfmEventSourceSerialNumber,
				dfmEventId, dfmEventName, dfmEventSeverity,
				dfmEventTimestamp, dfmEventMessage, 
				dfmEventMessageDetails,
				dfmEventSourceId, dfmEventSourceTable,
				dfmObjectId, dfmObjectType, dfmObjectFullName,
				dfmObjectStatus, dfmEventSourceProductId,
				dfmHostFullName, dfmCommentFields
			}
	DESCRIPTION
		"The dataset has been detached from the storage service."
	::= 11465
	
	dfmEvtStorageServiceDatasetAttached	TRAP-TYPE
	ENTERPRISE		netappDataFabricManager
	VARIABLES	{
				dfmSerialNumber, dfmEventSourceSerialNumber,
				dfmEventId, dfmEventName, dfmEventSeverity,
				dfmEventTimestamp, dfmEventMessage, 
				dfmEventMessageDetails,
				dfmEventSourceId, dfmEventSourceTable,
				dfmObjectId, dfmObjectType, dfmObjectFullName,
				dfmObjectStatus, dfmEventSourceProductId,
				dfmHostFullName, dfmCommentFields
			}
	DESCRIPTION
		"The dataset has been attached to the storage service."
	::= 11466
	
	END
